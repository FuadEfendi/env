BEA-WEBLOGIC-MIB DEFINITIONS ::=
BEGIN

   IMPORTS
      
      DisplayString    FROM RFC1213-MIB
      
      OBJECT-TYPE, MODULE-IDENTITY, Counter32, Integer32, 
      Counter64, NOTIFICATION-TYPE    FROM SNMPv2-SMI
      
   ;
   
   wls MODULE-IDENTITY
      LAST-UPDATED "201909120345Z"
      ORGANIZATION "BEA Systems Inc."
      CONTACT-INFO "www.bea.com"
      DESCRIPTION "BEA"
      ::= { bea 625  }
      
   
   bea OBJECT IDENTIFIER ::= { iso 3 6 1 4 1 140  }
   
   experimental OBJECT IDENTIFIER ::= { wls 10  }
   
   trapVars OBJECT IDENTIFIER ::= { wls 100  }
   
   alsb OBJECT IDENTIFIER ::= { bea 800  }
   
   alsbTrapVars OBJECT IDENTIFIER ::= { alsb 100  }
   
   mibObjectName OBJECT-TYPE
      SYNTAX      DisplayString (SIZE (1..512))
      MAX-ACCESS  read-write
      STATUS      current
      DESCRIPTION "Name of the Mib Object in the form <MBeanType>:<MBeanName>:<AttributeName>."
      ::= { experimental 1  }
   
   mibObjectOid OBJECT-TYPE
      SYNTAX      OBJECT IDENTIFIER
      MAX-ACCESS  read-only
      STATUS      current
      DESCRIPTION "The Oid of the Mib object name, that was specified in the MibObjectName."
      ::= { experimental 2  }
   
   trapTime OBJECT-TYPE
      SYNTAX      DisplayString (SIZE (1..32))
      MAX-ACCESS  read-only
      STATUS      current
      DESCRIPTION "A string that indicates the time"
      ::= { trapVars 5  }
   
   trapServerName OBJECT-TYPE
      SYNTAX      DisplayString (SIZE (1..64))
      MAX-ACCESS  read-only
      STATUS      current
      DESCRIPTION "A string that indicates the server which generated the trap"
      ::= { trapVars 10  }
   
   trapMachineName OBJECT-TYPE
      SYNTAX      DisplayString (SIZE (1..64))
      MAX-ACCESS  read-only
      STATUS      current
      DESCRIPTION "A string that indicates the machine where the trap is generated"
      ::= { trapVars 15  }
   
   trapLogThreadId OBJECT-TYPE
      SYNTAX      DisplayString (SIZE (1..16))
      MAX-ACCESS  read-only
      STATUS      current
      DESCRIPTION "An integer that indicates the if of the thread in which the trap is generated"
      ::= { trapVars 20  }
   
   trapLogTransactionId OBJECT-TYPE
      SYNTAX      DisplayString (SIZE (1..64))
      MAX-ACCESS  read-only
      STATUS      current
      DESCRIPTION "A string that indicates the transactions from which the trap is generated"
      ::= { trapVars 25  }
   
   trapLogUserId OBJECT-TYPE
      SYNTAX      DisplayString (SIZE (1..32))
      MAX-ACCESS  read-only
      STATUS      current
      DESCRIPTION "A string that indicates the user id from which the trap is generated"
      ::= { trapVars 30  }
   
   trapLogSubsystem OBJECT-TYPE
      SYNTAX      DisplayString (SIZE (1..32))
      MAX-ACCESS  read-only
      STATUS      current
      DESCRIPTION "A string that indicates the subsystem from which the trap is generated"
      ::= { trapVars 35  }
   
   trapLogMsgId OBJECT-TYPE
      SYNTAX      DisplayString (SIZE (1..16))
      MAX-ACCESS  read-only
      STATUS      current
      DESCRIPTION "An intefer that indicates the trap's message id"
      ::= { trapVars 40  }
   
   trapLogSeverity OBJECT-TYPE
      SYNTAX      DisplayString (SIZE (1..16))
      MAX-ACCESS  read-only
      STATUS      current
      DESCRIPTION "A string that indicates the severity of the trap's message"
      ::= { trapVars 45  }
   
   trapLogMessage OBJECT-TYPE
      SYNTAX      DisplayString (SIZE (1..1024))
      MAX-ACCESS  read-only
      STATUS      current
      DESCRIPTION "A string that includes the body of the log message"
      ::= { trapVars 50  }
   
   trapMonitorType OBJECT-TYPE
      SYNTAX      DisplayString (SIZE (1..16))
      MAX-ACCESS  read-only
      STATUS      current
      DESCRIPTION "A string that should be either CounterMonitor, or GaugeMonitor, or StringMonitor"
      ::= { trapVars 55  }
   
   trapMonitorThreshold OBJECT-TYPE
      SYNTAX      DisplayString (SIZE (1..32))
      MAX-ACCESS  read-only
      STATUS      current
      DESCRIPTION "An ASCII-string representation of the value which triggerd this monitor"
      ::= { trapVars 60  }
   
   trapMonitorValue OBJECT-TYPE
      SYNTAX      DisplayString (SIZE (1..32))
      MAX-ACCESS  read-only
      STATUS      current
      DESCRIPTION "An ASCII-string representation, which is the derived value"
      ::= { trapVars 65  }
   
   trapMBeanName OBJECT-TYPE
      SYNTAX      DisplayString (SIZE (1..256))
      MAX-ACCESS  read-only
      STATUS      current
      DESCRIPTION "The Name of the MBean"
      ::= { trapVars 70  }
   
   trapMBeanType OBJECT-TYPE
      SYNTAX      DisplayString (SIZE (1..256))
      MAX-ACCESS  read-only
      STATUS      current
      DESCRIPTION "The type of the MBean"
      ::= { trapVars 75  }
   
   trapAttributeName OBJECT-TYPE
      SYNTAX      DisplayString (SIZE (1..256))
      MAX-ACCESS  read-only
      STATUS      current
      DESCRIPTION "The name of an attribute"
      ::= { trapVars 80  }
   
   trapAttributeType OBJECT-TYPE
      SYNTAX      DisplayString (SIZE (1..32))
      MAX-ACCESS  read-only
      STATUS      current
      DESCRIPTION "The type of an attribute"
      ::= { trapVars 85  }
   
   trapAttributeChangeType OBJECT-TYPE
      SYNTAX      DisplayString (SIZE (1..32))
      MAX-ACCESS  read-only
      STATUS      current
      DESCRIPTION "The type of Change, an attribute has gone thru. It can be either ADD, or REMOVE, or UPDATE"
      ::= { trapVars 90  }
   
   trapAttributeOldVal OBJECT-TYPE
      SYNTAX      DisplayString (SIZE (1..512))
      MAX-ACCESS  read-only
      STATUS      current
      DESCRIPTION "The OLD value of an attribute"
      ::= { trapVars 95  }
   
   trapAttributeNewVal OBJECT-TYPE
      SYNTAX      DisplayString (SIZE (1..512))
      MAX-ACCESS  read-only
      STATUS      current
      DESCRIPTION "The NEW value of an attribute"
      ::= { trapVars 100  }
   
   trapConfigName OBJECT-TYPE
      SYNTAX      DisplayString (SIZE (1..512))
      MAX-ACCESS  read-only
      STATUS      current
      DESCRIPTION "The configuration name of the SNMP monitor."
      ::= { trapVars 101  }
   
   trapWatchName OBJECT-TYPE
      SYNTAX      DisplayString (SIZE (1..512))
      MAX-ACCESS  read-only
      STATUS      current
      DESCRIPTION "The name of the watch that evaluated to true"
      ::= { trapVars 105  }
   
   trapWatchRuleType OBJECT-TYPE
      SYNTAX      DisplayString (SIZE (1..32))
      MAX-ACCESS  read-only
      STATUS      current
      DESCRIPTION "The type of watch rule"
      ::= { trapVars 110  }
   
   trapWatchRule OBJECT-TYPE
      SYNTAX      DisplayString (SIZE (1..2048))
      MAX-ACCESS  read-only
      STATUS      current
      DESCRIPTION "The watch rule expression"
      ::= { trapVars 115  }
   
   trapWatchSeverity OBJECT-TYPE
      SYNTAX      DisplayString (SIZE (1..16))
      MAX-ACCESS  read-only
      STATUS      current
      DESCRIPTION "A string that indicates the severity of the watch rule"
      ::= { trapVars 120  }
   
   trapWatchData OBJECT-TYPE
      SYNTAX      DisplayString (SIZE (1..2048))
      MAX-ACCESS  read-only
      STATUS      current
      DESCRIPTION "A string that indicates the key value data of the event that satisfied the watch rule"
      ::= { trapVars 125  }
   
   trapWatchAlarmType OBJECT-TYPE
      SYNTAX      DisplayString (SIZE (1..32))
      MAX-ACCESS  read-only
      STATUS      current
      DESCRIPTION "The type of alarm for the watch rule"
      ::= { trapVars 130  }
   
   trapWatchAlarmResetPeriod OBJECT-TYPE
      SYNTAX      DisplayString (SIZE (1..16))
      MAX-ACCESS  read-only
      STATUS      current
      DESCRIPTION "The period to elaspe before the alarm is reset applicable for AutomaticReset type watches"
      ::= { trapVars 135  }
   
   trapWatchSNMPNotificationName OBJECT-TYPE
      SYNTAX      DisplayString (SIZE (1..16))
      MAX-ACCESS  read-only
      STATUS      current
      DESCRIPTION "The name of the configured WLDFSNMPNotification that issued this trap"
      ::= { trapVars 140  }
   
   trapDomainName OBJECT-TYPE
      SYNTAX      DisplayString (SIZE (1..16))
      MAX-ACCESS  read-only
      STATUS      current
      DESCRIPTION "The name of the WebLogic domain in which this trap occurred"
      ::= { trapVars 145  }
   
   trapWatchModule OBJECT-TYPE
      SYNTAX      DisplayString (SIZE (1..32))
      MAX-ACCESS  read-only
      STATUS      current
      DESCRIPTION "The name of the configured WLDF module where the Watch is configured that issued this trap"
      ::= { trapVars 150  }
   
   trapALSBAlertTrapType OBJECT-TYPE
      SYNTAX      DisplayString (SIZE (1..16))
      MAX-ACCESS  read-only
      STATUS      current
      DESCRIPTION "The Type of the ALSB Alert that caused this trap to occur"
      ::= { alsbTrapVars 1  }
   
   trapALSBAlertSeverity OBJECT-TYPE
      SYNTAX      DisplayString (SIZE (1..16))
      MAX-ACCESS  read-only
      STATUS      current
      DESCRIPTION "The Severity of the ALSB Alert that caused this trap to occur"
      ::= { alsbTrapVars 2  }
   
   trapALSBAlertDomainName OBJECT-TYPE
      SYNTAX      DisplayString (SIZE (1..64))
      MAX-ACCESS  read-only
      STATUS      current
      DESCRIPTION "The Domain Name for the domain in which the ALSB Alert occurred"
      ::= { alsbTrapVars 3  }
   
   trapALSBAlertServerName OBJECT-TYPE
      SYNTAX      DisplayString (SIZE (1..64))
      MAX-ACCESS  read-only
      STATUS      current
      DESCRIPTION "The Server Name for the server on which the ALSB Alert occurred"
      ::= { alsbTrapVars 4  }
   
   trapALSBAlertAlertId OBJECT-TYPE
      SYNTAX      DisplayString (SIZE (1..64))
      MAX-ACCESS  read-only
      STATUS      current
      DESCRIPTION "The Alert Id for the ALSB Alert that caused this trap to occur"
      ::= { alsbTrapVars 5  }
   
   trapALSBAlertRuleId OBJECT-TYPE
      SYNTAX      DisplayString (SIZE (1..64))
      MAX-ACCESS  read-only
      STATUS      current
      DESCRIPTION "The Rule Id for the ALSB Alert that caused this trap to occur"
      ::= { alsbTrapVars 6  }
   
   trapALSBAlertRuleName OBJECT-TYPE
      SYNTAX      DisplayString (SIZE (1..80))
      MAX-ACCESS  read-only
      STATUS      current
      DESCRIPTION "The Rule Name for the ALSB Alert that caused this trap to occur"
      ::= { alsbTrapVars 7  }
   
   trapALSBAlertRuleCondition OBJECT-TYPE
      SYNTAX      DisplayString (SIZE (1..512))
      MAX-ACCESS  read-only
      STATUS      current
      DESCRIPTION "The Rule Condition for the ALSB Alert that caused this trap to occur"
      ::= { alsbTrapVars 8  }
   
   trapALSBAlertAlertTime OBJECT-TYPE
      SYNTAX      DisplayString (SIZE (1..48))
      MAX-ACCESS  read-only
      STATUS      current
      DESCRIPTION "The Time that the ALSB Alert was raised that caused this trap to occur"
      ::= { alsbTrapVars 9  }
   
   trapALSBAlertAnnotation OBJECT-TYPE
      SYNTAX      DisplayString (SIZE (1..1024))
      MAX-ACCESS  read-only
      STATUS      current
      DESCRIPTION "The Annotation for the ALSB Alert that caused this trap to occur"
      ::= { alsbTrapVars 10  }
   
   trapALSBAlertServiceName OBJECT-TYPE
      SYNTAX      DisplayString (SIZE (1..80))
      MAX-ACCESS  read-only
      STATUS      current
      DESCRIPTION "The Service Name for the ALSB Alert that caused this trap to occur"
      ::= { alsbTrapVars 11  }
   
   trapALSBAlertServicePath OBJECT-TYPE
      SYNTAX      DisplayString (SIZE (1..256))
      MAX-ACCESS  read-only
      STATUS      current
      DESCRIPTION "The Service Path for the ALSB Alert that caused this trap to occur"
      ::= { alsbTrapVars 12  }
   
   applicationRuntimeTable OBJECT-TYPE
      SYNTAX      SEQUENCE OF ApplicationRuntimeEntry
      MAX-ACCESS  not-accessible
      STATUS      current
      DESCRIPTION "An application represents a Java EE enterprise application packaged in an EAR file or EAR exploded directory. The EAR file or directory contains a set of components such as WAR, EJB, and RAR connector components, each of which can be deployed on one or more targets. A target is a server or a cluster. Modules in the application can have one of the following states:   UNPREPARED - Indicates that none of the  modules in this application are currently prepared or active. PREPARED -  Indicates that none of the  modules in this application are currently prepared or active. ACTIVATED - Indicates that at least one module in this application is currently active.   ApplicationRuntimeMBean encapsulates runtime information about a deployed enterprise application. "
      ::= { wls 105  }
      
   
   applicationRuntimeEntry OBJECT-TYPE
      SYNTAX      ApplicationRuntimeEntry
      MAX-ACCESS  not-accessible
      STATUS      current
      DESCRIPTION "Entry of applicationRuntimeTable"
      INDEX { applicationRuntimeIndex}
      ::= { applicationRuntimeTable 1 }
      
   ApplicationRuntimeEntry ::=
      SEQUENCE
      {
         applicationRuntimeIndex DisplayString,
         applicationRuntimeObjectName DisplayString,
         applicationRuntimeType DisplayString,
         applicationRuntimeName DisplayString,
         applicationRuntimeParent DisplayString,
         applicationRuntimeApplicationName DisplayString,
         applicationRuntimeApplicationVersion OCTET STRING,
         applicationRuntimeActiveVersionState INTEGER,
         applicationRuntimeOverallHealthState OCTET STRING,
         applicationRuntimeHealthState OCTET STRING,
         applicationRuntimeInternal OCTET STRING,
         applicationRuntimePartitionName OCTET STRING
      }
      
   
   applicationRuntimeIndex OBJECT-TYPE
      SYNTAX      DisplayString (SIZE (1..16))
      MAX-ACCESS  read-only
      STATUS      current
      DESCRIPTION "Unique value directed from ObjectName which is used as table index"
      ::= { applicationRuntimeEntry 1  }
   
   
   applicationRuntimeObjectName OBJECT-TYPE
      SYNTAX      DisplayString (SIZE (1..256))
      MAX-ACCESS  read-only
      STATUS      current
      DESCRIPTION "JMX-standard MBean name"
      ::= { applicationRuntimeEntry 5  }
   
   
   applicationRuntimeType OBJECT-TYPE
      SYNTAX      DisplayString (SIZE (1..64))
      MAX-ACCESS  read-only
      STATUS      current
      DESCRIPTION "Returns the type of the MBean. "
      ::= { applicationRuntimeEntry 10  }
   
   
   applicationRuntimeName OBJECT-TYPE
      SYNTAX      DisplayString (SIZE (1..64))
      MAX-ACCESS  read-only
      STATUS      current
      DESCRIPTION "The name of this configuration. WebLogic Server uses an MBean to implement and persist the configuration. "
      ::= { applicationRuntimeEntry 15  }
   
   
   applicationRuntimeParent OBJECT-TYPE
      SYNTAX      DisplayString (SIZE (1..256))
      MAX-ACCESS  read-only
      STATUS      current
      DESCRIPTION "BEA-proprietary Parent object's identification, with syntax
      <type>:<name>"
      ::= { applicationRuntimeEntry 20  }
   
   
   applicationRuntimeApplicationName OBJECT-TYPE
      SYNTAX      DisplayString (SIZE (1..2048))
      MAX-ACCESS  read-only
      STATUS      current
      DESCRIPTION "The name of the application. "
      ::= { applicationRuntimeEntry 25  }
   
   
   applicationRuntimeApplicationVersion OBJECT-TYPE
      SYNTAX      OCTET STRING
      MAX-ACCESS  read-only
      STATUS      current
      DESCRIPTION "The application's version identifier.  This is particularly useful, when using the side-by-side deployment feature, to differentiate between two different versions of the same application that are deployed at the same time.  "
      ::= { applicationRuntimeEntry 26  }
   
   
   applicationRuntimeActiveVersionState OBJECT-TYPE
      SYNTAX      INTEGER
      MAX-ACCESS  read-only
      STATUS      current
      DESCRIPTION "Specifies whether this application version is the currently active version.  An application can be the only version currently deployed, or it can have more than one version currently deployed, using the side-by-side deployment feature. If more than one version is deployed, only one version can be active. This attribute specifies the state the current application version is in.  An application can be in an INACTIVE state, which means that it has not been activated yet, or that there is more than one version of the application deployed (using side-by-side deployment) and this version is retiring.  An application can be in ACTIVE_ADMIN state, which means that it is the currently active version for administrative channel requests.  An application can be in ACTIVE state, which means that it is the currently active version for normal (non-administrative) channel requests. "
      ::= { applicationRuntimeEntry 27  }
   
   
   applicationRuntimeOverallHealthState OBJECT-TYPE
      SYNTAX      OCTET STRING
      MAX-ACCESS  read-only
      STATUS      current
      DESCRIPTION "The overall health of the application including that of some of the components that report health. Currently, only connector modules report health status and are the only ones considered in the overall health state of the application. "
      ::= { applicationRuntimeEntry 28  }
   
   
   applicationRuntimeHealthState OBJECT-TYPE
      SYNTAX      OCTET STRING
      MAX-ACCESS  read-only
      STATUS      current
      DESCRIPTION "The HealthState MBean for the application.  "
      ::= { applicationRuntimeEntry 29  }
   
   
   applicationRuntimeInternal OBJECT-TYPE
      SYNTAX      OCTET STRING
      MAX-ACCESS  read-only
      STATUS      current
      DESCRIPTION "Indicates whether this application is an internal application. Such applications are not displayed in the console or persisted in the config.xml.  "
      ::= { applicationRuntimeEntry 30  }
   
   
   applicationRuntimePartitionName OBJECT-TYPE
      SYNTAX      OCTET STRING
      MAX-ACCESS  read-only
      STATUS      current
      DESCRIPTION "The application's partition.  Returns the partition to which this application is deployed.  "
      ::= { applicationRuntimeEntry 31  }
   
   
   clusterRuntimeTable OBJECT-TYPE
      SYNTAX      SEQUENCE OF ClusterRuntimeEntry
      MAX-ACCESS  not-accessible
      STATUS      current
      DESCRIPTION "This class is used for monitoring a server's view of the members of a WebLogic cluster within a WebLogic domain. "
      ::= { wls 110  }
      
   
   clusterRuntimeEntry OBJECT-TYPE
      SYNTAX      ClusterRuntimeEntry
      MAX-ACCESS  not-accessible
      STATUS      current
      DESCRIPTION "Entry of clusterRuntimeTable"
      INDEX { clusterRuntimeIndex}
      ::= { clusterRuntimeTable 1 }
      
   ClusterRuntimeEntry ::=
      SEQUENCE
      {
         clusterRuntimeIndex  DisplayString,
         clusterRuntimeObjectName DisplayString,
         clusterRuntimeType   DisplayString,
         clusterRuntimeName   DisplayString,
         clusterRuntimeParent DisplayString,
         clusterRuntimeAliveServerCount INTEGER,
         clusterRuntimeResendRequestsCount Counter64,
         clusterRuntimeFragmentsSentCount Counter64,
         clusterRuntimeFragmentsReceivedCount Counter64,
         clusterRuntimeMulticastMessagesLostCount Counter64,
         clusterRuntimeServerNames DisplayString,
         clusterRuntimeSecondaryDistributionNames DisplayString,
         clusterRuntimePrimaryCount Counter64,
         clusterRuntimeCurrentSecondaryServer OCTET STRING,
         clusterRuntimeForeignFragmentsDroppedCount Counter64,
         clusterRuntimeDetailedSecondariesDistribution OCTET STRING,
         clusterRuntimeActiveSingletonServices OCTET STRING,
         clusterRuntimeSecondaryServerDetails OCTET STRING,
         clusterRuntimeSecondaryCount Counter64,
         clusterRuntimeHealthState OCTET STRING
      }
      
   
   clusterRuntimeIndex OBJECT-TYPE
      SYNTAX      DisplayString (SIZE (1..16))
      MAX-ACCESS  read-only
      STATUS      current
      DESCRIPTION "Unique value directed from ObjectName which is used as table index"
      ::= { clusterRuntimeEntry 1  }
   
   
   clusterRuntimeObjectName OBJECT-TYPE
      SYNTAX      DisplayString (SIZE (1..256))
      MAX-ACCESS  read-only
      STATUS      current
      DESCRIPTION "JMX-standard MBean name"
      ::= { clusterRuntimeEntry 5  }
   
   
   clusterRuntimeType OBJECT-TYPE
      SYNTAX      DisplayString (SIZE (1..64))
      MAX-ACCESS  read-only
      STATUS      current
      DESCRIPTION "Returns the type of the MBean. "
      ::= { clusterRuntimeEntry 10  }
   
   
   clusterRuntimeName OBJECT-TYPE
      SYNTAX      DisplayString (SIZE (1..64))
      MAX-ACCESS  read-only
      STATUS      current
      DESCRIPTION "The name of this configuration. WebLogic Server uses an MBean to implement and persist the configuration. "
      ::= { clusterRuntimeEntry 15  }
   
   
   clusterRuntimeParent OBJECT-TYPE
      SYNTAX      DisplayString (SIZE (1..256))
      MAX-ACCESS  read-only
      STATUS      current
      DESCRIPTION "BEA-proprietary Parent object's identification, with syntax
      <type>:<name>"
      ::= { clusterRuntimeEntry 20  }
   
   
   clusterRuntimeAliveServerCount OBJECT-TYPE
      SYNTAX      INTEGER
      MAX-ACCESS  read-only
      STATUS      current
      DESCRIPTION "Provides the current total number of alive servers in this cluster.  Returns the current total number of alive servers in this cluster. "
      ::= { clusterRuntimeEntry 25  }
   
   
   clusterRuntimeResendRequestsCount OBJECT-TYPE
      SYNTAX      Counter64
      MAX-ACCESS  read-only
      STATUS      current
      DESCRIPTION "Provides the number of state-delta messages that had to be resent because a receiving server in the cluster missed a message.  Returns the number of state-delta messages that had to be resent because a receiving server in the cluster missed a message. "
      ::= { clusterRuntimeEntry 30  }
   
   
   clusterRuntimeFragmentsSentCount OBJECT-TYPE
      SYNTAX      Counter64
      MAX-ACCESS  read-only
      STATUS      current
      DESCRIPTION "Returns the total number of message fragments sent from this server into the cluster. This is applicable to both multicast and unicast message types. "
      ::= { clusterRuntimeEntry 35  }
   
   
   clusterRuntimeFragmentsReceivedCount OBJECT-TYPE
      SYNTAX      Counter64
      MAX-ACCESS  read-only
      STATUS      current
      DESCRIPTION "Provides the total number of messages received on this server from the cluster. This is applicable to both multicast and unicast message types. "
      ::= { clusterRuntimeEntry 40  }
   
   
   clusterRuntimeMulticastMessagesLostCount OBJECT-TYPE
      SYNTAX      Counter64
      MAX-ACCESS  read-only
      STATUS      current
      DESCRIPTION "Provides the total number of in-coming multicast messages that were lost according to this server. "
      ::= { clusterRuntimeEntry 45  }
   
   
   clusterRuntimeServerNames OBJECT-TYPE
      SYNTAX      DisplayString (SIZE (1..2048))
      MAX-ACCESS  read-only
      STATUS      current
      DESCRIPTION "Provides the names of the servers in the cluster. "
      ::= { clusterRuntimeEntry 50  }
   
   
   clusterRuntimeSecondaryDistributionNames OBJECT-TYPE
      SYNTAX      DisplayString (SIZE (1..2048))
      MAX-ACCESS  read-only
      STATUS      current
      DESCRIPTION "Provides the names of the remote servers (such as myserver) for which the local server is hosting secondary objects. The name is appended with a number to indicate the number of secondaries hosted on behalf of that server. "
      ::= { clusterRuntimeEntry 55  }
   
   
   clusterRuntimePrimaryCount OBJECT-TYPE
      SYNTAX      Counter64
      MAX-ACCESS  read-only
      STATUS      current
      DESCRIPTION "Provides the number of object that the local server hosts as primaries.  Answer the number of object that the local server hosts as primaries. "
      ::= { clusterRuntimeEntry 60  }
   
   
   clusterRuntimeCurrentSecondaryServer OBJECT-TYPE
      SYNTAX      OCTET STRING
      MAX-ACCESS  read-only
      STATUS      current
      DESCRIPTION " "
      ::= { clusterRuntimeEntry 61  }
   
   
   clusterRuntimeForeignFragmentsDroppedCount OBJECT-TYPE
      SYNTAX      Counter64
      MAX-ACCESS  read-only
      STATUS      current
      DESCRIPTION "Provides the number of fragments that originated in foreign domains or clusters which use the same multicast address.  Answer the number of fragments that originated in foreign domains/cluster that use the same multicast address. "
      ::= { clusterRuntimeEntry 62  }
   
   
   clusterRuntimeDetailedSecondariesDistribution OBJECT-TYPE
      SYNTAX      OCTET STRING
      MAX-ACCESS  read-only
      STATUS      current
      DESCRIPTION "Provides the names of the remote servers (such as myserver) for which the local server is hosting secondary objects. The name is appended with a number to indicate the number of secondaries hosted on behalf of that server. "
      ::= { clusterRuntimeEntry 65  }
   
   
   clusterRuntimeActiveSingletonServices OBJECT-TYPE
      SYNTAX      OCTET STRING
      MAX-ACCESS  read-only
      STATUS      current
      DESCRIPTION "Returns an array of the names of the singleton services that are active on this server. "
      ::= { clusterRuntimeEntry 66  }
   
   
   clusterRuntimeSecondaryServerDetails OBJECT-TYPE
      SYNTAX      OCTET STRING
      MAX-ACCESS  read-only
      STATUS      current
      DESCRIPTION " "
      ::= { clusterRuntimeEntry 67  }
   
   
   clusterRuntimeSecondaryCount OBJECT-TYPE
      SYNTAX      Counter64
      MAX-ACCESS  read-only
      STATUS      current
      DESCRIPTION "Answer the number of object that the local server hosts as secondaries. "
      ::= { clusterRuntimeEntry 68  }
   
   
   clusterRuntimeHealthState OBJECT-TYPE
      SYNTAX      OCTET STRING
      MAX-ACCESS  read-only
      STATUS      current
      DESCRIPTION "Provides health information returned by the server self-health monitor service.  HEALTH_OK = 0, Server service is healthy.  HEALTH_WARN = 1, Service could have problems in the future. Check the server logs and the corresponding RuntimeMBean for more details.  HEALTH_CRITICAL = 2, Something must be done now to prevent service failure. Check the server logs and the corresponding RuntimeMBean for more details.  HEALTH_FAILED = 3, Service has failed - must be restarted. Check the server logs and the corresponding RuntimeMBean for more details.  HEALTH_OVERLOADED = 4, Service is functioning normally but there is too much work in it. CRITICAL and OVERLOADED are different. A subsystem is in the critical state when a part of it is malfunctioning, for example, stuck threads. An overloaded state means that there is more work assigned to the service than the configured threshold. A service might refuse more work in this state.  LOW_MEMORY_REASON = 'server is low on memory', Reason code that indicates that the server is low on memory. Administrators can configure low and high thresholds for memory usage. The server health changes to OVERLOADED with this reason code if the low threshold is reached.  "
      ::= { clusterRuntimeEntry 69  }
   
   
   wanreplicationRuntimeTable OBJECT-TYPE
      SYNTAX      SEQUENCE OF WanreplicationRuntimeEntry
      MAX-ACCESS  not-accessible
      STATUS      current
      DESCRIPTION "RuntimeMBean for WAN Replication "
      ::= { wls 111  }
      
   
   wanreplicationRuntimeEntry OBJECT-TYPE
      SYNTAX      WanreplicationRuntimeEntry
      MAX-ACCESS  not-accessible
      STATUS      current
      DESCRIPTION "Entry of wanreplicationRuntimeTable"
      INDEX { wanreplicationRuntimeIndex}
      ::= { wanreplicationRuntimeTable 1 }
      
   WanreplicationRuntimeEntry ::=
      SEQUENCE
      {
         wanreplicationRuntimeIndex DisplayString,
         wanreplicationRuntimeObjectName DisplayString,
         wanreplicationRuntimeType DisplayString,
         wanreplicationRuntimeName DisplayString,
         wanreplicationRuntimeParent DisplayString,
         wanreplicationRuntimeNumberOfSessionsFlushedToTheDatabase Counter64,
         wanreplicationRuntimeNumberOfSessionsRetrievedFromTheDatabase Counter64,
         wanreplicationRuntimeSecondaryServerName DisplayString,
         wanreplicationRuntimePrimaryCount Counter64,
         wanreplicationRuntimeSecondaryCount Counter64,
         wanreplicationRuntimeRemoteClusterReachable INTEGER,
         wanreplicationRuntimeDetailedSecondariesDistribution OCTET STRING,
         wanreplicationRuntimeSecondaryServerDetails OCTET STRING
      }
      
   
   wanreplicationRuntimeIndex OBJECT-TYPE
      SYNTAX      DisplayString (SIZE (1..16))
      MAX-ACCESS  read-only
      STATUS      current
      DESCRIPTION "Unique value directed from ObjectName which is used as table index"
      ::= { wanreplicationRuntimeEntry 1  }
   
   
   wanreplicationRuntimeObjectName OBJECT-TYPE
      SYNTAX      DisplayString (SIZE (1..256))
      MAX-ACCESS  read-only
      STATUS      current
      DESCRIPTION "JMX-standard MBean name"
      ::= { wanreplicationRuntimeEntry 5  }
   
   
   wanreplicationRuntimeType OBJECT-TYPE
      SYNTAX      DisplayString (SIZE (1..64))
      MAX-ACCESS  read-only
      STATUS      current
      DESCRIPTION "Returns the type of the MBean. "
      ::= { wanreplicationRuntimeEntry 10  }
   
   
   wanreplicationRuntimeName OBJECT-TYPE
      SYNTAX      DisplayString (SIZE (1..64))
      MAX-ACCESS  read-only
      STATUS      current
      DESCRIPTION "The name of this configuration. WebLogic Server uses an MBean to implement and persist the configuration. "
      ::= { wanreplicationRuntimeEntry 15  }
   
   
   wanreplicationRuntimeParent OBJECT-TYPE
      SYNTAX      DisplayString (SIZE (1..256))
      MAX-ACCESS  read-only
      STATUS      current
      DESCRIPTION "BEA-proprietary Parent object's identification, with syntax <type>:<name>"
      ::= { wanreplicationRuntimeEntry 20  }
   
   
   wanreplicationRuntimeNumberOfSessionsFlushedToTheDatabase OBJECT-TYPE
      SYNTAX      Counter64
      MAX-ACCESS  read-only
      STATUS      current
      DESCRIPTION " "
      ::= { wanreplicationRuntimeEntry 25  }
   
   
   wanreplicationRuntimeNumberOfSessionsRetrievedFromTheDatabase OBJECT-TYPE
      SYNTAX      Counter64
      MAX-ACCESS  read-only
      STATUS      current
      DESCRIPTION " "
      ::= { wanreplicationRuntimeEntry 30  }
   
   
   wanreplicationRuntimeSecondaryServerName OBJECT-TYPE
      SYNTAX      DisplayString (SIZE (1..128))
      MAX-ACCESS  read-only
      STATUS      current
      DESCRIPTION "Answer the current secondary server  "
      ::= { wanreplicationRuntimeEntry 35  }
   
   
   wanreplicationRuntimePrimaryCount OBJECT-TYPE
      SYNTAX      Counter64
      MAX-ACCESS  read-only
      STATUS      current
      DESCRIPTION "Provides the number of object that the local server hosts as primaries.  Answer the number of object that the local server hosts as primaries. "
      ::= { wanreplicationRuntimeEntry 40  }
   
   
   wanreplicationRuntimeSecondaryCount OBJECT-TYPE
      SYNTAX      Counter64
      MAX-ACCESS  read-only
      STATUS      current
      DESCRIPTION "Answer the number of object that the local server hosts as secondaries. "
      ::= { wanreplicationRuntimeEntry 45  }
   
   
   wanreplicationRuntimeRemoteClusterReachable OBJECT-TYPE
      SYNTAX      INTEGER
      MAX-ACCESS  read-only
      STATUS      current
      DESCRIPTION "Answer if the remote cluster is reachable or not. "
      ::= { wanreplicationRuntimeEntry 50  }
   
   
   wanreplicationRuntimeDetailedSecondariesDistribution OBJECT-TYPE
      SYNTAX      OCTET STRING
      MAX-ACCESS  read-only
      STATUS      current
      DESCRIPTION "Provides the names of the remote servers (such as myserver) for which the local server is hosting secondary objects. The name is appended with a number to indicate the number of secondaries hosted on behalf of that server. "
      ::= { wanreplicationRuntimeEntry 51  }
   
   
   wanreplicationRuntimeSecondaryServerDetails OBJECT-TYPE
      SYNTAX      OCTET STRING
      MAX-ACCESS  read-only
      STATUS      current
      DESCRIPTION " "
      ::= { wanreplicationRuntimeEntry 52  }
   
   
   deploymentTaskRuntimeTable OBJECT-TYPE
      SYNTAX      SEQUENCE OF DeploymentTaskRuntimeEntry
      MAX-ACCESS  not-accessible
      STATUS      current
      DESCRIPTION "This table is used for monitoring a WebLogic deploymentTask."
      ::= { wls 121  }
      
   
   deploymentTaskRuntimeEntry OBJECT-TYPE
      SYNTAX      DeploymentTaskRuntimeEntry
      MAX-ACCESS  not-accessible
      STATUS      current
      DESCRIPTION "Entry of deploymentTaskRuntimeTable"
      INDEX { deploymentTaskRuntimeIndex}
      ::= { deploymentTaskRuntimeTable 1 }
      
   DeploymentTaskRuntimeEntry ::=
      SEQUENCE
      {
         deploymentTaskRuntimeIndex DisplayString,
         deploymentTaskRuntimeObjectName DisplayString,
         deploymentTaskRuntimeType DisplayString,
         deploymentTaskRuntimeName DisplayString,
         deploymentTaskRuntimeParent DisplayString,
         deploymentTaskRuntimeApplicationName DisplayString,
         deploymentTaskRuntimeId DisplayString,
         deploymentTaskRuntimeSource DisplayString,
         deploymentTaskRuntimeState DisplayString,
         deploymentTaskRuntimeInUse INTEGER,
         deploymentTaskRuntimeNewSource DisplayString,
         deploymentTaskRuntimeSystemTask OCTET STRING,
         deploymentTaskRuntimeNotificationLevel INTEGER,
         deploymentTaskRuntimeDescription OCTET STRING,
         deploymentTaskRuntimeRunning OCTET STRING,
         deploymentTaskRuntimeStatus OCTET STRING,
         deploymentTaskRuntimeBeginTime Counter64,
         deploymentTaskRuntimeTask INTEGER,
         deploymentTaskRuntimeEndTime Counter64
      }
      
   
   deploymentTaskRuntimeIndex OBJECT-TYPE
      SYNTAX      DisplayString (SIZE (1..16))
      MAX-ACCESS  read-only
      STATUS      current
      DESCRIPTION "Unique value directed from ObjectName which is used as table index"
      ::= { deploymentTaskRuntimeEntry 1  }
   
   
   deploymentTaskRuntimeObjectName OBJECT-TYPE
      SYNTAX      DisplayString (SIZE (1..256))
      MAX-ACCESS  read-only
      STATUS      current
      DESCRIPTION "JMX-standard MBean name"
      ::= { deploymentTaskRuntimeEntry 5  }
   
   
   deploymentTaskRuntimeType OBJECT-TYPE
      SYNTAX      DisplayString (SIZE (1..64))
      MAX-ACCESS  read-only
      STATUS      current
      DESCRIPTION "BEA-proprietary MBean type"
      ::= { deploymentTaskRuntimeEntry 10  }
   
   
   deploymentTaskRuntimeName OBJECT-TYPE
      SYNTAX      DisplayString (SIZE (1..64))
      MAX-ACCESS  read-only
      STATUS      current
      DESCRIPTION "BEA-proprietary MBean name"
      ::= { deploymentTaskRuntimeEntry 15  }
   
   
   deploymentTaskRuntimeParent OBJECT-TYPE
      SYNTAX      DisplayString (SIZE (1..256))
      MAX-ACCESS  read-only
      STATUS      current
      DESCRIPTION "BEA-proprietary Parent object's identification, with syntax
      <type>:<name>"
      ::= { deploymentTaskRuntimeEntry 20  }
   
   
   deploymentTaskRuntimeApplicationName OBJECT-TYPE
      SYNTAX      DisplayString (SIZE (1..256))
      MAX-ACCESS  read-only
      STATUS      current
      DESCRIPTION "The value of the name for the application that was specified to DeployerRuntime.activate"
      ::= { deploymentTaskRuntimeEntry 25  }
   
   
   deploymentTaskRuntimeId OBJECT-TYPE
      SYNTAX      DisplayString (SIZE (1..256))
      MAX-ACCESS  read-only
      STATUS      current
      DESCRIPTION "A task can be referenced by the id assigned to it, or one the user assigns to it."
      ::= { deploymentTaskRuntimeEntry 30  }
   
   
   deploymentTaskRuntimeSource OBJECT-TYPE
      SYNTAX      DisplayString (SIZE (1..16))
      MAX-ACCESS  read-only
      STATUS      current
      DESCRIPTION "The value of the source file that was specified to DeployerRuntime.activate."
      ::= { deploymentTaskRuntimeEntry 35  }
   
   
   deploymentTaskRuntimeState OBJECT-TYPE
      SYNTAX      DisplayString (SIZE (1..32))
      MAX-ACCESS  read-only
      STATUS      current
      DESCRIPTION "Overall state of this task"
      ::= { deploymentTaskRuntimeEntry 40  }
   
   
   deploymentTaskRuntimeInUse OBJECT-TYPE
      SYNTAX      INTEGER
      MAX-ACCESS  read-only
      STATUS      current
      DESCRIPTION "This indicates if the MBean is free for deletion or timeout."
      ::= { deploymentTaskRuntimeEntry 45  }
   
   
   deploymentTaskRuntimeNewSource OBJECT-TYPE
      SYNTAX      DisplayString (SIZE (1..256))
      MAX-ACCESS  read-only
      STATUS      current
      DESCRIPTION "Indicates whether a new source for the application was specified in an activate request."
      ::= { deploymentTaskRuntimeEntry 46  }
   
   
   deploymentTaskRuntimeSystemTask OBJECT-TYPE
      SYNTAX      OCTET STRING
      MAX-ACCESS  read-only
      STATUS      current
      DESCRIPTION ""
      ::= { deploymentTaskRuntimeEntry 47  }
   
   
   deploymentTaskRuntimeNotificationLevel OBJECT-TYPE
      SYNTAX      INTEGER
      MAX-ACCESS  read-only
      STATUS      current
      DESCRIPTION "Provides the notification level applied to this task."
      ::= { deploymentTaskRuntimeEntry 48  }
   
   
   deploymentTaskRuntimeDescription OBJECT-TYPE
      SYNTAX      OCTET STRING
      MAX-ACCESS  read-only
      STATUS      current
      DESCRIPTION ""
      ::= { deploymentTaskRuntimeEntry 49  }
   
   
   deploymentTaskRuntimeRunning OBJECT-TYPE
      SYNTAX      OCTET STRING
      MAX-ACCESS  read-only
      STATUS      current
      DESCRIPTION ""
      ::= { deploymentTaskRuntimeEntry 50  }
   
   
   deploymentTaskRuntimeStatus OBJECT-TYPE
      SYNTAX      OCTET STRING
      MAX-ACCESS  read-only
      STATUS      current
      DESCRIPTION ""
      ::= { deploymentTaskRuntimeEntry 51  }
   
   
   deploymentTaskRuntimeBeginTime OBJECT-TYPE
      SYNTAX      Counter64
      MAX-ACCESS  read-only
      STATUS      current
      DESCRIPTION ""
      ::= { deploymentTaskRuntimeEntry 52  }
   
   
   deploymentTaskRuntimeTask OBJECT-TYPE
      SYNTAX      INTEGER
      MAX-ACCESS  read-only
      STATUS      current
      DESCRIPTION "Indicates a specific task associated with this MBean"
      ::= { deploymentTaskRuntimeEntry 53  }
   
   
   deploymentTaskRuntimeEndTime OBJECT-TYPE
      SYNTAX      Counter64
      MAX-ACCESS  read-only
      STATUS      current
      DESCRIPTION ""
      ::= { deploymentTaskRuntimeEntry 54  }
   
   
   domainRuntimeTable OBJECT-TYPE
      SYNTAX      SEQUENCE OF DomainRuntimeEntry
      MAX-ACCESS  not-accessible
      STATUS      current
      DESCRIPTION "This class is used for monitoring a WebLogic domain. A domain may contain zero or more clusters. A cluster may be looked up by a logical name. "
      ::= { wls 130  }
      
   
   domainRuntimeEntry OBJECT-TYPE
      SYNTAX      DomainRuntimeEntry
      MAX-ACCESS  not-accessible
      STATUS      current
      DESCRIPTION "Entry of domainRuntimeTable"
      INDEX { domainRuntimeIndex}
      ::= { domainRuntimeTable 1 }
      
   DomainRuntimeEntry ::=
      SEQUENCE
      {
         domainRuntimeIndex   DisplayString,
         domainRuntimeObjectName DisplayString,
         domainRuntimeType    DisplayString,
         domainRuntimeName    DisplayString,
         domainRuntimeParent  DisplayString,
         domainRuntimeActivationTime DisplayString
      }
      
   
   domainRuntimeIndex OBJECT-TYPE
      SYNTAX      DisplayString (SIZE (1..16))
      MAX-ACCESS  read-only
      STATUS      current
      DESCRIPTION "Unique value directed from ObjectName which is used as table index"
      ::= { domainRuntimeEntry 1  }
   
   
   domainRuntimeObjectName OBJECT-TYPE
      SYNTAX      DisplayString (SIZE (1..256))
      MAX-ACCESS  read-only
      STATUS      current
      DESCRIPTION "JMX-standard MBean name"
      ::= { domainRuntimeEntry 5  }
   
   
   domainRuntimeType OBJECT-TYPE
      SYNTAX      DisplayString (SIZE (1..64))
      MAX-ACCESS  read-only
      STATUS      current
      DESCRIPTION "Returns the type of the MBean. "
      ::= { domainRuntimeEntry 10  }
   
   
   domainRuntimeName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { domainRuntimeEntry 15  }
   
   
   domainRuntimeParent OBJECT-TYPE
      SYNTAX      DisplayString (SIZE (1..256))
      MAX-ACCESS  read-only
      STATUS      current
      DESCRIPTION "BEA-proprietary Parent object's identification, with syntax
      <type>:<name>"
      ::= { domainRuntimeEntry 20  }
   
   
   domainRuntimeActivationTime OBJECT-TYPE
      SYNTAX      DisplayString (SIZE (1..32))
      MAX-ACCESS  read-only
      STATUS      current
      DESCRIPTION "The time when the domain became active. "
      ::= { domainRuntimeEntry 25  }
   
   
   queryCacheRuntimeTable OBJECT-TYPE
      SYNTAX      SEQUENCE OF QueryCacheRuntimeEntry
      MAX-ACCESS  not-accessible
      STATUS      current
      DESCRIPTION "This interface contains accessor methods for all query cache runtime information collected for an EJB. The cache miss counts need some explaining. A query-cache miss can occur due to one of the following reasons:   The query result was not found in the query-cache The query result has timed out A bean which satisfies the query wasnot found in the entity cache A query with relationship-caching turned on did not find the related-beans query result A query which loads multiple EJBs could not load one or more of them   To better aid tuning, there are separate counters provided for each of the last four of the above causes. The fifth counter is a total cache miss counter. This counter takes into account all five causes of a cache miss. "
      ::= { wls 135  }
      
   
   queryCacheRuntimeEntry OBJECT-TYPE
      SYNTAX      QueryCacheRuntimeEntry
      MAX-ACCESS  not-accessible
      STATUS      current
      DESCRIPTION "Entry of queryCacheRuntimeTable"
      INDEX { queryCacheRuntimeIndex}
      ::= { queryCacheRuntimeTable 1 }
      
   QueryCacheRuntimeEntry ::=
      SEQUENCE
      {
         queryCacheRuntimeIndex DisplayString,
         queryCacheRuntimeObjectName DisplayString,
         queryCacheRuntimeType DisplayString,
         queryCacheRuntimeName DisplayString,
         queryCacheRuntimeParent DisplayString,
         queryCacheRuntimeTotalCachedQueriesCount INTEGER,
         queryCacheRuntimeCacheAccessCount Counter64,
         queryCacheRuntimeCacheHitCount Counter64,
         queryCacheRuntimeTotalCacheMissCount Counter64,
         queryCacheRuntimeCacheMissByTimeoutCount Counter64,
         queryCacheRuntimeCacheMissByBeanEvictionCount Counter64,
         queryCacheRuntimeCacheMissByRelatedQueryMissCount Counter64,
         queryCacheRuntimeCacheMissByDependentQueryMissCount Counter64
      }
      
   
   queryCacheRuntimeIndex OBJECT-TYPE
      SYNTAX      DisplayString (SIZE (1..16))
      MAX-ACCESS  read-only
      STATUS      current
      DESCRIPTION "Unique value directed from ObjectName which is used as table index"
      ::= { queryCacheRuntimeEntry 1  }
   
   
   queryCacheRuntimeObjectName OBJECT-TYPE
      SYNTAX      DisplayString (SIZE (1..256))
      MAX-ACCESS  read-only
      STATUS      current
      DESCRIPTION "JMX-standard MBean name"
      ::= { queryCacheRuntimeEntry 5  }
   
   
   queryCacheRuntimeType OBJECT-TYPE
      SYNTAX      DisplayString (SIZE (1..64))
      MAX-ACCESS  read-only
      STATUS      current
      DESCRIPTION "Returns the type of the MBean. "
      ::= { queryCacheRuntimeEntry 10  }
   
   
   queryCacheRuntimeName OBJECT-TYPE
      SYNTAX      DisplayString (SIZE (1..64))
      MAX-ACCESS  read-only
      STATUS      current
      DESCRIPTION "The name of this configuration. WebLogic Server uses an MBean to implement and persist the configuration. "
      ::= { queryCacheRuntimeEntry 15  }
   
   
   queryCacheRuntimeParent OBJECT-TYPE
      SYNTAX      DisplayString (SIZE (1..256))
      MAX-ACCESS  read-only
      STATUS      current
      DESCRIPTION "BEA-proprietary Parent object's identification, with syntax
      <type>:<name>"
      ::= { queryCacheRuntimeEntry 20  }
   
   
   queryCacheRuntimeTotalCachedQueriesCount OBJECT-TYPE
      SYNTAX      INTEGER
      MAX-ACCESS  read-only
      STATUS      current
      DESCRIPTION "Provides a count of the total number of query results for this EJB currently in the query cache.  Returns the total number of query results for this EJB currently in the EJB cache. "
      ::= { queryCacheRuntimeEntry 25  }
   
   
   queryCacheRuntimeCacheAccessCount OBJECT-TYPE
      SYNTAX      Counter64
      MAX-ACCESS  read-only
      STATUS      current
      DESCRIPTION "Provides a count of the number of accesses of the query cache for this EJB.  Returns the number of accesses of the query cache for this EJB. "
      ::= { queryCacheRuntimeEntry 30  }
   
   
   queryCacheRuntimeCacheHitCount OBJECT-TYPE
      SYNTAX      Counter64
      MAX-ACCESS  read-only
      STATUS      current
      DESCRIPTION "Provides a count of the number of cache hits of the query cache for this EJB.  Returns the number of cache hits of the query cache for this EJB. "
      ::= { queryCacheRuntimeEntry 35  }
   
   
   queryCacheRuntimeTotalCacheMissCount OBJECT-TYPE
      SYNTAX      Counter64
      MAX-ACCESS  read-only
      STATUS      current
      DESCRIPTION "Provides a count of the total number of cache misses of the query cache for this EJB.  Returns the total number of cache misses of the query cache for this EJB. "
      ::= { queryCacheRuntimeEntry 40  }
   
   
   queryCacheRuntimeCacheMissByTimeoutCount OBJECT-TYPE
      SYNTAX      Counter64
      MAX-ACCESS  read-only
      STATUS      current
      DESCRIPTION "Provides a count of the number of cache misses of the query cache for this EJB due to query results timing out.  Returns the number of cache misses due to query result timeout for this EJB. "
      ::= { queryCacheRuntimeEntry 45  }
   
   
   queryCacheRuntimeCacheMissByBeanEvictionCount OBJECT-TYPE
      SYNTAX      Counter64
      MAX-ACCESS  read-only
      STATUS      current
      DESCRIPTION "Provides a count of the number of cache misses of the query cache for this EJB because corresponding beans were not found in the entity cache.  Returns the number of times a cache miss occurred for this EJB because corresponding beans were not found in the entity cache. "
      ::= { queryCacheRuntimeEntry 50  }
   
   
   queryCacheRuntimeCacheMissByRelatedQueryMissCount OBJECT-TYPE
      SYNTAX      Counter64
      MAX-ACCESS  read-only
      STATUS      current
      DESCRIPTION "Provides a count of the number of cache misses of the query cache for this EJB because a related query was not found in another EJB's query cache.  Returns the number of times a cache miss occurred for this EJB because a related query was not found in another EJB's query cache. "
      ::= { queryCacheRuntimeEntry 55  }
   
   
   queryCacheRuntimeCacheMissByDependentQueryMissCount OBJECT-TYPE
      SYNTAX      Counter64
      MAX-ACCESS  read-only
      STATUS      current
      DESCRIPTION "Provides a count of the number of cache misses of the query cache for this EJB because a dependent query was not found in another EJB's query cache.  Returns the number of times a cache miss occurred for this EJB because a dependent query was not found in another EJB's query cache. "
      ::= { queryCacheRuntimeEntry 60  }
   
   
   ejbCacheRuntimeTable OBJECT-TYPE
      SYNTAX      SEQUENCE OF EjbCacheRuntimeEntry
      MAX-ACCESS  not-accessible
      STATUS      current
      DESCRIPTION "This interface contains accessor methods for all cache runtime information collected for an EJB.  Note that the sum of the cacheHitCount and cacheMissCount may not add up to the cacheAccessCount in a running server because these metrics are retrieved using multiple calls and the counts could change between the calls. "
      ::= { wls 137  }
      
   
   ejbCacheRuntimeEntry OBJECT-TYPE
      SYNTAX      EjbCacheRuntimeEntry
      MAX-ACCESS  not-accessible
      STATUS      current
      DESCRIPTION "Entry of ejbCacheRuntimeTable"
      INDEX { ejbCacheRuntimeIndex}
      ::= { ejbCacheRuntimeTable 1 }
      
   EjbCacheRuntimeEntry ::=
      SEQUENCE
      {
         ejbCacheRuntimeIndex DisplayString,
         ejbCacheRuntimeObjectName DisplayString,
         ejbCacheRuntimeType  DisplayString,
         ejbCacheRuntimeName  DisplayString,
         ejbCacheRuntimeParent DisplayString,
         ejbCacheRuntimeActivationCount DisplayString,
         ejbCacheRuntimeCacheAccessCount Counter64,
         ejbCacheRuntimeCachedBeansCurrentCount Counter64,
         ejbCacheRuntimeCacheHitCount Counter64,
         ejbCacheRuntimePassivationCount Counter64,
         ejbCacheRuntimeCacheMissCount Counter64
      }
      
   
   ejbCacheRuntimeIndex OBJECT-TYPE
      SYNTAX      DisplayString (SIZE (1..16))
      MAX-ACCESS  read-only
      STATUS      current
      DESCRIPTION "Unique value directed from ObjectName which is used as table index"
      ::= { ejbCacheRuntimeEntry 1  }
   
   
   ejbCacheRuntimeObjectName OBJECT-TYPE
      SYNTAX      DisplayString (SIZE (1..256))
      MAX-ACCESS  read-only
      STATUS      current
      DESCRIPTION "JMX-standard MBean name"
      ::= { ejbCacheRuntimeEntry 5  }
   
   
   ejbCacheRuntimeType OBJECT-TYPE
      SYNTAX      DisplayString (SIZE (1..64))
      MAX-ACCESS  read-only
      STATUS      current
      DESCRIPTION "Returns the type of the MBean. "
      ::= { ejbCacheRuntimeEntry 10  }
   
   
   ejbCacheRuntimeName OBJECT-TYPE
      SYNTAX      DisplayString (SIZE (1..64))
      MAX-ACCESS  read-only
      STATUS      current
      DESCRIPTION "The name of this configuration. WebLogic Server uses an MBean to implement and persist the configuration. "
      ::= { ejbCacheRuntimeEntry 15  }
   
   
   ejbCacheRuntimeParent OBJECT-TYPE
      SYNTAX      DisplayString (SIZE (1..256))
      MAX-ACCESS  read-only
      STATUS      current
      DESCRIPTION "BEA-proprietary Parent object's identification, with syntax
      <type>:<name>"
      ::= { ejbCacheRuntimeEntry 20  }
   
   
   ejbCacheRuntimeActivationCount OBJECT-TYPE
      SYNTAX      DisplayString (SIZE (1..16))
      MAX-ACCESS  read-only
      STATUS      current
      DESCRIPTION "Provides a count of the total number of beans from this EJB Home that have been activated. "
      ::= { ejbCacheRuntimeEntry 25  }
   
   
   ejbCacheRuntimeCacheAccessCount OBJECT-TYPE
      SYNTAX      Counter64
      MAX-ACCESS  read-only
      STATUS      current
      DESCRIPTION "Provides a count of the total number of attempts to access a bean from the cache.   The sum of the Cache Hit Count and Cache Miss Count may not add up to the cacheAccessCount in a running server because these metrics are retrieved using multiple calls and the counts could change between the calls.* "
      ::= { ejbCacheRuntimeEntry 30  }
   
   
   ejbCacheRuntimeCachedBeansCurrentCount OBJECT-TYPE
      SYNTAX      Counter64
      MAX-ACCESS  read-only
      STATUS      current
      DESCRIPTION "Provides a count of the total number of beans from this EJB Home currently in the EJB cache. "
      ::= { ejbCacheRuntimeEntry 35  }
   
   
   ejbCacheRuntimeCacheHitCount OBJECT-TYPE
      SYNTAX      Counter64
      MAX-ACCESS  read-only
      STATUS      current
      DESCRIPTION "Provides a count of the total number of times an attempt to access a bean from the cache succeeded.   The sum of the Cache Hit Count and Cache Miss Count may not add up to the cacheAccessCount in a running server because these metrics are retrieved using multiple calls and the counts could change between the calls. "
      ::= { ejbCacheRuntimeEntry 40  }
   
   
   ejbCacheRuntimePassivationCount OBJECT-TYPE
      SYNTAX      Counter64
      MAX-ACCESS  read-only
      STATUS      current
      DESCRIPTION "Provides a count of the total number of beans from this EJB Home that have been passivated. "
      ::= { ejbCacheRuntimeEntry 45  }
   
   
   ejbCacheRuntimeCacheMissCount OBJECT-TYPE
      SYNTAX      Counter64
      MAX-ACCESS  read-only
      STATUS      current
      DESCRIPTION "Provides a count of the total number of times an attempt to access a bean from the cache failed.   The sum of the Cache Hit Count and Cache Miss Count may not add up to the cacheAccessCount in a running server because these metrics are retrieved using multiple calls and the counts could change between the calls. "
      ::= { ejbCacheRuntimeEntry 46  }
   
   
   ejbRuntimeTable OBJECT-TYPE
      SYNTAX      SEQUENCE OF EjbRuntimeEntry
      MAX-ACCESS  not-accessible
      STATUS      current
      DESCRIPTION "This interface contains accessor methods for all common run-time information collected for all EJB types. "
      ::= { wls 138  }
      
   
   ejbRuntimeEntry OBJECT-TYPE
      SYNTAX      EjbRuntimeEntry
      MAX-ACCESS  not-accessible
      STATUS      current
      DESCRIPTION "Entry of ejbRuntimeTable"
      INDEX { ejbRuntimeIndex}
      ::= { ejbRuntimeTable 1 }
      
   EjbRuntimeEntry ::=
      SEQUENCE
      {
         ejbRuntimeIndex      DisplayString,
         ejbRuntimeObjectName DisplayString,
         ejbRuntimeType       DisplayString,
         ejbRuntimeName       DisplayString,
         ejbRuntimeParent     DisplayString,
         ejbRuntimeEJBName    DisplayString
      }
      
   
   ejbRuntimeIndex OBJECT-TYPE
      SYNTAX      DisplayString (SIZE (1..16))
      MAX-ACCESS  read-only
      STATUS      current
      DESCRIPTION "Unique value directed from ObjectName which is used as table index"
      ::= { ejbRuntimeEntry 1  }
   
   
   ejbRuntimeObjectName OBJECT-TYPE
      SYNTAX      DisplayString (SIZE (1..256))
      MAX-ACCESS  read-only
      STATUS      current
      DESCRIPTION "JMX-standard MBean name"
      ::= { ejbRuntimeEntry 5  }
   
   
   ejbRuntimeType OBJECT-TYPE
      SYNTAX      DisplayString (SIZE (1..64))
      MAX-ACCESS  read-only
      STATUS      current
      DESCRIPTION "Returns the type of the MBean. "
      ::= { ejbRuntimeEntry 10  }
   
   
   ejbRuntimeName OBJECT-TYPE
      SYNTAX      DisplayString (SIZE (1..64))
      MAX-ACCESS  read-only
      STATUS      current
      DESCRIPTION "The name of this configuration. WebLogic Server uses an MBean to implement and persist the configuration. "
      ::= { ejbRuntimeEntry 15  }
   
   
   ejbRuntimeParent OBJECT-TYPE
      SYNTAX      DisplayString (SIZE (1..256))
      MAX-ACCESS  read-only
      STATUS      current
      DESCRIPTION "BEA-proprietary Parent object's identification, with syntax
      <type>:<name>"
      ::= { ejbRuntimeEntry 20  }
   
   
   ejbRuntimeEJBName OBJECT-TYPE
      SYNTAX      DisplayString (SIZE (1..16))
      MAX-ACCESS  read-only
      STATUS      current
      DESCRIPTION "Provides the name for this EJB as defined in the javax.ejb.EJB annotation, or the ejb-name when * using the ejb-jar.xml deployment descriptor. "
      ::= { ejbRuntimeEntry 25  }
   
   
   ejbComponentRuntimeTable OBJECT-TYPE
      SYNTAX      SEQUENCE OF EjbComponentRuntimeEntry
      MAX-ACCESS  not-accessible
      STATUS      current
      DESCRIPTION "This is the top level interface for all runtime information collected for an EJB module. "
      ::= { wls 140  }
      
   
   ejbComponentRuntimeEntry OBJECT-TYPE
      SYNTAX      EjbComponentRuntimeEntry
      MAX-ACCESS  not-accessible
      STATUS      current
      DESCRIPTION "Entry of ejbComponentRuntimeTable"
      INDEX { ejbComponentRuntimeIndex}
      ::= { ejbComponentRuntimeTable 1 }
      
   EjbComponentRuntimeEntry ::=
      SEQUENCE
      {
         ejbComponentRuntimeIndex DisplayString,
         ejbComponentRuntimeObjectName DisplayString,
         ejbComponentRuntimeType DisplayString,
         ejbComponentRuntimeName DisplayString,
         ejbComponentRuntimeParent DisplayString,
         ejbComponentRuntimeModuleId OCTET STRING,
         ejbComponentRuntimeDeploymentState INTEGER
      }
      
   
   ejbComponentRuntimeIndex OBJECT-TYPE
      SYNTAX      DisplayString (SIZE (1..16))
      MAX-ACCESS  read-only
      STATUS      current
      DESCRIPTION "Unique value directed from ObjectName which is used as table index"
      ::= { ejbComponentRuntimeEntry 1  }
   
   
   ejbComponentRuntimeObjectName OBJECT-TYPE
      SYNTAX      DisplayString (SIZE (1..256))
      MAX-ACCESS  read-only
      STATUS      current
      DESCRIPTION "JMX-standard MBean name"
      ::= { ejbComponentRuntimeEntry 5  }
   
   
   ejbComponentRuntimeType OBJECT-TYPE
      SYNTAX      DisplayString (SIZE (1..64))
      MAX-ACCESS  read-only
      STATUS      current
      DESCRIPTION "Returns the type of the MBean. "
      ::= { ejbComponentRuntimeEntry 10  }
   
   
   ejbComponentRuntimeName OBJECT-TYPE
      SYNTAX      DisplayString (SIZE (1..64))
      MAX-ACCESS  read-only
      STATUS      current
      DESCRIPTION "The name of this configuration. WebLogic Server uses an MBean to implement and persist the configuration. "
      ::= { ejbComponentRuntimeEntry 15  }
   
   
   ejbComponentRuntimeParent OBJECT-TYPE
      SYNTAX      DisplayString (SIZE (1..256))
      MAX-ACCESS  read-only
      STATUS      current
      DESCRIPTION "BEA-proprietary Parent object's identification, with syntax
      <type>:<name>"
      ::= { ejbComponentRuntimeEntry 20  }
   
   
   ejbComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { ejbComponentRuntimeEntry 21  }
   
   
   ejbComponentRuntimeDeploymentState OBJECT-TYPE
      SYNTAX      INTEGER
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { ejbComponentRuntimeEntry 22  }
   
   
   ejbLockingRuntimeTable OBJECT-TYPE
      SYNTAX      SEQUENCE OF EjbLockingRuntimeEntry
      MAX-ACCESS  not-accessible
      STATUS      current
      DESCRIPTION "This interface contains accessor methods for all lock manager runtime information collected for an EJB. "
      ::= { wls 151  }
      
   
   ejbLockingRuntimeEntry OBJECT-TYPE
      SYNTAX      EjbLockingRuntimeEntry
      MAX-ACCESS  not-accessible
      STATUS      current
      DESCRIPTION "Entry of ejbTimerRuntimeTable"
      INDEX { ejbLockingRuntimeIndex}
      ::= { ejbLockingRuntimeTable 1 }
      
   EjbLockingRuntimeEntry ::=
      SEQUENCE
      {
         ejbLockingRuntimeIndex DisplayString,
         ejbLockingRuntimeObjectName DisplayString,
         ejbLockingRuntimeType DisplayString,
         ejbLockingRuntimeName DisplayString,
         ejbLockingRuntimeParent DisplayString,
         ejbLockingRuntimeLockEntriesCurrentCount DisplayString,
         ejbLockingRuntimeLockManagerAccessCount Counter64,
         ejbLockingRuntimeWaiterTotalCount Counter64,
         ejbLockingRuntimeWaiterCurrentCount INTEGER,
         ejbLockingRuntimeTimeoutTotalCount Counter64
      }
      
   
   ejbLockingRuntimeIndex OBJECT-TYPE
      SYNTAX      DisplayString (SIZE (1..16))
      MAX-ACCESS  read-only
      STATUS      current
      DESCRIPTION "Unique value directed from ObjectName which is used as table index"
      ::= { ejbLockingRuntimeEntry 1  }
   
   
   ejbLockingRuntimeObjectName OBJECT-TYPE
      SYNTAX      DisplayString (SIZE (1..256))
      MAX-ACCESS  read-only
      STATUS      current
      DESCRIPTION "JMX-standard MBean name"
      ::= { ejbLockingRuntimeEntry 5  }
   
   
   ejbLockingRuntimeType OBJECT-TYPE
      SYNTAX      DisplayString (SIZE (1..64))
      MAX-ACCESS  read-only
      STATUS      current
      DESCRIPTION "Returns the type of the MBean. "
      ::= { ejbLockingRuntimeEntry 10  }
   
   
   ejbLockingRuntimeName OBJECT-TYPE
      SYNTAX      DisplayString (SIZE (1..64))
      MAX-ACCESS  read-only
      STATUS      current
      DESCRIPTION "The name of this configuration. WebLogic Server uses an MBean to implement and persist the configuration. "
      ::= { ejbLockingRuntimeEntry 15  }
   
   
   ejbLockingRuntimeParent OBJECT-TYPE
      SYNTAX      DisplayString (SIZE (1..256))
      MAX-ACCESS  read-only
      STATUS      current
      DESCRIPTION "BEA-proprietary Parent object's identification, with syntax
      <type>:<name>"
      ::= { ejbLockingRuntimeEntry 20  }
   
   
   ejbLockingRuntimeLockEntriesCurrentCount OBJECT-TYPE
      SYNTAX      DisplayString (SIZE (1..16))
      MAX-ACCESS  read-only
      STATUS      current
      DESCRIPTION "Provides a count of the number of beans currently locked. "
      ::= { ejbLockingRuntimeEntry 25  }
   
   
   ejbLockingRuntimeLockManagerAccessCount OBJECT-TYPE
      SYNTAX      Counter64
      MAX-ACCESS  read-only
      STATUS      current
      DESCRIPTION "Provides the total number of attempts to obtain a lock on a bean. This includes attempts to obtain a lock on a bean that is already locked on behalf of the client. "
      ::= { ejbLockingRuntimeEntry 30  }
   
   
   ejbLockingRuntimeWaiterTotalCount OBJECT-TYPE
      SYNTAX      Counter64
      MAX-ACCESS  read-only
      STATUS      current
      DESCRIPTION "Provides the total number of Threads that have waited for a lock on a bean.  Returns the total number of Threads that have waited for a lock on a bean. "
      ::= { ejbLockingRuntimeEntry 35  }
   
   
   ejbLockingRuntimeWaiterCurrentCount OBJECT-TYPE
      SYNTAX      INTEGER
      MAX-ACCESS  read-only
      STATUS      current
      DESCRIPTION "Provides the current number of Threads that have waited for a lock on a bean. "
      ::= { ejbLockingRuntimeEntry 40  }
   
   
   ejbLockingRuntimeTimeoutTotalCount OBJECT-TYPE
      SYNTAX      Counter64
      MAX-ACCESS  read-only
      STATUS      current
      DESCRIPTION "Provides the current number of Threads that have timed out waiting for a lock on a bean. "
      ::= { ejbLockingRuntimeEntry 45  }
   
   
   ejbPoolRuntimeTable OBJECT-TYPE
      SYNTAX      SEQUENCE OF EjbPoolRuntimeEntry
      MAX-ACCESS  not-accessible
      STATUS      current
      DESCRIPTION "This interface contains accessor methods for all free pool runtime information collected for an EJB. "
      ::= { wls 161  }
      
   
   ejbPoolRuntimeEntry OBJECT-TYPE
      SYNTAX      EjbPoolRuntimeEntry
      MAX-ACCESS  not-accessible
      STATUS      current
      DESCRIPTION "Entry of ejbPoolRuntimeTable"
      INDEX { ejbPoolRuntimeIndex}
      ::= { ejbPoolRuntimeTable 1 }
      
   EjbPoolRuntimeEntry ::=
      SEQUENCE
      {
         ejbPoolRuntimeIndex  DisplayString,
         ejbPoolRuntimeObjectName DisplayString,
         ejbPoolRuntimeType   DisplayString,
         ejbPoolRuntimeName   DisplayString,
         ejbPoolRuntimeParent DisplayString,
         ejbPoolRuntimeBeansInUseCount INTEGER,
         ejbPoolRuntimeIdleBeansCount INTEGER,
         ejbPoolRuntimeTimeoutTotalCount Counter64,
         ejbPoolRuntimeWaiterTotalCount Counter64,
         ejbPoolRuntimeAccessTotalCount Counter64,
         ejbPoolRuntimeBeansInUseCurrentCount INTEGER,
         ejbPoolRuntimeDestroyedTotalCount Counter64,
         ejbPoolRuntimeMissTotalCount Counter64,
         ejbPoolRuntimeWaiterCurrentCount INTEGER,
         ejbPoolRuntimePooledBeansCurrentCount INTEGER
      }
      
   
   ejbPoolRuntimeIndex OBJECT-TYPE
      SYNTAX      DisplayString (SIZE (1..16))
      MAX-ACCESS  read-only
      STATUS      current
      DESCRIPTION "Unique value directed from ObjectName which is used as table index"
      ::= { ejbPoolRuntimeEntry 1  }
   
   
   ejbPoolRuntimeObjectName OBJECT-TYPE
      SYNTAX      DisplayString (SIZE (1..256))
      MAX-ACCESS  read-only
      STATUS      current
      DESCRIPTION "JMX-standard MBean name"
      ::= { ejbPoolRuntimeEntry 5  }
   
   
   ejbPoolRuntimeType OBJECT-TYPE
      SYNTAX      DisplayString (SIZE (1..64))
      MAX-ACCESS  read-only
      STATUS      current
      DESCRIPTION "Returns the type of the MBean. "
      ::= { ejbPoolRuntimeEntry 10  }
   
   
   ejbPoolRuntimeName OBJECT-TYPE
      SYNTAX      DisplayString (SIZE (1..64))
      MAX-ACCESS  read-only
      STATUS      current
      DESCRIPTION "The name of this configuration. WebLogic Server uses an MBean to implement and persist the configuration. "
      ::= { ejbPoolRuntimeEntry 15  }
   
   
   ejbPoolRuntimeParent OBJECT-TYPE
      SYNTAX      DisplayString (SIZE (1..256))
      MAX-ACCESS  read-only
      STATUS      current
      DESCRIPTION "BEA-proprietary Parent object's identification, with syntax
      <type>:<name>"
      ::= { ejbPoolRuntimeEntry 20  }
   
   
   ejbPoolRuntimeBeansInUseCount OBJECT-TYPE
      SYNTAX      INTEGER
      MAX-ACCESS  read-only
      STATUS      current
      DESCRIPTION "Provides a count of the total number of bean instances currently in use from the free pool. "
      ::= { ejbPoolRuntimeEntry 25  }
   
   
   ejbPoolRuntimeIdleBeansCount OBJECT-TYPE
      SYNTAX      INTEGER
      MAX-ACCESS  read-only
      STATUS      current
      DESCRIPTION "Provides a count of the total number of available bean instances in the free pool.  Returns the total number of available bean instances in the free pool. "
      ::= { ejbPoolRuntimeEntry 30  }
   
   
   ejbPoolRuntimeTimeoutTotalCount OBJECT-TYPE
      SYNTAX      Counter64
      MAX-ACCESS  read-only
      STATUS      current
      DESCRIPTION "Provides a count of the total number of Threads that have timed out waiting for an available bean instance from the free pool. "
      ::= { ejbPoolRuntimeEntry 35  }
   
   
   ejbPoolRuntimeWaiterTotalCount OBJECT-TYPE
      SYNTAX      Counter64
      MAX-ACCESS  read-only
      STATUS      current
      DESCRIPTION "Provides a count of the total number of Threads currently waiting for an available bean instance from the free pool. "
      ::= { ejbPoolRuntimeEntry 40  }
   
   
   ejbPoolRuntimeAccessTotalCount OBJECT-TYPE
      SYNTAX      Counter64
      MAX-ACCESS  read-only
      STATUS      current
      DESCRIPTION "Provides a count of the total number of times an attempt was made to get an instance from the free pool. "
      ::= { ejbPoolRuntimeEntry 41  }
   
   
   ejbPoolRuntimeBeansInUseCurrentCount OBJECT-TYPE
      SYNTAX      INTEGER
      MAX-ACCESS  read-only
      STATUS      current
      DESCRIPTION "Provides a count of the number of bean instances currently being used from the free pool. "
      ::= { ejbPoolRuntimeEntry 42  }
   
   
   ejbPoolRuntimeDestroyedTotalCount OBJECT-TYPE
      SYNTAX      Counter64
      MAX-ACCESS  read-only
      STATUS      current
      DESCRIPTION "Provides a count of the total number of times a bean instance from this pool was destroyed due to a non-application Exception being thrown from it. "
      ::= { ejbPoolRuntimeEntry 43  }
   
   
   ejbPoolRuntimeMissTotalCount OBJECT-TYPE
      SYNTAX      Counter64
      MAX-ACCESS  read-only
      STATUS      current
      DESCRIPTION "Provides a count of the total number of times a failed attempt was made to get an instance from the free pool. An Attempt to get a bean from the pool will fail if there are no available instances in the pool. "
      ::= { ejbPoolRuntimeEntry 44  }
   
   
   ejbPoolRuntimeWaiterCurrentCount OBJECT-TYPE
      SYNTAX      INTEGER
      MAX-ACCESS  read-only
      STATUS      current
      DESCRIPTION "Provides a count of the number of Threads currently waiting for an available bean instance from the free pool. "
      ::= { ejbPoolRuntimeEntry 45  }
   
   
   ejbPoolRuntimePooledBeansCurrentCount OBJECT-TYPE
      SYNTAX      INTEGER
      MAX-ACCESS  read-only
      STATUS      current
      DESCRIPTION "Provides a count of the current number of available bean instances in the free pool. "
      ::= { ejbPoolRuntimeEntry 46  }
   
   
   ejbTimerRuntimeTable OBJECT-TYPE
      SYNTAX      SEQUENCE OF EjbTimerRuntimeEntry
      MAX-ACCESS  not-accessible
      STATUS      current
      DESCRIPTION "This interface contains accessor methods for all EJB Timer runtime information collected for an EJB. "
      ::= { wls 162  }
      
   
   ejbTimerRuntimeEntry OBJECT-TYPE
      SYNTAX      EjbTimerRuntimeEntry
      MAX-ACCESS  not-accessible
      STATUS      current
      DESCRIPTION "Entry of ejbTimerRuntimeTable"
      INDEX { ejbTimerRuntimeIndex}
      ::= { ejbTimerRuntimeTable 1 }
      
   EjbTimerRuntimeEntry ::=
      SEQUENCE
      {
         ejbTimerRuntimeIndex DisplayString,
         ejbTimerRuntimeObjectName DisplayString,
         ejbTimerRuntimeType  DisplayString,
         ejbTimerRuntimeName  DisplayString,
         ejbTimerRuntimeParent DisplayString,
         ejbTimerRuntimeDisabledTimerCount INTEGER,
         ejbTimerRuntimeCancelledTimerCount Counter64,
         ejbTimerRuntimeTimeoutCount Counter64,
         ejbTimerRuntimeActiveTimerCount INTEGER
      }
      
   
   ejbTimerRuntimeIndex OBJECT-TYPE
      SYNTAX      DisplayString (SIZE (1..16))
      MAX-ACCESS  read-only
      STATUS      current
      DESCRIPTION "Unique value directed from ObjectName which is used as table index"
      ::= { ejbTimerRuntimeEntry 1  }
   
   
   ejbTimerRuntimeObjectName OBJECT-TYPE
      SYNTAX      DisplayString (SIZE (1..256))
      MAX-ACCESS  read-only
      STATUS      current
      DESCRIPTION "JMX-standard MBean name"
      ::= { ejbTimerRuntimeEntry 5  }
   
   
   ejbTimerRuntimeType OBJECT-TYPE
      SYNTAX      DisplayString (SIZE (1..64))
      MAX-ACCESS  read-only
      STATUS      current
      DESCRIPTION "Returns the type of the MBean. "
      ::= { ejbTimerRuntimeEntry 10  }
   
   
   ejbTimerRuntimeName OBJECT-TYPE
      SYNTAX      DisplayString (SIZE (1..64))
      MAX-ACCESS  read-only
      STATUS      current
      DESCRIPTION "The name of this configuration. WebLogic Server uses an MBean to implement and persist the configuration. "
      ::= { ejbTimerRuntimeEntry 15  }
   
   
   ejbTimerRuntimeParent OBJECT-TYPE
      SYNTAX      DisplayString (SIZE (1..256))
      MAX-ACCESS  read-only
      STATUS      current
      DESCRIPTION "BEA-proprietary Parent object's identification, with syntax
      <type>:<name>"
      ::= { ejbTimerRuntimeEntry 20  }
   
   
   ejbTimerRuntimeDisabledTimerCount OBJECT-TYPE
      SYNTAX      INTEGER
      MAX-ACCESS  read-only
      STATUS      current
      DESCRIPTION "Provides the current number of timers temporarily disabled for this EJB "
      ::= { ejbTimerRuntimeEntry 25  }
   
   
   ejbTimerRuntimeCancelledTimerCount OBJECT-TYPE
      SYNTAX      Counter64
      MAX-ACCESS  read-only
      STATUS      current
      DESCRIPTION "Provides the total number of timers that have been explicitly cancelled for this EJB. "
      ::= { ejbTimerRuntimeEntry 30  }
   
   
   ejbTimerRuntimeTimeoutCount OBJECT-TYPE
      SYNTAX      Counter64
      MAX-ACCESS  read-only
      STATUS      current
      DESCRIPTION "Provides the total number of successful timeout notifications that have been made for this EJB. "
      ::= { ejbTimerRuntimeEntry 35  }
   
   
   ejbTimerRuntimeActiveTimerCount OBJECT-TYPE
      SYNTAX      INTEGER
      MAX-ACCESS  read-only
      STATUS      current
      DESCRIPTION "Provides the current number of active timers for this EJB "
      ::= { ejbTimerRuntimeEntry 40  }
   
   
   ejbTransactionRuntimeTable OBJECT-TYPE
      SYNTAX      SEQUENCE OF EjbTransactionRuntimeEntry
      MAX-ACCESS  not-accessible
      STATUS      current
      DESCRIPTION "This interface contains accessor methods for all transaction runtime information collected for an EJB. "
      ::= { wls 171  }
      
   
   ejbTransactionRuntimeEntry OBJECT-TYPE
      SYNTAX      EjbTransactionRuntimeEntry
      MAX-ACCESS  not-accessible
      STATUS      current
      DESCRIPTION "Entry of ejbTransactionRuntimeTable"
      INDEX { ejbTransactionRuntimeIndex}
      ::= { ejbTransactionRuntimeTable 1 }
      
   EjbTransactionRuntimeEntry ::=
      SEQUENCE
      {
         ejbTransactionRuntimeIndex DisplayString,
         ejbTransactionRuntimeObjectName DisplayString,
         ejbTransactionRuntimeType DisplayString,
         ejbTransactionRuntimeName DisplayString,
         ejbTransactionRuntimeParent DisplayString,
         ejbTransactionRuntimeTransactionsCommittedTotalCount Counter64,
         ejbTransactionRuntimeTransactionsRolledBackTotalCount Counter64,
         ejbTransactionRuntimeTransactionsTimedOutTotalCount Counter64
      }
      
   
   ejbTransactionRuntimeIndex OBJECT-TYPE
      SYNTAX      DisplayString (SIZE (1..16))
      MAX-ACCESS  read-only
      STATUS      current
      DESCRIPTION "Unique value directed from ObjectName which is used as table index"
      ::= { ejbTransactionRuntimeEntry 1  }
   
   
   ejbTransactionRuntimeObjectName OBJECT-TYPE
      SYNTAX      DisplayString (SIZE (1..256))
      MAX-ACCESS  read-only
      STATUS      current
      DESCRIPTION "JMX-standard MBean name"
      ::= { ejbTransactionRuntimeEntry 5  }
   
   
   ejbTransactionRuntimeType OBJECT-TYPE
      SYNTAX      DisplayString (SIZE (1..64))
      MAX-ACCESS  read-only
      STATUS      current
      DESCRIPTION "Returns the type of the MBean. "
      ::= { ejbTransactionRuntimeEntry 10  }
   
   
   ejbTransactionRuntimeName OBJECT-TYPE
      SYNTAX      DisplayString (SIZE (1..64))
      MAX-ACCESS  read-only
      STATUS      current
      DESCRIPTION "The name of this configuration. WebLogic Server uses an MBean to implement and persist the configuration. "
      ::= { ejbTransactionRuntimeEntry 15  }
   
   
   ejbTransactionRuntimeParent OBJECT-TYPE
      SYNTAX      DisplayString (SIZE (1..256))
      MAX-ACCESS  read-only
      STATUS      current
      DESCRIPTION "BEA-proprietary Parent object's identification, with syntax
      <type>:<name>"
      ::= { ejbTransactionRuntimeEntry 20  }
   
   
   ejbTransactionRuntimeTransactionsCommittedTotalCount OBJECT-TYPE
      SYNTAX      Counter64
      MAX-ACCESS  read-only
      STATUS      current
      DESCRIPTION "Provides a count of the total number of transactions that have been committed for this EJB. "
      ::= { ejbTransactionRuntimeEntry 25  }
   
   
   ejbTransactionRuntimeTransactionsRolledBackTotalCount OBJECT-TYPE
      SYNTAX      Counter64
      MAX-ACCESS  read-only
      STATUS      current
      DESCRIPTION "Provides a count of the total number of transactions that have been rolled back for this EJB. "
      ::= { ejbTransactionRuntimeEntry 30  }
   
   
   ejbTransactionRuntimeTransactionsTimedOutTotalCount OBJECT-TYPE
      SYNTAX      Counter64
      MAX-ACCESS  read-only
      STATUS      current
      DESCRIPTION "Provides a count of the total number of transactions that have timed out for this EJB. "
      ::= { ejbTransactionRuntimeEntry 35  }
   
   
   entityCacheCumulativeRuntimeTable OBJECT-TYPE
      SYNTAX      SEQUENCE OF EntityCacheCumulativeRuntimeEntry
      MAX-ACCESS  not-accessible
      STATUS      current
      DESCRIPTION "This class is used for monitoring an XML Cache. "
      ::= { wls 172  }
      
   
   entityCacheCumulativeRuntimeEntry OBJECT-TYPE
      SYNTAX      EntityCacheCumulativeRuntimeEntry
      MAX-ACCESS  not-accessible
      STATUS      current
      DESCRIPTION "Entry of entityCacheCumulativeRuntimeTable"
      INDEX { entityCacheCumulativeRuntimeIndex}
      ::= { entityCacheCumulativeRuntimeTable 1 }
      
   EntityCacheCumulativeRuntimeEntry ::=
      SEQUENCE
      {
         entityCacheCumulativeRuntimeIndex DisplayString,
         entityCacheCumulativeRuntimeObjectName DisplayString,
         entityCacheCumulativeRuntimeType DisplayString,
         entityCacheCumulativeRuntimeName DisplayString,
         entityCacheCumulativeRuntimeParent DisplayString,
         entityCacheCumulativeRuntimeAvgEntrySizeDiskPurged INTEGER,
         entityCacheCumulativeRuntimeAvgEntrySizeMemoryPurged INTEGER,
         entityCacheCumulativeRuntimeDiskPurgesPerHour INTEGER,
         entityCacheCumulativeRuntimeMostRecentDiskPurge INTEGER,
         entityCacheCumulativeRuntimeMostRecentMemoryPurge INTEGER,
         entityCacheCumulativeRuntimePercentRejected INTEGER,
         entityCacheCumulativeRuntimeTotalItemsDiskPurged Counter64,
         entityCacheCumulativeRuntimeTotalItemsMemoryPurged Counter64,
         entityCacheCumulativeRuntimeTotalNumberDiskPurges Counter64,
         entityCacheCumulativeRuntimeTotalNumberMemoryPurges Counter64,
         entityCacheCumulativeRuntimeTotalNumberOfRejections Counter64,
         entityCacheCumulativeRuntimeTotalNumberOfRenewals Counter64,
         entityCacheCumulativeRuntimeTotalSizeOfRejections Counter64,
         entityCacheCumulativeRuntimeTotalCurrentEntries Counter64,
         entityCacheCumulativeRuntimeAvgPerEntryDiskSize OCTET STRING,
         entityCacheCumulativeRuntimeTotalPersistentCurrentEntries Counter64,
         entityCacheCumulativeRuntimeMaxEntryTimeout OCTET STRING,
         entityCacheCumulativeRuntimeMaxEntryMemorySize Counter64,
         entityCacheCumulativeRuntimeTotalTransientCurrentEntries Counter64,
         entityCacheCumulativeRuntimeAvgPerEntryMemorySize OCTET STRING,
         entityCacheCumulativeRuntimeAvgPercentPersistent OCTET STRING,
         entityCacheCumulativeRuntimeMinEntryMemorySize Counter64,
         entityCacheCumulativeRuntimeAvgTimeout OCTET STRING,
         entityCacheCumulativeRuntimeMemoryPurgesPerHour OCTET STRING,
         entityCacheCumulativeRuntimeMinEntryTimeout OCTET STRING,
         entityCacheCumulativeRuntimeAvgPercentTransient OCTET STRING
      }
      
   
   entityCacheCumulativeRuntimeIndex OBJECT-TYPE
      SYNTAX      DisplayString (SIZE (1..16))
      MAX-ACCESS  read-only
      STATUS      current
      DESCRIPTION "Unique value directed from ObjectName which is used as table index"
      ::= { entityCacheCumulativeRuntimeEntry 1  }
   
   
   entityCacheCumulativeRuntimeObjectName OBJECT-TYPE
      SYNTAX      DisplayString (SIZE (1..256))
      MAX-ACCESS  read-only
      STATUS      current
      DESCRIPTION "JMX-standard MBean name"
      ::= { entityCacheCumulativeRuntimeEntry 5  }
   
   
   entityCacheCumulativeRuntimeType OBJECT-TYPE
      SYNTAX      DisplayString (SIZE (1..64))
      MAX-ACCESS  read-only
      STATUS      current
      DESCRIPTION "Returns the type of the MBean. "
      ::= { entityCacheCumulativeRuntimeEntry 10  }
   
   
   entityCacheCumulativeRuntimeName OBJECT-TYPE
      SYNTAX      DisplayString (SIZE (1..64))
      MAX-ACCESS  read-only
      STATUS      current
      DESCRIPTION "The name of this configuration. WebLogic Server uses an MBean to implement and persist the configuration. "
      ::= { entityCacheCumulativeRuntimeEntry 15  }
   
   
   entityCacheCumulativeRuntimeParent OBJECT-TYPE
      SYNTAX      DisplayString (SIZE (1..256))
      MAX-ACCESS  read-only
      STATUS      current
      DESCRIPTION "BEA-proprietary Parent object's identification, with syntax
      <type>:<name>"
      ::= { entityCacheCumulativeRuntimeEntry 20  }
   
   
   entityCacheCumulativeRuntimeAvgEntrySizeDiskPurged OBJECT-TYPE
      SYNTAX      INTEGER
      MAX-ACCESS  read-only
      STATUS      current
      DESCRIPTION "Provides the cumulative average size of entries that have been purged from the disk cache. "
      ::= { entityCacheCumulativeRuntimeEntry 25  }
   
   
   entityCacheCumulativeRuntimeAvgEntrySizeMemoryPurged OBJECT-TYPE
      SYNTAX      INTEGER
      MAX-ACCESS  read-only
      STATUS      current
      DESCRIPTION "Provides the average size of the all the entries that have been purged from the memory. "
      ::= { entityCacheCumulativeRuntimeEntry 26  }
   
   
   entityCacheCumulativeRuntimeDiskPurgesPerHour OBJECT-TYPE
      SYNTAX      INTEGER
      MAX-ACCESS  read-only
      STATUS      current
      DESCRIPTION "Provides cumulative average number of purges from the disk cache per hour. "
      ::= { entityCacheCumulativeRuntimeEntry 27  }
   
   
   entityCacheCumulativeRuntimeMostRecentDiskPurge OBJECT-TYPE
      SYNTAX      INTEGER
      MAX-ACCESS  read-only
      STATUS      current
      DESCRIPTION "Provides the date of the most recent purge from the disk cache. "
      ::= { entityCacheCumulativeRuntimeEntry 28  }
   
   
   entityCacheCumulativeRuntimeMostRecentMemoryPurge OBJECT-TYPE
      SYNTAX      INTEGER
      MAX-ACCESS  read-only
      STATUS      current
      DESCRIPTION "Provides the date of the most recent purge of the entity cache. "
      ::= { entityCacheCumulativeRuntimeEntry 29  }
   
   
   entityCacheCumulativeRuntimePercentRejected OBJECT-TYPE
      SYNTAX      INTEGER
      MAX-ACCESS  read-only
      STATUS      current
      DESCRIPTION "Provides the cumulative percent of the potential entries to the entity cache that have been rejected. "
      ::= { entityCacheCumulativeRuntimeEntry 30  }
   
   
   entityCacheCumulativeRuntimeTotalItemsDiskPurged OBJECT-TYPE
      SYNTAX      Counter64
      MAX-ACCESS  read-only
      STATUS      current
      DESCRIPTION "Provides the total number of items that have been purged from the disk cache. "
      ::= { entityCacheCumulativeRuntimeEntry 31  }
   
   
   entityCacheCumulativeRuntimeTotalItemsMemoryPurged OBJECT-TYPE
      SYNTAX      Counter64
      MAX-ACCESS  read-only
      STATUS      current
      DESCRIPTION "Provides the cumulative number of items that have been purged from the entity cache. "
      ::= { entityCacheCumulativeRuntimeEntry 32  }
   
   
   entityCacheCumulativeRuntimeTotalNumberDiskPurges OBJECT-TYPE
      SYNTAX      Counter64
      MAX-ACCESS  read-only
      STATUS      current
      DESCRIPTION "Provides a count of the total number of entries that have been purged from the disk cache. "
      ::= { entityCacheCumulativeRuntimeEntry 33  }
   
   
   entityCacheCumulativeRuntimeTotalNumberMemoryPurges OBJECT-TYPE
      SYNTAX      Counter64
      MAX-ACCESS  read-only
      STATUS      current
      DESCRIPTION "Provides the cumulative number of entries that have been purged from the entity cache. "
      ::= { entityCacheCumulativeRuntimeEntry 34  }
   
   
   entityCacheCumulativeRuntimeTotalNumberOfRejections OBJECT-TYPE
      SYNTAX      Counter64
      MAX-ACCESS  read-only
      STATUS      current
      DESCRIPTION "Provides the cumulative total number of rejections of entries from the entity cache for the current session. "
      ::= { entityCacheCumulativeRuntimeEntry 35  }
   
   
   entityCacheCumulativeRuntimeTotalNumberOfRenewals OBJECT-TYPE
      SYNTAX      Counter64
      MAX-ACCESS  read-only
      STATUS      current
      DESCRIPTION "Provides a count of the cumulative number of entries that have been refreshed in the entity cache. "
      ::= { entityCacheCumulativeRuntimeEntry 36  }
   
   
   entityCacheCumulativeRuntimeTotalSizeOfRejections OBJECT-TYPE
      SYNTAX      Counter64
      MAX-ACCESS  read-only
      STATUS      current
      DESCRIPTION "Provides the cumulative total size of the rejections from the entity cache. "
      ::= { entityCacheCumulativeRuntimeEntry 37  }
   
   
   entityCacheCumulativeRuntimeTotalCurrentEntries OBJECT-TYPE
      SYNTAX      Counter64
      MAX-ACCESS  read-only
      STATUS      current
      DESCRIPTION "Provides a count of the total current number of entries in the entity cache.  Returns the total current number of entries in the entity cache. "
      ::= { entityCacheCumulativeRuntimeEntry 38  }
   
   
   entityCacheCumulativeRuntimeAvgPerEntryDiskSize OBJECT-TYPE
      SYNTAX      OCTET STRING
      MAX-ACCESS  read-only
      STATUS      current
      DESCRIPTION "Provides the current average size of the entries in the entity disk cache.  Returns the current average size of the entries in the entity disk cache. "
      ::= { entityCacheCumulativeRuntimeEntry 39  }
   
   
   entityCacheCumulativeRuntimeTotalPersistentCurrentEntries OBJECT-TYPE
      SYNTAX      Counter64
      MAX-ACCESS  read-only
      STATUS      current
      DESCRIPTION "Provides a count of the total current number of entries in the cache that have been persisted to disk.  Returns the total current number of entries in the cache that have been persisted to disk. "
      ::= { entityCacheCumulativeRuntimeEntry 40  }
   
   
   entityCacheCumulativeRuntimeMaxEntryTimeout OBJECT-TYPE
      SYNTAX      OCTET STRING
      MAX-ACCESS  read-only
      STATUS      current
      DESCRIPTION "Provides the largest timeout value for any current entry in the entity cache.  Returns the largest timeout value for any current entry in the entity cache. "
      ::= { entityCacheCumulativeRuntimeEntry 41  }
   
   
   entityCacheCumulativeRuntimeMaxEntryMemorySize OBJECT-TYPE
      SYNTAX      Counter64
      MAX-ACCESS  read-only
      STATUS      current
      DESCRIPTION "Provides the current maximum size of the entries in the entity memory cache.  Returns the current maximum size of the entries in the entity memory cache. "
      ::= { entityCacheCumulativeRuntimeEntry 42  }
   
   
   entityCacheCumulativeRuntimeTotalTransientCurrentEntries OBJECT-TYPE
      SYNTAX      Counter64
      MAX-ACCESS  read-only
      STATUS      current
      DESCRIPTION "Provides a count of the total current number of transient (not yet persisted to disk) entries in the entity cache.  Returns the total current number of transient entries in the entity cache. "
      ::= { entityCacheCumulativeRuntimeEntry 43  }
   
   
   entityCacheCumulativeRuntimeAvgPerEntryMemorySize OBJECT-TYPE
      SYNTAX      OCTET STRING
      MAX-ACCESS  read-only
      STATUS      current
      DESCRIPTION "Provides the current average size of the entries in the entity memory cache.  Returns the current average size of the entries in the entity memory cache. "
      ::= { entityCacheCumulativeRuntimeEntry 44  }
   
   
   entityCacheCumulativeRuntimeAvgPercentPersistent OBJECT-TYPE
      SYNTAX      OCTET STRING
      MAX-ACCESS  read-only
      STATUS      current
      DESCRIPTION "Provides the current average percentage of entries in the entity cache that have been persisted to the disk cache.  Returns current average percentage of entries in the entity cache that have been persisted to the disk cache. "
      ::= { entityCacheCumulativeRuntimeEntry 45  }
   
   
   entityCacheCumulativeRuntimeMinEntryMemorySize OBJECT-TYPE
      SYNTAX      Counter64
      MAX-ACCESS  read-only
      STATUS      current
      DESCRIPTION "Provides the current minimum size of the entries in the entity memory cache.  Returns the current minimum size of the entries in the entity memory cache. "
      ::= { entityCacheCumulativeRuntimeEntry 46  }
   
   
   entityCacheCumulativeRuntimeAvgTimeout OBJECT-TYPE
      SYNTAX      OCTET STRING
      MAX-ACCESS  read-only
      STATUS      current
      DESCRIPTION "Provides the average amount of time that the entity cache has timed out when trying to retrieve an entity.  Returns the average amount of time that the entity cache has timed out when trying to retrieve an entity. "
      ::= { entityCacheCumulativeRuntimeEntry 47  }
   
   
   entityCacheCumulativeRuntimeMemoryPurgesPerHour OBJECT-TYPE
      SYNTAX      OCTET STRING
      MAX-ACCESS  read-only
      STATUS      current
      DESCRIPTION "Provides the cumulative average number of entries that have been purged from the entity cache. "
      ::= { entityCacheCumulativeRuntimeEntry 48  }
   
   
   entityCacheCumulativeRuntimeMinEntryTimeout OBJECT-TYPE
      SYNTAX      OCTET STRING
      MAX-ACCESS  read-only
      STATUS      current
      DESCRIPTION "Provides the smallest timeout value for any current entry in the entity cache.  Returns the smallest timeout value for any current entry in the entity cache. "
      ::= { entityCacheCumulativeRuntimeEntry 49  }
   
   
   entityCacheCumulativeRuntimeAvgPercentTransient OBJECT-TYPE
      SYNTAX      OCTET STRING
      MAX-ACCESS  read-only
      STATUS      current
      DESCRIPTION "Provides the current average percentage of entries in the entity cache that are transient, or have not been persisted.  Returns current average percentage of entries in the entity cache that are transient, or have not been persisted. "
      ::= { entityCacheCumulativeRuntimeEntry 50  }
   
   
   entityCacheCurrentStateRuntimeTable OBJECT-TYPE
      SYNTAX      SEQUENCE OF EntityCacheCurrentStateRuntimeEntry
      MAX-ACCESS  not-accessible
      STATUS      current
      DESCRIPTION "This class is used for monitoring the size and usage of an XML Cache. "
      ::= { wls 173  }
      
   
   entityCacheCurrentStateRuntimeEntry OBJECT-TYPE
      SYNTAX      EntityCacheCurrentStateRuntimeEntry
      MAX-ACCESS  not-accessible
      STATUS      current
      DESCRIPTION "Entry of entityCacheCurrentStateRuntimeTable"
      INDEX { entityCacheCurrentStateRuntimeIndex}
      ::= { entityCacheCurrentStateRuntimeTable 1 }
      
   EntityCacheCurrentStateRuntimeEntry ::=
      SEQUENCE
      {
         entityCacheCurrentStateRuntimeIndex DisplayString,
         entityCacheCurrentStateRuntimeObjectName DisplayString,
         entityCacheCurrentStateRuntimeType DisplayString,
         entityCacheCurrentStateRuntimeName DisplayString,
         entityCacheCurrentStateRuntimeParent DisplayString,
         entityCacheCurrentStateRuntimeDiskUsage Counter64,
         entityCacheCurrentStateRuntimeMemoryUsage Counter64,
         entityCacheCurrentStateRuntimeTotalCurrentEntries Counter64,
         entityCacheCurrentStateRuntimeMinEntryMemorySize Counter64,
         entityCacheCurrentStateRuntimeAvgPercentPersistent OCTET STRING,
         entityCacheCurrentStateRuntimeAvgTimeout OCTET STRING,
         entityCacheCurrentStateRuntimeAvgPerEntryDiskSize OCTET STRING,
         entityCacheCurrentStateRuntimeTotalPersistentCurrentEntries Counter64,
         entityCacheCurrentStateRuntimeMaxEntryTimeout OCTET STRING,
         entityCacheCurrentStateRuntimeMaxEntryMemorySize Counter64,
         entityCacheCurrentStateRuntimeTotalTransientCurrentEntries Counter64,
         entityCacheCurrentStateRuntimeAvgPerEntryMemorySize OCTET STRING,
         entityCacheCurrentStateRuntimeMinEntryTimeout OCTET STRING,
         entityCacheCurrentStateRuntimeAvgPercentTransient OCTET STRING
      }
      
   
   entityCacheCurrentStateRuntimeIndex OBJECT-TYPE
      SYNTAX      DisplayString (SIZE (1..16))
      MAX-ACCESS  read-only
      STATUS      current
      DESCRIPTION "Unique value directed from ObjectName which is used as table index"
      ::= { entityCacheCurrentStateRuntimeEntry 1  }
   
   
   entityCacheCurrentStateRuntimeObjectName OBJECT-TYPE
      SYNTAX      DisplayString (SIZE (1..256))
      MAX-ACCESS  read-only
      STATUS      current
      DESCRIPTION "JMX-standard MBean name"
      ::= { entityCacheCurrentStateRuntimeEntry 5  }
   
   
   entityCacheCurrentStateRuntimeType OBJECT-TYPE
      SYNTAX      DisplayString (SIZE (1..64))
      MAX-ACCESS  read-only
      STATUS      current
      DESCRIPTION "Returns the type of the MBean. "
      ::= { entityCacheCurrentStateRuntimeEntry 10  }
   
   
   entityCacheCurrentStateRuntimeName OBJECT-TYPE
      SYNTAX      DisplayString (SIZE (1..64))
      MAX-ACCESS  read-only
      STATUS      current
      DESCRIPTION "The name of this configuration. WebLogic Server uses an MBean to implement and persist the configuration. "
      ::= { entityCacheCurrentStateRuntimeEntry 15  }
   
   
   entityCacheCurrentStateRuntimeParent OBJECT-TYPE
      SYNTAX      DisplayString (SIZE (1..256))
      MAX-ACCESS  read-only
      STATUS      current
      DESCRIPTION "BEA-proprietary Parent object's identification, with syntax
      <type>:<name>"
      ::= { entityCacheCurrentStateRuntimeEntry 20  }
   
   
   entityCacheCurrentStateRuntimeDiskUsage OBJECT-TYPE
      SYNTAX      Counter64
      MAX-ACCESS  read-only
      STATUS      current
      DESCRIPTION "Provides the current size of the entity disk cache.  Returns the current size of the entity disk cache. "
      ::= { entityCacheCurrentStateRuntimeEntry 25  }
   
   
   entityCacheCurrentStateRuntimeMemoryUsage OBJECT-TYPE
      SYNTAX      Counter64
      MAX-ACCESS  read-only
      STATUS      current
      DESCRIPTION "Provides the current size of the entity memory cache.  Returns current size of the entity memory cache. "
      ::= { entityCacheCurrentStateRuntimeEntry 30  }
   
   
   entityCacheCurrentStateRuntimeTotalCurrentEntries OBJECT-TYPE
      SYNTAX      Counter64
      MAX-ACCESS  read-only
      STATUS      current
      DESCRIPTION "Provides a count of the total current number of entries in the entity cache.  Returns the total current number of entries in the entity cache. "
      ::= { entityCacheCurrentStateRuntimeEntry 31  }
   
   
   entityCacheCurrentStateRuntimeMinEntryMemorySize OBJECT-TYPE
      SYNTAX      Counter64
      MAX-ACCESS  read-only
      STATUS      current
      DESCRIPTION "Provides the current minimum size of the entries in the entity memory cache.  Returns the current minimum size of the entries in the entity memory cache. "
      ::= { entityCacheCurrentStateRuntimeEntry 32  }
   
   
   entityCacheCurrentStateRuntimeAvgPercentPersistent OBJECT-TYPE
      SYNTAX      OCTET STRING
      MAX-ACCESS  read-only
      STATUS      current
      DESCRIPTION "Provides the current average percentage of entries in the entity cache that have been persisted to the disk cache.  Returns current average percentage of entries in the entity cache that have been persisted to the disk cache. "
      ::= { entityCacheCurrentStateRuntimeEntry 33  }
   
   
   entityCacheCurrentStateRuntimeAvgTimeout OBJECT-TYPE
      SYNTAX      OCTET STRING
      MAX-ACCESS  read-only
      STATUS      current
      DESCRIPTION "Provides the average amount of time that the entity cache has timed out when trying to retrieve an entity.  Returns the average amount of time that the entity cache has timed out when trying to retrieve an entity. "
      ::= { entityCacheCurrentStateRuntimeEntry 34  }
   
   
   entityCacheCurrentStateRuntimeAvgPerEntryDiskSize OBJECT-TYPE
      SYNTAX      OCTET STRING
      MAX-ACCESS  read-only
      STATUS      current
      DESCRIPTION "Provides the current average size of the entries in the entity disk cache.  Returns the current average size of the entries in the entity disk cache. "
      ::= { entityCacheCurrentStateRuntimeEntry 35  }
   
   
   entityCacheCurrentStateRuntimeTotalPersistentCurrentEntries OBJECT-TYPE
      SYNTAX      Counter64
      MAX-ACCESS  read-only
      STATUS      current
      DESCRIPTION "Provides a count of the total current number of entries in the cache that have been persisted to disk.  Returns the total current number of entries in the cache that have been persisted to disk. "
      ::= { entityCacheCurrentStateRuntimeEntry 36  }
   
   
   entityCacheCurrentStateRuntimeMaxEntryTimeout OBJECT-TYPE
      SYNTAX      OCTET STRING
      MAX-ACCESS  read-only
      STATUS      current
      DESCRIPTION "Provides the largest timeout value for any current entry in the entity cache.  Returns the largest timeout value for any current entry in the entity cache. "
      ::= { entityCacheCurrentStateRuntimeEntry 37  }
   
   
   entityCacheCurrentStateRuntimeMaxEntryMemorySize OBJECT-TYPE
      SYNTAX      Counter64
      MAX-ACCESS  read-only
      STATUS      current
      DESCRIPTION "Provides the current maximum size of the entries in the entity memory cache.  Returns the current maximum size of the entries in the entity memory cache. "
      ::= { entityCacheCurrentStateRuntimeEntry 38  }
   
   
   entityCacheCurrentStateRuntimeTotalTransientCurrentEntries OBJECT-TYPE
      SYNTAX      Counter64
      MAX-ACCESS  read-only
      STATUS      current
      DESCRIPTION "Provides a count of the total current number of transient (not yet persisted to disk) entries in the entity cache.  Returns the total current number of transient entries in the entity cache. "
      ::= { entityCacheCurrentStateRuntimeEntry 39  }
   
   
   entityCacheCurrentStateRuntimeAvgPerEntryMemorySize OBJECT-TYPE
      SYNTAX      OCTET STRING
      MAX-ACCESS  read-only
      STATUS      current
      DESCRIPTION "Provides the current average size of the entries in the entity memory cache.  Returns the current average size of the entries in the entity memory cache. "
      ::= { entityCacheCurrentStateRuntimeEntry 40  }
   
   
   entityCacheCurrentStateRuntimeMinEntryTimeout OBJECT-TYPE
      SYNTAX      OCTET STRING
      MAX-ACCESS  read-only
      STATUS      current
      DESCRIPTION "Provides the smallest timeout value for any current entry in the entity cache.  Returns the smallest timeout value for any current entry in the entity cache. "
      ::= { entityCacheCurrentStateRuntimeEntry 41  }
   
   
   entityCacheCurrentStateRuntimeAvgPercentTransient OBJECT-TYPE
      SYNTAX      OCTET STRING
      MAX-ACCESS  read-only
      STATUS      current
      DESCRIPTION "Provides the current average percentage of entries in the entity cache that are transient, or have not been persisted.  Returns current average percentage of entries in the entity cache that are transient, or have not been persisted. "
      ::= { entityCacheCurrentStateRuntimeEntry 42  }
   
   
   entityCacheRuntimeTable OBJECT-TYPE
      SYNTAX      SEQUENCE OF EntityCacheRuntimeEntry
      MAX-ACCESS  not-accessible
      STATUS      current
      DESCRIPTION "This class is used for monitoring an XML Cache. "
      ::= { wls 174  }
      
   
   entityCacheRuntimeEntry OBJECT-TYPE
      SYNTAX      EntityCacheRuntimeEntry
      MAX-ACCESS  not-accessible
      STATUS      current
      DESCRIPTION "Entry of entityCacheRuntimeTable"
      INDEX { entityCacheRuntimeIndex}
      ::= { entityCacheRuntimeTable 1 }
      
   EntityCacheRuntimeEntry ::=
      SEQUENCE
      {
         entityCacheRuntimeIndex DisplayString,
         entityCacheRuntimeObjectName DisplayString,
         entityCacheRuntimeType DisplayString,
         entityCacheRuntimeName DisplayString,
         entityCacheRuntimeParent DisplayString,
         entityCacheRuntimeAvgPercentTransient INTEGER,
         entityCacheRuntimeAvgPerEntryDiskSize INTEGER,
         entityCacheRuntimeAvgPercentPersistent INTEGER,
         entityCacheRuntimeAvgPerEntryMemorySize INTEGER,
         entityCacheRuntimeAvgTimeout INTEGER,
         entityCacheRuntimeMaxEntryMemorySize Counter64,
         entityCacheRuntimeMaxEntryTimeout INTEGER,
         entityCacheRuntimeMinEntryMemorySize Counter64,
         entityCacheRuntimeMinEntryTimeout INTEGER,
         entityCacheRuntimeTotalCurrentEntries Counter64,
         entityCacheRuntimeTotalPersistentCurrentEntries Counter64,
         entityCacheRuntimeTotalTransientCurrentEntries Counter64
      }
      
   
   entityCacheRuntimeIndex OBJECT-TYPE
      SYNTAX      DisplayString (SIZE (1..16))
      MAX-ACCESS  read-only
      STATUS      current
      DESCRIPTION "Unique value directed from ObjectName which is used as table index"
      ::= { entityCacheRuntimeEntry 1  }
   
   
   entityCacheRuntimeObjectName OBJECT-TYPE
      SYNTAX      DisplayString (SIZE (1..256))
      MAX-ACCESS  read-only
      STATUS      current
      DESCRIPTION "JMX-standard MBean name"
      ::= { entityCacheRuntimeEntry 5  }
   
   
   entityCacheRuntimeType OBJECT-TYPE
      SYNTAX      DisplayString (SIZE (1..64))
      MAX-ACCESS  read-only
      STATUS      current
      DESCRIPTION "Returns the type of the MBean. "
      ::= { entityCacheRuntimeEntry 10  }
   
   
   entityCacheRuntimeName OBJECT-TYPE
      SYNTAX      DisplayString (SIZE (1..64))
      MAX-ACCESS  read-only
      STATUS      current
      DESCRIPTION "The name of this configuration. WebLogic Server uses an MBean to implement and persist the configuration. "
      ::= { entityCacheRuntimeEntry 15  }
   
   
   entityCacheRuntimeParent OBJECT-TYPE
      SYNTAX      DisplayString (SIZE (1..256))
      MAX-ACCESS  read-only
      STATUS      current
      DESCRIPTION "BEA-proprietary Parent object's identification, with syntax
      <type>:<name>"
      ::= { entityCacheRuntimeEntry 20  }
   
   
   entityCacheRuntimeAvgPercentTransient OBJECT-TYPE
      SYNTAX      INTEGER
      MAX-ACCESS  read-only
      STATUS      current
      DESCRIPTION "Provides the current average percentage of entries in the entity cache that are transient, or have not been persisted.  Returns current average percentage of entries in the entity cache that are transient, or have not been persisted. "
      ::= { entityCacheRuntimeEntry 25  }
   
   
   entityCacheRuntimeAvgPerEntryDiskSize OBJECT-TYPE
      SYNTAX      INTEGER
      MAX-ACCESS  read-only
      STATUS      current
      DESCRIPTION "Provides the current average size of the entries in the entity disk cache.  Returns the current average size of the entries in the entity disk cache. "
      ::= { entityCacheRuntimeEntry 30  }
   
   
   entityCacheRuntimeAvgPercentPersistent OBJECT-TYPE
      SYNTAX      INTEGER
      MAX-ACCESS  read-only
      STATUS      current
      DESCRIPTION "Provides the current average percentage of entries in the entity cache that have been persisted to the disk cache.  Returns current average percentage of entries in the entity cache that have been persisted to the disk cache. "
      ::= { entityCacheRuntimeEntry 31  }
   
   
   entityCacheRuntimeAvgPerEntryMemorySize OBJECT-TYPE
      SYNTAX      INTEGER
      MAX-ACCESS  read-only
      STATUS      current
      DESCRIPTION "Provides the current average size of the entries in the entity memory cache.  Returns the current average size of the entries in the entity memory cache. "
      ::= { entityCacheRuntimeEntry 32  }
   
   
   entityCacheRuntimeAvgTimeout OBJECT-TYPE
      SYNTAX      INTEGER
      MAX-ACCESS  read-only
      STATUS      current
      DESCRIPTION "Provides the average amount of time that the entity cache has timed out when trying to retrieve an entity.  Returns the average amount of time that the entity cache has timed out when trying to retrieve an entity. "
      ::= { entityCacheRuntimeEntry 33  }
   
   
   entityCacheRuntimeMaxEntryMemorySize OBJECT-TYPE
      SYNTAX      Counter64
      MAX-ACCESS  read-only
      STATUS      current
      DESCRIPTION "Provides the current maximum size of the entries in the entity memory cache.  Returns the current maximum size of the entries in the entity memory cache. "
      ::= { entityCacheRuntimeEntry 34  }
   
   
   entityCacheRuntimeMaxEntryTimeout OBJECT-TYPE
      SYNTAX      INTEGER
      MAX-ACCESS  read-only
      STATUS      current
      DESCRIPTION "Provides the largest timeout value for any current entry in the entity cache.  Returns the largest timeout value for any current entry in the entity cache. "
      ::= { entityCacheRuntimeEntry 35  }
   
   
   entityCacheRuntimeMinEntryMemorySize OBJECT-TYPE
      SYNTAX      Counter64
      MAX-ACCESS  read-only
      STATUS      current
      DESCRIPTION "Provides the current minimum size of the entries in the entity memory cache.  Returns the current minimum size of the entries in the entity memory cache. "
      ::= { entityCacheRuntimeEntry 36  }
   
   
   entityCacheRuntimeMinEntryTimeout OBJECT-TYPE
      SYNTAX      INTEGER
      MAX-ACCESS  read-only
      STATUS      current
      DESCRIPTION "Provides the smallest timeout value for any current entry in the entity cache.  Returns the smallest timeout value for any current entry in the entity cache. "
      ::= { entityCacheRuntimeEntry 37  }
   
   
   entityCacheRuntimeTotalCurrentEntries OBJECT-TYPE
      SYNTAX      Counter64
      MAX-ACCESS  read-only
      STATUS      current
      DESCRIPTION "Provides a count of the total current number of entries in the entity cache.  Returns the total current number of entries in the entity cache. "
      ::= { entityCacheRuntimeEntry 38  }
   
   
   entityCacheRuntimeTotalPersistentCurrentEntries OBJECT-TYPE
      SYNTAX      Counter64
      MAX-ACCESS  read-only
      STATUS      current
      DESCRIPTION "Provides a count of the total current number of entries in the cache that have been persisted to disk.  Returns the total current number of entries in the cache that have been persisted to disk. "
      ::= { entityCacheRuntimeEntry 39  }
   
   
   entityCacheRuntimeTotalTransientCurrentEntries OBJECT-TYPE
      SYNTAX      Counter64
      MAX-ACCESS  read-only
      STATUS      current
      DESCRIPTION "Provides a count of the total current number of transient (not yet persisted to disk) entries in the entity cache.  Returns the total current number of transient entries in the entity cache. "
      ::= { entityCacheRuntimeEntry 40  }
   
   
   executeQueueRuntimeTable OBJECT-TYPE
      SYNTAX      SEQUENCE OF ExecuteQueueRuntimeEntry
      MAX-ACCESS  not-accessible
      STATUS      current
      DESCRIPTION "This bean is used to monitor an execute queue and its associated thread pool. "
      ::= { wls 180  }
      
   
   executeQueueRuntimeEntry OBJECT-TYPE
      SYNTAX      ExecuteQueueRuntimeEntry
      MAX-ACCESS  not-accessible
      STATUS      current
      DESCRIPTION "Entry of executeQueueRuntimeTable"
      INDEX { executeQueueRuntimeIndex}
      ::= { executeQueueRuntimeTable 1 }
      
   ExecuteQueueRuntimeEntry ::=
      SEQUENCE
      {
         executeQueueRuntimeIndex DisplayString,
         executeQueueRuntimeObjectName DisplayString,
         executeQueueRuntimeType DisplayString,
         executeQueueRuntimeName DisplayString,
         executeQueueRuntimeParent DisplayString,
         executeQueueRuntimeExecuteThreadCurrentIdleCount INTEGER,
         executeQueueRuntimePendingRequestOldestTime Counter64,
         executeQueueRuntimePendingRequestCurrentCount INTEGER,
         executeQueueRuntimeServicedRequestTotalCount INTEGER,
         executeQueueRuntimeExecuteThreadTotalCount INTEGER
      }
      
   
   executeQueueRuntimeIndex OBJECT-TYPE
      SYNTAX      DisplayString (SIZE (1..16))
      MAX-ACCESS  read-only
      STATUS      current
      DESCRIPTION "Unique value directed from ObjectName which is used as table index"
      ::= { executeQueueRuntimeEntry 1  }
   
   
   executeQueueRuntimeObjectName OBJECT-TYPE
      SYNTAX      DisplayString (SIZE (1..256))
      MAX-ACCESS  read-only
      STATUS      current
      DESCRIPTION "JMX-standard MBean name"
      ::= { executeQueueRuntimeEntry 5  }
   
   
   executeQueueRuntimeType OBJECT-TYPE
      SYNTAX      DisplayString (SIZE (1..64))
      MAX-ACCESS  read-only
      STATUS      current
      DESCRIPTION "Returns the type of the MBean. "
      ::= { executeQueueRuntimeEntry 10  }
   
   
   executeQueueRuntimeName OBJECT-TYPE
      SYNTAX      DisplayString (SIZE (1..64))
      MAX-ACCESS  read-only
      STATUS      current
      DESCRIPTION "The name of this configuration. WebLogic Server uses an MBean to implement and persist the configuration. "
      ::= { executeQueueRuntimeEntry 15  }
   
   
   executeQueueRuntimeParent OBJECT-TYPE
      SYNTAX      DisplayString (SIZE (1..256))
      MAX-ACCESS  read-only
      STATUS      current
      DESCRIPTION "BEA-proprietary Parent object's identification, with syntax
      <type>:<name>"
      ::= { executeQueueRuntimeEntry 20  }
   
   
   executeQueueRuntimeExecuteThreadCurrentIdleCount OBJECT-TYPE
      SYNTAX      INTEGER
      MAX-ACCESS  read-only
      STATUS      current
      DESCRIPTION "The number of idle threads assigned to the queue. "
      ::= { executeQueueRuntimeEntry 25  }
   
   
   executeQueueRuntimePendingRequestOldestTime OBJECT-TYPE
      SYNTAX      Counter64
      MAX-ACCESS  read-only
      STATUS      current
      DESCRIPTION "The time since the longest waiting request was placed in the queue. "
      ::= { executeQueueRuntimeEntry 30  }
   
   
   executeQueueRuntimePendingRequestCurrentCount OBJECT-TYPE
      SYNTAX      INTEGER
      MAX-ACCESS  read-only
      STATUS      current
      DESCRIPTION "The number of waiting requests in the queue. "
      ::= { executeQueueRuntimeEntry 35  }
   
   
   executeQueueRuntimeServicedRequestTotalCount OBJECT-TYPE
      SYNTAX      INTEGER
      MAX-ACCESS  read-only
      STATUS      current
      DESCRIPTION "The number of requests that have been processed by the queue. "
      ::= { executeQueueRuntimeEntry 40  }
   
   
   executeQueueRuntimeExecuteThreadTotalCount OBJECT-TYPE
      SYNTAX      INTEGER
      MAX-ACCESS  read-only
      STATUS      current
      DESCRIPTION "The total number of execute threads assigned to the queue. "
      ::= { executeQueueRuntimeEntry 46  }
   
   
   interceptionComponentRuntimeTable OBJECT-TYPE
      SYNTAX      SEQUENCE OF InterceptionComponentRuntimeEntry
      MAX-ACCESS  not-accessible
      STATUS      current
      DESCRIPTION "Interception: This is the top level interface for all runtime information collected for an Interception module. "
      ::= { wls 181  }
      
   
   interceptionComponentRuntimeEntry OBJECT-TYPE
      SYNTAX      InterceptionComponentRuntimeEntry
      MAX-ACCESS  not-accessible
      STATUS      current
      DESCRIPTION "Entry of interceptionComponentRuntimeTable"
      INDEX { interceptionComponentRuntimeIndex}
      ::= { interceptionComponentRuntimeTable 1 }
      
   InterceptionComponentRuntimeEntry ::=
      SEQUENCE
      {
         interceptionComponentRuntimeIndex DisplayString,
         interceptionComponentRuntimeObjectName DisplayString,
         interceptionComponentRuntimeType DisplayString,
         interceptionComponentRuntimeName DisplayString,
         interceptionComponentRuntimeParent DisplayString,
         interceptionComponentRuntimeModuleId DisplayString,
         interceptionComponentRuntimeDeploymentState INTEGER
      }
      
   
   interceptionComponentRuntimeIndex OBJECT-TYPE
      SYNTAX      DisplayString (SIZE (1..16))
      MAX-ACCESS  read-only
      STATUS      current
      DESCRIPTION "Unique value directed from ObjectName which is used as table index"
      ::= { interceptionComponentRuntimeEntry 1  }
   
   
   interceptionComponentRuntimeObjectName OBJECT-TYPE
      SYNTAX      DisplayString (SIZE (1..256))
      MAX-ACCESS  read-only
      STATUS      current
      DESCRIPTION "JMX-standard MBean name"
      ::= { interceptionComponentRuntimeEntry 5  }
   
   
   interceptionComponentRuntimeType OBJECT-TYPE
      SYNTAX      DisplayString (SIZE (1..64))
      MAX-ACCESS  read-only
      STATUS      current
      DESCRIPTION "Returns the type of the MBean. "
      ::= { interceptionComponentRuntimeEntry 10  }
   
   
   interceptionComponentRuntimeName OBJECT-TYPE
      SYNTAX      DisplayString (SIZE (1..64))
      MAX-ACCESS  read-only
      STATUS      current
      DESCRIPTION "The name of this configuration. WebLogic Server uses an MBean to implement and persist the configuration. "
      ::= { interceptionComponentRuntimeEntry 15  }
   
   
   interceptionComponentRuntimeParent OBJECT-TYPE
      SYNTAX      DisplayString (SIZE (1..256))
      MAX-ACCESS  read-only
      STATUS      current
      DESCRIPTION "BEA-proprietary Parent object's identification, with syntax
      <type>:<name>"
      ::= { interceptionComponentRuntimeEntry 20  }
   
   
   interceptionComponentRuntimeModuleId OBJECT-TYPE
      SYNTAX      DisplayString (SIZE (1..256))
      MAX-ACCESS  read-only
      STATUS      current
      DESCRIPTION "Returns the identifier for this Component.  The identifier is unique within the application.  Typical modules will use the URI for their id.  Web Modules will return their context-root since the web-uri may not be unique within an EAR. "
      ::= { interceptionComponentRuntimeEntry 25  }
   
   
   interceptionComponentRuntimeDeploymentState OBJECT-TYPE
      SYNTAX      INTEGER
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { interceptionComponentRuntimeEntry 30  }
   
   
   jdbcConnectionPoolRuntimeTable OBJECT-TYPE
      SYNTAX      SEQUENCE OF JdbcConnectionPoolRuntimeEntry
      MAX-ACCESS  not-accessible
      STATUS      current
      DESCRIPTION "This table is used for monitoring a WebLogic JDBC component"
      ::= { wls 190  }
      
   
   jdbcConnectionPoolRuntimeEntry OBJECT-TYPE
      SYNTAX      JdbcConnectionPoolRuntimeEntry
      MAX-ACCESS  not-accessible
      STATUS      current
      DESCRIPTION "Entry of jdbcConnectionPoolRuntimeTable"
      INDEX { jdbcConnectionPoolRuntimeIndex}
      ::= { jdbcConnectionPoolRuntimeTable 1 }
      
   JdbcConnectionPoolRuntimeEntry ::=
      SEQUENCE
      {
         jdbcConnectionPoolRuntimeIndex DisplayString,
         jdbcConnectionPoolRuntimeObjectName DisplayString,
         jdbcConnectionPoolRuntimeType DisplayString,
         jdbcConnectionPoolRuntimeName DisplayString,
         jdbcConnectionPoolRuntimeParent DisplayString,
         jdbcConnectionPoolRuntimeActiveConnectionsCurrentCount INTEGER,
         jdbcConnectionPoolRuntimeWaitingForConnectionCurrentCount INTEGER,
         jdbcConnectionPoolRuntimeVersionJDBCDriver DisplayString,
         jdbcConnectionPoolRuntimeActiveConnectionsHighCount INTEGER,
         jdbcConnectionPoolRuntimeWaitingForConnectionHighCount INTEGER,
         jdbcConnectionPoolRuntimeWaitSecondsHighCount INTEGER,
         jdbcConnectionPoolRuntimeConnectionsTotalCount INTEGER,
         jdbcConnectionPoolRuntimeMaxCapacity INTEGER,
         jdbcConnectionPoolRuntimeActiveConnectionsAverageCount INTEGER,
         jdbcConnectionPoolRuntimeConnectionDelayTime INTEGER,
         jdbcConnectionPoolRuntimeConnectionLeakProfileCount Counter32,
         jdbcConnectionPoolRuntimeCurrCapacity INTEGER,
         jdbcConnectionPoolRuntimeFailuresToReconnectCount INTEGER,
         jdbcConnectionPoolRuntimeHighestNumAvailable INTEGER,
         jdbcConnectionPoolRuntimeHighestNumUnavailable INTEGER,
         jdbcConnectionPoolRuntimeLeakedConnectionCount INTEGER,
         jdbcConnectionPoolRuntimeNumAvailable INTEGER,
         jdbcConnectionPoolRuntimeNumUnavailable INTEGER,
         jdbcConnectionPoolRuntimeStatementProfileCount INTEGER,
         jdbcConnectionPoolRuntimeEnabled OCTET STRING,
         jdbcConnectionPoolRuntimePoolState OCTET STRING,
         jdbcConnectionPoolRuntimeModuleId OCTET STRING,
         jdbcConnectionPoolRuntimeState OCTET STRING,
         jdbcConnectionPoolRuntimeDeploymentState INTEGER
      }
      
   
   jdbcConnectionPoolRuntimeIndex OBJECT-TYPE
      SYNTAX      DisplayString (SIZE (1..16))
      MAX-ACCESS  read-only
      STATUS      current
      DESCRIPTION "Unique value directed from ObjectName which is used as table index"
      ::= { jdbcConnectionPoolRuntimeEntry 1  }
   
   
   jdbcConnectionPoolRuntimeObjectName OBJECT-TYPE
      SYNTAX      DisplayString (SIZE (1..256))
      MAX-ACCESS  read-only
      STATUS      current
      DESCRIPTION "JMX-standard MBean name"
      ::= { jdbcConnectionPoolRuntimeEntry 5  }
   
   
   jdbcConnectionPoolRuntimeType OBJECT-TYPE
      SYNTAX      DisplayString (SIZE (1..64))
      MAX-ACCESS  read-only
      STATUS      current
      DESCRIPTION "BEA-proprietary MBean type"
      ::= { jdbcConnectionPoolRuntimeEntry 10  }
   
   
   jdbcConnectionPoolRuntimeName OBJECT-TYPE
      SYNTAX      DisplayString (SIZE (1..64))
      MAX-ACCESS  read-only
      STATUS      current
      DESCRIPTION "BEA-proprietary MBean name"
      ::= { jdbcConnectionPoolRuntimeEntry 15  }
   
   
   jdbcConnectionPoolRuntimeParent OBJECT-TYPE
      SYNTAX      DisplayString (SIZE (1..256))
      MAX-ACCESS  read-only
      STATUS      current
      DESCRIPTION "BEA-proprietary Parent object's identification, with syntax
      <type>:<name>"
      ::= { jdbcConnectionPoolRuntimeEntry 20  }
   
   
   jdbcConnectionPoolRuntimeActiveConnectionsCurrentCount OBJECT-TYPE
      SYNTAX      INTEGER
      MAX-ACCESS  read-only
      STATUS      current
      DESCRIPTION "The current total active connections."
      ::= { jdbcConnectionPoolRuntimeEntry 25  }
   
   
   jdbcConnectionPoolRuntimeWaitingForConnectionCurrentCount OBJECT-TYPE
      SYNTAX      INTEGER
      MAX-ACCESS  read-only
      STATUS      current
      DESCRIPTION "The current total waiting for a connection."
      ::= { jdbcConnectionPoolRuntimeEntry 30  }
   
   
   jdbcConnectionPoolRuntimeVersionJDBCDriver OBJECT-TYPE
      SYNTAX      DisplayString (SIZE (1..32))
      MAX-ACCESS  read-only
      STATUS      current
      DESCRIPTION "The version of the JDBC driver, in the format of
      concatenating the Driver class name with 'major: XX, minor: YY'."
      ::= { jdbcConnectionPoolRuntimeEntry 35  }
   
   
   jdbcConnectionPoolRuntimeActiveConnectionsHighCount OBJECT-TYPE
      SYNTAX      INTEGER
      MAX-ACCESS  read-only
      STATUS      current
      DESCRIPTION "The high water mark of active connections in this JDBCConnectionPoolRuntimeMBean.
      The count starts at zero each time the JDBCConnectionPoolRuntimeMBean
      is instantiated."
      ::= { jdbcConnectionPoolRuntimeEntry 40  }
   
   
   jdbcConnectionPoolRuntimeWaitingForConnectionHighCount OBJECT-TYPE
      SYNTAX      INTEGER
      MAX-ACCESS  read-only
      STATUS      current
      DESCRIPTION "The high water mark of waiters for a connection in this JDBCConnectionPoolRuntimeMBean.
      The count starts at zero each time the JDBCConnectionPoolRuntimeMBean
      is instantiated."
      ::= { jdbcConnectionPoolRuntimeEntry 45  }
   
   
   jdbcConnectionPoolRuntimeWaitSecondsHighCount OBJECT-TYPE
      SYNTAX      INTEGER
      MAX-ACCESS  read-only
      STATUS      current
      DESCRIPTION "The number of seconds the longest waiter for a connection waited"
      ::= { jdbcConnectionPoolRuntimeEntry 50  }
   
   
   jdbcConnectionPoolRuntimeConnectionsTotalCount OBJECT-TYPE
      SYNTAX      INTEGER
      MAX-ACCESS  read-only
      STATUS      current
      DESCRIPTION "the total number of JDBC connections in this
      JDBCConnectionPoolRuntimeMBean since the pool is instantiated."
      ::= { jdbcConnectionPoolRuntimeEntry 55  }
   
   
   jdbcConnectionPoolRuntimeMaxCapacity OBJECT-TYPE
      SYNTAX      INTEGER
      MAX-ACCESS  read-only
      STATUS      current
      DESCRIPTION "The maximum capacity of this JDBC pool"
      ::= { jdbcConnectionPoolRuntimeEntry 60  }
   
   
   jdbcConnectionPoolRuntimeActiveConnectionsAverageCount OBJECT-TYPE
      SYNTAX      INTEGER
      MAX-ACCESS  read-only
      STATUS      current
      DESCRIPTION "The running average of active connections in this JDBCConnectionPoolRuntimeMBean"
      ::= { jdbcConnectionPoolRuntimeEntry 61  }
   
   
   jdbcConnectionPoolRuntimeConnectionDelayTime OBJECT-TYPE
      SYNTAX      INTEGER
      MAX-ACCESS  read-only
      STATUS      current
      DESCRIPTION "Averaged time necessary to get a connection from the database"
      ::= { jdbcConnectionPoolRuntimeEntry 62  }
   
   
   jdbcConnectionPoolRuntimeConnectionLeakProfileCount OBJECT-TYPE
      SYNTAX      Counter32
      MAX-ACCESS  read-only
      STATUS      current
      DESCRIPTION "Generated Object."
      ::= { jdbcConnectionPoolRuntimeEntry 63  }
   
   
   jdbcConnectionPoolRuntimeCurrCapacity OBJECT-TYPE
      SYNTAX      INTEGER
      MAX-ACCESS  read-only
      STATUS      current
      DESCRIPTION "Returns the current capacity of this connection pool."
      ::= { jdbcConnectionPoolRuntimeEntry 64  }
   
   
   jdbcConnectionPoolRuntimeFailuresToReconnectCount OBJECT-TYPE
      SYNTAX      INTEGER
      MAX-ACCESS  read-only
      STATUS      current
      DESCRIPTION "Number of cases when a connection pool attempted to refresh a connection to a database and failed"
      ::= { jdbcConnectionPoolRuntimeEntry 65  }
   
   
   jdbcConnectionPoolRuntimeHighestNumAvailable OBJECT-TYPE
      SYNTAX      INTEGER
      MAX-ACCESS  read-only
      STATUS      current
      DESCRIPTION "Returns the highest number of available connections in this pool"
      ::= { jdbcConnectionPoolRuntimeEntry 66  }
   
   
   jdbcConnectionPoolRuntimeHighestNumUnavailable OBJECT-TYPE
      SYNTAX      INTEGER
      MAX-ACCESS  read-only
      STATUS      current
      DESCRIPTION "Returns the highest number of unavailable connections in this pool"
      ::= { jdbcConnectionPoolRuntimeEntry 67  }
   
   
   jdbcConnectionPoolRuntimeLeakedConnectionCount OBJECT-TYPE
      SYNTAX      INTEGER
      MAX-ACCESS  read-only
      STATUS      current
      DESCRIPTION "Number of leaked connections."
      ::= { jdbcConnectionPoolRuntimeEntry 68  }
   
   
   jdbcConnectionPoolRuntimeNumAvailable OBJECT-TYPE
      SYNTAX      INTEGER
      MAX-ACCESS  read-only
      STATUS      current
      DESCRIPTION "Returns the number of available connections in this pool"
      ::= { jdbcConnectionPoolRuntimeEntry 69  }
   
   
   jdbcConnectionPoolRuntimeNumUnavailable OBJECT-TYPE
      SYNTAX      INTEGER
      MAX-ACCESS  read-only
      STATUS      current
      DESCRIPTION "Returns the number of unavailable connections in this pool"
      ::= { jdbcConnectionPoolRuntimeEntry 70  }
   
   
   jdbcConnectionPoolRuntimeStatementProfileCount OBJECT-TYPE
      SYNTAX      INTEGER
      MAX-ACCESS  read-only
      STATUS      current
      DESCRIPTION "Number of the SQL statement profiles in profile storage."
      ::= { jdbcConnectionPoolRuntimeEntry 71  }
   
   
   jdbcConnectionPoolRuntimeEnabled OBJECT-TYPE
      SYNTAX      OCTET STRING
      MAX-ACCESS  read-only
      STATUS      current
      DESCRIPTION ""
      ::= { jdbcConnectionPoolRuntimeEntry 72  }
   
   
   jdbcConnectionPoolRuntimePoolState OBJECT-TYPE
      SYNTAX      OCTET STRING
      MAX-ACCESS  read-only
      STATUS      current
      DESCRIPTION ""
      ::= { jdbcConnectionPoolRuntimeEntry 73  }
   
   
   jdbcConnectionPoolRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR."
      ::= { jdbcConnectionPoolRuntimeEntry 74  }
   
   
   jdbcConnectionPoolRuntimeState OBJECT-TYPE
      SYNTAX      OCTET STRING
      MAX-ACCESS  read-only
      STATUS      current
      DESCRIPTION "The current state of the connection pool.  Possible values are:   Running if the pool is enabled (deployed and not Suspended). This is the normal state of the connection pool.   Suspended if the pool disabled.   Shutdown if the pool is shutdown and all database connections have been closed.   Unknown if the pool state is unknown.   Unhealthy if all connections are unavailable (not because they are in use). This state occurs if the database server is unavailable when the connection pool is created (creation retry must be enabled) or if all connections have failed connection tests (on creation, on reserve, on release, or periodic testing)."
      ::= { jdbcConnectionPoolRuntimeEntry 75  }
   
   
   jdbcConnectionPoolRuntimeDeploymentState OBJECT-TYPE
      SYNTAX      INTEGER
      MAX-ACCESS  read-only
      STATUS      current
      DESCRIPTION "The current deployment state of the module.  A module can be in one and only one of the following states. State can be changed via deployment or administrator console.  - UNPREPARED. State indicating at this  module is neither  prepared or active.  - PREPARED. State indicating at this module of this application is prepared, but not active. The classes have been loaded and the module has been validated.  - ACTIVATED. State indicating at this module  is currently active.  - NEW. State indicating this module has just been created and is being initialized."
      ::= { jdbcConnectionPoolRuntimeEntry 76  }
   
   
   jdbcDataSourceRuntimeTable OBJECT-TYPE
      SYNTAX      SEQUENCE OF JdbcDataSourceRuntimeEntry
      MAX-ACCESS  not-accessible
      STATUS      current
      DESCRIPTION "This class is used for monitoring a WebLogic JDBC Data Source and its associated connection pool. "
      ::= { wls 191  }
      
   
   jdbcDataSourceRuntimeEntry OBJECT-TYPE
      SYNTAX      JdbcDataSourceRuntimeEntry
      MAX-ACCESS  not-accessible
      STATUS      current
      DESCRIPTION "Entry of jdbcDataSourceRuntimeTable"
      INDEX { jdbcDataSourceRuntimeIndex}
      ::= { jdbcDataSourceRuntimeTable 1 }
      
   JdbcDataSourceRuntimeEntry ::=
      SEQUENCE
      {
         jdbcDataSourceRuntimeIndex DisplayString,
         jdbcDataSourceRuntimeObjectName DisplayString,
         jdbcDataSourceRuntimeType DisplayString,
         jdbcDataSourceRuntimeName DisplayString,
         jdbcDataSourceRuntimeParent DisplayString,
         jdbcDataSourceRuntimeLeakedConnectionCount INTEGER,
         jdbcDataSourceRuntimeEnabled INTEGER,
         jdbcDataSourceRuntimeState DisplayString,
         jdbcDataSourceRuntimeFailuresToReconnectCount INTEGER,
         jdbcDataSourceRuntimeConnectionDelayTime INTEGER,
         jdbcDataSourceRuntimePrepStmtCacheAccessCount Counter64,
         jdbcDataSourceRuntimePrepStmtCacheAddCount Counter64,
         jdbcDataSourceRuntimePrepStmtCacheDeleteCount Counter64,
         jdbcDataSourceRuntimePrepStmtCacheCurrentSize INTEGER,
         jdbcDataSourceRuntimePrepStmtCacheHitCount INTEGER,
         jdbcDataSourceRuntimePrepStmtCacheMissCount INTEGER,
         jdbcDataSourceRuntimeActiveConnectionsCurrentCount INTEGER,
         jdbcDataSourceRuntimeWaitingForConnectionCurrentCount INTEGER,
         jdbcDataSourceRuntimeVersionJDBCDriver DisplayString,
         jdbcDataSourceRuntimeActiveConnectionsHighCount INTEGER,
         jdbcDataSourceRuntimeActiveConnectionsAverageCount INTEGER,
         jdbcDataSourceRuntimeReserveRequestCount Counter64,
         jdbcDataSourceRuntimeFailedReserveRequestCount Counter64,
         jdbcDataSourceRuntimeWaitingForConnectionHighCount INTEGER,
         jdbcDataSourceRuntimeWaitingForConnectionTotal Counter64,
         jdbcDataSourceRuntimeWaitingForConnectionSuccessTotal Counter64,
         jdbcDataSourceRuntimeWaitingForConnectionFailureTotal Counter64,
         jdbcDataSourceRuntimeWaitSecondsHighCount INTEGER,
         jdbcDataSourceRuntimeConnectionsTotalCount INTEGER,
         jdbcDataSourceRuntimeCurrCapacity INTEGER,
         jdbcDataSourceRuntimeCurrCapacityHighCount INTEGER,
         jdbcDataSourceRuntimeNumAvailable INTEGER,
         jdbcDataSourceRuntimeHighestNumAvailable INTEGER,
         jdbcDataSourceRuntimeNumUnavailable INTEGER,
         jdbcDataSourceRuntimeHighestNumUnavailable INTEGER,
         jdbcDataSourceRuntimeModuleId OCTET STRING,
         jdbcDataSourceRuntimeDeploymentState INTEGER,
         jdbcDataSourceRuntimeDatabaseProductName OCTET STRING,
         jdbcDataSourceRuntimeDriverVersion OCTET STRING,
         jdbcDataSourceRuntimeDriverName OCTET STRING,
         jdbcDataSourceRuntimeDatabaseProductVersion OCTET STRING,
         jdbcDataSourceRuntimeRepurposeCount Counter64,
         jdbcDataSourceRuntimeUnresolvedTotalCount Counter64,
         jdbcDataSourceRuntimeResolvedAsCommittedTotalCount Counter64,
         jdbcDataSourceRuntimeCommitOutcomeRetryTotalCount Counter64,
         jdbcDataSourceRuntimeResolvedAsNotCommittedTotalCount Counter64,
         jdbcDataSourceRuntimeFailedRepurposeCount Counter64
      }
      
   
   jdbcDataSourceRuntimeIndex OBJECT-TYPE
      SYNTAX      DisplayString (SIZE (1..16))
      MAX-ACCESS  read-only
      STATUS      current
      DESCRIPTION "Unique value directed from ObjectName which is used as table index"
      ::= { jdbcDataSourceRuntimeEntry 1  }
   
   
   jdbcDataSourceRuntimeObjectName OBJECT-TYPE
      SYNTAX      DisplayString (SIZE (1..256))
      MAX-ACCESS  read-only
      STATUS      current
      DESCRIPTION "JMX-standard MBean name"
      ::= { jdbcDataSourceRuntimeEntry 5  }
   
   
   jdbcDataSourceRuntimeType OBJECT-TYPE
      SYNTAX      DisplayString (SIZE (1..64))
      MAX-ACCESS  read-only
      STATUS      current
      DESCRIPTION "Returns the type of the MBean. "
      ::= { jdbcDataSourceRuntimeEntry 10  }
   
   
   jdbcDataSourceRuntimeName OBJECT-TYPE
      SYNTAX      DisplayString (SIZE (1..64))
      MAX-ACCESS  read-only
      STATUS      current
      DESCRIPTION "The name of this configuration. WebLogic Server uses an MBean to implement and persist the configuration. "
      ::= { jdbcDataSourceRuntimeEntry 15  }
   
   
   jdbcDataSourceRuntimeParent OBJECT-TYPE
      SYNTAX      DisplayString (SIZE (1..256))
      MAX-ACCESS  read-only
      STATUS      current
      DESCRIPTION "BEA-proprietary Parent object's identification, with syntax
      <type>:<name>"
      ::= { jdbcDataSourceRuntimeEntry 20  }
   
   
   jdbcDataSourceRuntimeLeakedConnectionCount OBJECT-TYPE
      SYNTAX      INTEGER
      MAX-ACCESS  read-only
      STATUS      current
      DESCRIPTION "The number of leaked connections. A leaked connection is a connection that was reserved from the data source but was not returned to the data source by calling close(). "
      ::= { jdbcDataSourceRuntimeEntry 25  }
   
   
   jdbcDataSourceRuntimeEnabled OBJECT-TYPE
      SYNTAX      INTEGER
                  {
                     true(1),
                     false(2)
                  }
      
      MAX-ACCESS  read-only
      STATUS      current
      DESCRIPTION "Indicates whether the data source is enabled or disabled:   true if the data source is enabled. false if the data source is disabled.  "
      ::= { jdbcDataSourceRuntimeEntry 30  }
   
   
   jdbcDataSourceRuntimeState OBJECT-TYPE
      SYNTAX      DisplayString (SIZE (1..64))
      MAX-ACCESS  read-only
      STATUS      current
      DESCRIPTION "The current state of the data source. Possible states are: Running - the data source is enabled (deployed and not Suspended). This is the normal state of the data source. This state includes conditions when the database server is not available and the data source is created (creation retry must be enabled) or when all connections have failed connection tests (on creation, on reserve, or periodic testing). Suspended - the data source has been disabled. Shutdown - the data source is shutdown and all database connections have been closed. Overloaded - all resources in pool are in use. Unknown - the data source state is unknown. "
      ::= { jdbcDataSourceRuntimeEntry 35  }
   
   
   jdbcDataSourceRuntimeFailuresToReconnectCount OBJECT-TYPE
      SYNTAX      INTEGER
      MAX-ACCESS  read-only
      STATUS      current
      DESCRIPTION "The number of times that the data source attempted to refresh a database connection and failed.  Failures may occur when the database is unavailable or when the network connection to the database is interrupted. "
      ::= { jdbcDataSourceRuntimeEntry 40  }
   
   
   jdbcDataSourceRuntimeConnectionDelayTime OBJECT-TYPE
      SYNTAX      INTEGER
      MAX-ACCESS  read-only
      STATUS      current
      DESCRIPTION "The average amount of time, in milliseconds, that it takes to create a physical connection to the database.  The value is calculated as summary of all times to connect divided by the total number of connections. "
      ::= { jdbcDataSourceRuntimeEntry 45  }
   
   
   jdbcDataSourceRuntimePrepStmtCacheAccessCount OBJECT-TYPE
      SYNTAX      Counter64
      MAX-ACCESS  read-only
      STATUS      current
      DESCRIPTION "The cumulative, running count of the number of times that the statement cache was accessed. "
      ::= { jdbcDataSourceRuntimeEntry 50  }
   
   
   jdbcDataSourceRuntimePrepStmtCacheAddCount OBJECT-TYPE
      SYNTAX      Counter64
      MAX-ACCESS  read-only
      STATUS      current
      DESCRIPTION "The cumulative, running count of the number of statements added to the statement cache.  Each connection in the connection pool has its own cache of statements. This number is the sum of the number of statements added to the caches for all connections in the connection pool. "
      ::= { jdbcDataSourceRuntimeEntry 55  }
   
   
   jdbcDataSourceRuntimePrepStmtCacheDeleteCount OBJECT-TYPE
      SYNTAX      Counter64
      MAX-ACCESS  read-only
      STATUS      current
      DESCRIPTION "The cumulative, running count of statements discarded from the cache.  Each connection in the connection pool has its own cache of statements. This number is the sum of the number of statements that were discarded from the caches for all connections in the connection pool. "
      ::= { jdbcDataSourceRuntimeEntry 60  }
   
   
   jdbcDataSourceRuntimePrepStmtCacheCurrentSize OBJECT-TYPE
      SYNTAX      INTEGER
      MAX-ACCESS  read-only
      STATUS      current
      DESCRIPTION "The number of prepared and callable statements currently cached in the statement cache.  Each connection in the connection pool has its own cache of statements. This number is the sum of the number of statements in the caches for all connections in the connection pool. "
      ::= { jdbcDataSourceRuntimeEntry 65  }
   
   
   jdbcDataSourceRuntimePrepStmtCacheHitCount OBJECT-TYPE
      SYNTAX      INTEGER
      MAX-ACCESS  read-only
      STATUS      current
      DESCRIPTION "The cumulative, running count of the number of times that statements from the cache were used. "
      ::= { jdbcDataSourceRuntimeEntry 70  }
   
   
   jdbcDataSourceRuntimePrepStmtCacheMissCount OBJECT-TYPE
      SYNTAX      INTEGER
      MAX-ACCESS  read-only
      STATUS      current
      DESCRIPTION "The number of times that a statement request could not be satisfied with a statement from the cache. "
      ::= { jdbcDataSourceRuntimeEntry 75  }
   
   
   jdbcDataSourceRuntimeActiveConnectionsCurrentCount OBJECT-TYPE
      SYNTAX      INTEGER
      MAX-ACCESS  read-only
      STATUS      current
      DESCRIPTION "The number of connections currently in use by applications. "
      ::= { jdbcDataSourceRuntimeEntry 80  }
   
   
   jdbcDataSourceRuntimeWaitingForConnectionCurrentCount OBJECT-TYPE
      SYNTAX      INTEGER
      MAX-ACCESS  read-only
      STATUS      current
      DESCRIPTION "The number of connection requests waiting for a database connection. "
      ::= { jdbcDataSourceRuntimeEntry 85  }
   
   
   jdbcDataSourceRuntimeVersionJDBCDriver OBJECT-TYPE
      SYNTAX      DisplayString (SIZE (1..64))
      MAX-ACCESS  read-only
      STATUS      current
      DESCRIPTION "The driver class name of the JDBC driver used to create database connections.  "
      ::= { jdbcDataSourceRuntimeEntry 90  }
   
   
   jdbcDataSourceRuntimeActiveConnectionsHighCount OBJECT-TYPE
      SYNTAX      INTEGER
      MAX-ACCESS  read-only
      STATUS      current
      DESCRIPTION "Highest number of active database connections in this instance of the data source since the data source was instantiated.   Active connections are connections in use by an application. "
      ::= { jdbcDataSourceRuntimeEntry 95  }
   
   
   jdbcDataSourceRuntimeActiveConnectionsAverageCount OBJECT-TYPE
      SYNTAX      INTEGER
      MAX-ACCESS  read-only
      STATUS      current
      DESCRIPTION "Average number of active connections in this instance of the data source.  Active connections are connections in use by an application.  This value is only valid if the resource is configured to allow shrinking. "
      ::= { jdbcDataSourceRuntimeEntry 100  }
   
   
   jdbcDataSourceRuntimeReserveRequestCount OBJECT-TYPE
      SYNTAX      Counter64
      MAX-ACCESS  read-only
      STATUS      current
      DESCRIPTION "The cumulative, running count of requests for a connection from this data source. "
      ::= { jdbcDataSourceRuntimeEntry 105  }
   
   
   jdbcDataSourceRuntimeFailedReserveRequestCount OBJECT-TYPE
      SYNTAX      Counter64
      MAX-ACCESS  read-only
      STATUS      current
      DESCRIPTION "The cumulative, running count of requests for a connection from this data source that could not be fulfilled. "
      ::= { jdbcDataSourceRuntimeEntry 110  }
   
   
   jdbcDataSourceRuntimeWaitingForConnectionHighCount OBJECT-TYPE
      SYNTAX      INTEGER
      MAX-ACCESS  read-only
      STATUS      current
      DESCRIPTION "Highest number of application requests concurrently waiting for a connection from this instance of the data source. "
      ::= { jdbcDataSourceRuntimeEntry 115  }
   
   
   jdbcDataSourceRuntimeWaitingForConnectionTotal OBJECT-TYPE
      SYNTAX      Counter64
      MAX-ACCESS  read-only
      STATUS      current
      DESCRIPTION "The cumulative, running count of requests for a connection from this data source that had to wait before getting a connection, including those that eventually got a connection and those that did not get a connection. "
      ::= { jdbcDataSourceRuntimeEntry 120  }
   
   
   jdbcDataSourceRuntimeWaitingForConnectionSuccessTotal OBJECT-TYPE
      SYNTAX      Counter64
      MAX-ACCESS  read-only
      STATUS      current
      DESCRIPTION "The cumulative, running count of requests for a connection from this data source that had to wait before getting a connection and eventually succeeded in getting a connection. "
      ::= { jdbcDataSourceRuntimeEntry 125  }
   
   
   jdbcDataSourceRuntimeWaitingForConnectionFailureTotal OBJECT-TYPE
      SYNTAX      Counter64
      MAX-ACCESS  read-only
      STATUS      current
      DESCRIPTION "The cumulative, running count of requests for a connection from this data source that had to wait before getting a connection and eventually failed to get a connection.  Waiting connection requests can fail for a variety of reasons, including waiting for longer than the ConnectionReserveTimeoutSeconds. "
      ::= { jdbcDataSourceRuntimeEntry 130  }
   
   
   jdbcDataSourceRuntimeWaitSecondsHighCount OBJECT-TYPE
      SYNTAX      INTEGER
      MAX-ACCESS  read-only
      STATUS      current
      DESCRIPTION "The highest number of seconds that an application waited for a connection (the longest connection reserve wait time) from this instance of the connection pool since the connection pool was instantiated. This value is updated when a completed getConnection request takes longer to return a connection than any previous request. "
      ::= { jdbcDataSourceRuntimeEntry 135  }
   
   
   jdbcDataSourceRuntimeConnectionsTotalCount OBJECT-TYPE
      SYNTAX      INTEGER
      MAX-ACCESS  read-only
      STATUS      current
      DESCRIPTION "The cumulative total number of database connections created in this data source since the data source was deployed. "
      ::= { jdbcDataSourceRuntimeEntry 140  }
   
   
   jdbcDataSourceRuntimeCurrCapacity OBJECT-TYPE
      SYNTAX      INTEGER
      MAX-ACCESS  read-only
      STATUS      current
      DESCRIPTION "The current count of JDBC connections in the connection pool in the data source. "
      ::= { jdbcDataSourceRuntimeEntry 145  }
   
   
   jdbcDataSourceRuntimeCurrCapacityHighCount OBJECT-TYPE
      SYNTAX      INTEGER
      MAX-ACCESS  read-only
      STATUS      current
      DESCRIPTION "Highest number of database connections available or in use (current capacity) in this instance of the data source since the data source was deployed. "
      ::= { jdbcDataSourceRuntimeEntry 150  }
   
   
   jdbcDataSourceRuntimeNumAvailable OBJECT-TYPE
      SYNTAX      INTEGER
      MAX-ACCESS  read-only
      STATUS      current
      DESCRIPTION "The number of database connections that are currently idle and  available to be used by applications in this instance of the data source. "
      ::= { jdbcDataSourceRuntimeEntry 155  }
   
   
   jdbcDataSourceRuntimeHighestNumAvailable OBJECT-TYPE
      SYNTAX      INTEGER
      MAX-ACCESS  read-only
      STATUS      current
      DESCRIPTION "Highest number of database connections that were idle and available to be used by an application at any time in this instance of the data source since the data source was deployed. "
      ::= { jdbcDataSourceRuntimeEntry 160  }
   
   
   jdbcDataSourceRuntimeNumUnavailable OBJECT-TYPE
      SYNTAX      INTEGER
      MAX-ACCESS  read-only
      STATUS      current
      DESCRIPTION "The number of connections currently in use by applications or being tested in this instance of the data source. "
      ::= { jdbcDataSourceRuntimeEntry 165  }
   
   
   jdbcDataSourceRuntimeHighestNumUnavailable OBJECT-TYPE
      SYNTAX      INTEGER
      MAX-ACCESS  read-only
      STATUS      current
      DESCRIPTION "Highest number of database connections that were in use by applications or being tested by the system in this instance of the data source since the data source was deployed. "
      ::= { jdbcDataSourceRuntimeEntry 170  }
   
   
   jdbcDataSourceRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { jdbcDataSourceRuntimeEntry 171  }
   
   
   jdbcDataSourceRuntimeDeploymentState OBJECT-TYPE
      SYNTAX      INTEGER
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jdbcDataSourceRuntimeEntry 172  }
   
   
   jdbcDataSourceRuntimeDatabaseProductName OBJECT-TYPE
      SYNTAX      OCTET STRING
      MAX-ACCESS  read-only
      STATUS      current
      DESCRIPTION " The product name of the database that this data source is connected to.  "
      ::= { jdbcDataSourceRuntimeEntry 173  }
   
   
   jdbcDataSourceRuntimeDriverVersion OBJECT-TYPE
      SYNTAX      OCTET STRING
      MAX-ACCESS  read-only
      STATUS      current
      DESCRIPTION " The version of the JDBC driver that this data source is configured to use.  "
      ::= { jdbcDataSourceRuntimeEntry 174  }
   
   
   jdbcDataSourceRuntimeDriverName OBJECT-TYPE
      SYNTAX      OCTET STRING
      MAX-ACCESS  read-only
      STATUS      current
      DESCRIPTION " The product name of the JDBC driver that this data source is configured to use.  "
      ::= { jdbcDataSourceRuntimeEntry 175  }
   
   
   jdbcDataSourceRuntimeDatabaseProductVersion OBJECT-TYPE
      SYNTAX      OCTET STRING
      MAX-ACCESS  read-only
      STATUS      current
      DESCRIPTION " The product version of the database that this data source is connected to.  "
      ::= { jdbcDataSourceRuntimeEntry 176  }
   
   
   jdbcDataSourceRuntimeRepurposeCount OBJECT-TYPE
      SYNTAX      Counter64
      MAX-ACCESS  read-only
      STATUS      current
      DESCRIPTION "The number of times connections have been repurposed since the datasource was deployed. "
      ::= { jdbcDataSourceRuntimeEntry 177  }
   
   
   jdbcDataSourceRuntimeUnresolvedTotalCount OBJECT-TYPE
      SYNTAX      Counter64
      MAX-ACCESS  read-only
      STATUS      current
      DESCRIPTION "The cumulative total number of commit outcomes unsuccessfully resolved in this data source since the data source was deployed. This does not refer to the number of outcome query retries used to resolve the outcomes. "
      ::= { jdbcDataSourceRuntimeEntry 178  }
   
   
   jdbcDataSourceRuntimeResolvedAsCommittedTotalCount OBJECT-TYPE
      SYNTAX      Counter64
      MAX-ACCESS  read-only
      STATUS      current
      DESCRIPTION "The cumulative total number of commit outcomes successfully resolved as committed in this data source since the data source was deployed. This does not refer to the number of outcome query retries used to resolve the outcomes. "
      ::= { jdbcDataSourceRuntimeEntry 179  }
   
   
   jdbcDataSourceRuntimeCommitOutcomeRetryTotalCount OBJECT-TYPE
      SYNTAX      Counter64
      MAX-ACCESS  read-only
      STATUS      current
      DESCRIPTION "The cumulative total number of commit outcome query retries conducted before resolving the outcome or exceeding the retry seconds in this data source since the data source was deployed. "
      ::= { jdbcDataSourceRuntimeEntry 180  }
   
   
   jdbcDataSourceRuntimeResolvedAsNotCommittedTotalCount OBJECT-TYPE
      SYNTAX      Counter64
      MAX-ACCESS  read-only
      STATUS      current
      DESCRIPTION "The cumulative total number of commit outcomes successfully resolved as not committed in this data source since the data source was deployed. This does not refer to the number of outcome query retries used to resolve the outcomes. "
      ::= { jdbcDataSourceRuntimeEntry 181  }
   
   
   jdbcDataSourceRuntimeFailedRepurposeCount OBJECT-TYPE
      SYNTAX      Counter64
      MAX-ACCESS  read-only
      STATUS      current
      DESCRIPTION "The number of repurpose errors that have occurred since the datasource was deployed. "
      ::= { jdbcDataSourceRuntimeEntry 182  }
   
   
   jmsConnectionRuntimeTable OBJECT-TYPE
      SYNTAX      SEQUENCE OF JmsConnectionRuntimeEntry
      MAX-ACCESS  not-accessible
      STATUS      current
      DESCRIPTION "This class is used for monitoring a WebLogic JMS connection. "
      ::= { wls 200  }
      
   
   jmsConnectionRuntimeEntry OBJECT-TYPE
      SYNTAX      JmsConnectionRuntimeEntry
      MAX-ACCESS  not-accessible
      STATUS      current
      DESCRIPTION "Entry of jmsConnectionRuntimeTable"
      INDEX { jmsConnectionRuntimeIndex}
      ::= { jmsConnectionRuntimeTable 1 }
      
   JmsConnectionRuntimeEntry ::=
      SEQUENCE
      {
         jmsConnectionRuntimeIndex DisplayString,
         jmsConnectionRuntimeObjectName DisplayString,
         jmsConnectionRuntimeType DisplayString,
         jmsConnectionRuntimeName DisplayString,
         jmsConnectionRuntimeParent DisplayString,
         jmsConnectionRuntimeClientID DisplayString,
         jmsConnectionRuntimeSessionsCurrentCount Counter64,
         jmsConnectionRuntimeSessionsHighCount Counter64,
         jmsConnectionRuntimeSessionsTotalCount Counter64,
         jmsConnectionRuntimeHostAddress OCTET STRING,
         jmsConnectionRuntimeClientIDPolicy OCTET STRING
      }
      
   
   jmsConnectionRuntimeIndex OBJECT-TYPE
      SYNTAX      DisplayString (SIZE (1..16))
      MAX-ACCESS  read-only
      STATUS      current
      DESCRIPTION "Unique value directed from ObjectName which is used as table index"
      ::= { jmsConnectionRuntimeEntry 1  }
   
   
   jmsConnectionRuntimeObjectName OBJECT-TYPE
      SYNTAX      DisplayString (SIZE (1..256))
      MAX-ACCESS  read-only
      STATUS      current
      DESCRIPTION "JMX-standard MBean name"
      ::= { jmsConnectionRuntimeEntry 5  }
   
   
   jmsConnectionRuntimeType OBJECT-TYPE
      SYNTAX      DisplayString (SIZE (1..64))
      MAX-ACCESS  read-only
      STATUS      current
      DESCRIPTION "Returns the type of the MBean. "
      ::= { jmsConnectionRuntimeEntry 10  }
   
   
   jmsConnectionRuntimeName OBJECT-TYPE
      SYNTAX      DisplayString (SIZE (1..64))
      MAX-ACCESS  read-only
      STATUS      current
      DESCRIPTION "The name of this configuration. WebLogic Server uses an MBean to implement and persist the configuration. "
      ::= { jmsConnectionRuntimeEntry 15  }
   
   
   jmsConnectionRuntimeParent OBJECT-TYPE
      SYNTAX      DisplayString (SIZE (1..256))
      MAX-ACCESS  read-only
      STATUS      current
      DESCRIPTION "BEA-proprietary Parent object's identification, with syntax
      <type>:<name>"
      ::= { jmsConnectionRuntimeEntry 20  }
   
   
   jmsConnectionRuntimeClientID OBJECT-TYPE
      SYNTAX      DisplayString (SIZE (1..64))
      MAX-ACCESS  read-only
      STATUS      current
      DESCRIPTION "The client ID for this connection. "
      ::= { jmsConnectionRuntimeEntry 25  }
   
   
   jmsConnectionRuntimeSessionsCurrentCount OBJECT-TYPE
      SYNTAX      Counter64
      MAX-ACCESS  read-only
      STATUS      current
      DESCRIPTION "The current number of sessions for this connection. "
      ::= { jmsConnectionRuntimeEntry 35  }
   
   
   jmsConnectionRuntimeSessionsHighCount OBJECT-TYPE
      SYNTAX      Counter64
      MAX-ACCESS  read-only
      STATUS      current
      DESCRIPTION "The peak number of sessions for this connection since the last reset. "
      ::= { jmsConnectionRuntimeEntry 40  }
   
   
   jmsConnectionRuntimeSessionsTotalCount OBJECT-TYPE
      SYNTAX      Counter64
      MAX-ACCESS  read-only
      STATUS      current
      DESCRIPTION "The number of sessions on this connection since the last reset. "
      ::= { jmsConnectionRuntimeEntry 45  }
   
   
   jmsConnectionRuntimeHostAddress OBJECT-TYPE
      SYNTAX      OCTET STRING
      MAX-ACCESS  read-only
      STATUS      current
      DESCRIPTION "The host address of the client JVM as a string. "
      ::= { jmsConnectionRuntimeEntry 46  }
   
   
   jmsConnectionRuntimeClientIDPolicy OBJECT-TYPE
      SYNTAX      OCTET STRING
      MAX-ACCESS  read-only
      STATUS      current
      DESCRIPTION "The ClientIDPolicy on this connection or durable subscriber. Values are:  weblogic.management.configuration.JMSConstants.CLIENT_ID_POLICY_RESTRICTED: Only one connection that uses this policy exists in a cluster at any given time for a particular ClientID. weblogic.management.configuration.JMSConstants.CLIENT_ID_POLICY_UNRESTRICTED: Connections created using this policy can specify any ClientID, even when other restricted or unrestricted connections already use the same ClientID.  "
      ::= { jmsConnectionRuntimeEntry 47  }
   
   
   jmsConsumerRuntimeTable OBJECT-TYPE
      SYNTAX      SEQUENCE OF JmsConsumerRuntimeEntry
      MAX-ACCESS  not-accessible
      STATUS      current
      DESCRIPTION "This class is used for monitoring a WebLogic JMS consumer. "
      ::= { wls 210  }
      
   
   jmsConsumerRuntimeEntry OBJECT-TYPE
      SYNTAX      JmsConsumerRuntimeEntry
      MAX-ACCESS  not-accessible
      STATUS      current
      DESCRIPTION "Entry of jmsConsumerRuntimeTable"
      INDEX { jmsConsumerRuntimeIndex}
      ::= { jmsConsumerRuntimeTable 1 }
      
   JmsConsumerRuntimeEntry ::=
      SEQUENCE
      {
         jmsConsumerRuntimeIndex DisplayString,
         jmsConsumerRuntimeObjectName DisplayString,
         jmsConsumerRuntimeType DisplayString,
         jmsConsumerRuntimeName DisplayString,
         jmsConsumerRuntimeParent DisplayString,
         jmsConsumerRuntimeMessagesPendingCount Counter64,
         jmsConsumerRuntimeMessagesReceivedCount Counter64,
         jmsConsumerRuntimeBytesPendingCount Counter64,
         jmsConsumerRuntimeBytesReceivedCount Counter64,
         jmsConsumerRuntimeDestinationName DisplayString,
         jmsConsumerRuntimeSelector DisplayString,
         jmsConsumerRuntimeDurable INTEGER,
         jmsConsumerRuntimeActive INTEGER,
         jmsConsumerRuntimeMemberDestinationName OCTET STRING,
         jmsConsumerRuntimeSubscriptionSharingPolicy OCTET STRING,
         jmsConsumerRuntimeClientID OCTET STRING,
         jmsConsumerRuntimeClientIDPolicy OCTET STRING
      }
      
   
   jmsConsumerRuntimeIndex OBJECT-TYPE
      SYNTAX      DisplayString (SIZE (1..16))
      MAX-ACCESS  read-only
      STATUS      current
      DESCRIPTION "Unique value directed from ObjectName which is used as table index"
      ::= { jmsConsumerRuntimeEntry 1  }
   
   
   jmsConsumerRuntimeObjectName OBJECT-TYPE
      SYNTAX      DisplayString (SIZE (1..256))
      MAX-ACCESS  read-only
      STATUS      current
      DESCRIPTION "JMX-standard MBean name"
      ::= { jmsConsumerRuntimeEntry 5  }
   
   
   jmsConsumerRuntimeType OBJECT-TYPE
      SYNTAX      DisplayString (SIZE (1..64))
      MAX-ACCESS  read-only
      STATUS      current
      DESCRIPTION "Returns the type of the MBean. "
      ::= { jmsConsumerRuntimeEntry 10  }
   
   
   jmsConsumerRuntimeName OBJECT-TYPE
      SYNTAX      DisplayString (SIZE (1..64))
      MAX-ACCESS  read-only
      STATUS      current
      DESCRIPTION "The name of this configuration. WebLogic Server uses an MBean to implement and persist the configuration. "
      ::= { jmsConsumerRuntimeEntry 15  }
   
   
   jmsConsumerRuntimeParent OBJECT-TYPE
      SYNTAX      DisplayString (SIZE (1..256))
      MAX-ACCESS  read-only
      STATUS      current
      DESCRIPTION "BEA-proprietary Parent object's identification, with syntax
      <type>:<name>"
      ::= { jmsConsumerRuntimeEntry 20  }
   
   
   jmsConsumerRuntimeMessagesPendingCount OBJECT-TYPE
      SYNTAX      Counter64
      MAX-ACCESS  read-only
      STATUS      current
      DESCRIPTION "The number of messages pending (uncommitted and unacknowledged) by this consumer. "
      ::= { jmsConsumerRuntimeEntry 25  }
   
   
   jmsConsumerRuntimeMessagesReceivedCount OBJECT-TYPE
      SYNTAX      Counter64
      MAX-ACCESS  read-only
      STATUS      current
      DESCRIPTION "The number of messages received by this consumer since the last reset. "
      ::= { jmsConsumerRuntimeEntry 30  }
   
   
   jmsConsumerRuntimeBytesPendingCount OBJECT-TYPE
      SYNTAX      Counter64
      MAX-ACCESS  read-only
      STATUS      current
      DESCRIPTION "The number of bytes pending (uncommitted and unacknowledged) by this consumer. "
      ::= { jmsConsumerRuntimeEntry 35  }
   
   
   jmsConsumerRuntimeBytesReceivedCount OBJECT-TYPE
      SYNTAX      Counter64
      MAX-ACCESS  read-only
      STATUS      current
      DESCRIPTION "The number of bytes received by this consumer since the last reset. "
      ::= { jmsConsumerRuntimeEntry 40  }
   
   
   jmsConsumerRuntimeDestinationName OBJECT-TYPE
      SYNTAX      DisplayString (SIZE (1..256))
      MAX-ACCESS  read-only
      STATUS      current
      DESCRIPTION "The name of the destination for this consumer. In case of a distributed destination, it is the name of the distributed destination, instead of the member destination. "
      ::= { jmsConsumerRuntimeEntry 45  }
   
   
   jmsConsumerRuntimeSelector OBJECT-TYPE
      SYNTAX      DisplayString (SIZE (1..256))
      MAX-ACCESS  read-only
      STATUS      current
      DESCRIPTION "The selector associated with this consumer, if any. "
      ::= { jmsConsumerRuntimeEntry 50  }
   
   
   jmsConsumerRuntimeDurable OBJECT-TYPE
      SYNTAX      INTEGER
                  {
                     true(1),
                     false(2)
                  }
      
      MAX-ACCESS  read-only
      STATUS      current
      DESCRIPTION "Indicates whether the consumer is durable. "
      ::= { jmsConsumerRuntimeEntry 55  }
   
   
   jmsConsumerRuntimeActive OBJECT-TYPE
      SYNTAX      INTEGER
      MAX-ACCESS  read-only
      STATUS      current
      DESCRIPTION "Indicates whether the consumer active. A consumer is active if it has a message listener set up or a synchronous receive in progress. "
      ::= { jmsConsumerRuntimeEntry 56  }
   
   
   jmsConsumerRuntimeMemberDestinationName OBJECT-TYPE
      SYNTAX      OCTET STRING
      MAX-ACCESS  read-only
      STATUS      current
      DESCRIPTION "The name of the destination for this consumer. In case of a distributed destination, it is the name of the member destination. "
      ::= { jmsConsumerRuntimeEntry 57  }
   
   
   jmsConsumerRuntimeSubscriptionSharingPolicy OBJECT-TYPE
      SYNTAX      OCTET STRING
      MAX-ACCESS  read-only
      STATUS      current
      DESCRIPTION "The Subscription Sharing Policy on this subscriber. "
      ::= { jmsConsumerRuntimeEntry 58  }
   
   
   jmsConsumerRuntimeClientID OBJECT-TYPE
      SYNTAX      OCTET STRING
      MAX-ACCESS  read-only
      STATUS      current
      DESCRIPTION "The client ID for this connection. "
      ::= { jmsConsumerRuntimeEntry 59  }
   
   
   jmsConsumerRuntimeClientIDPolicy OBJECT-TYPE
      SYNTAX      OCTET STRING
      MAX-ACCESS  read-only
      STATUS      current
      DESCRIPTION "The ClientIDPolicy on this connection or durable subscriber. Valid values are:  weblogic.management.configuration.JMSConstants.CLIENT_ID_POLICY_RESTRICTED: Only one connection that uses this policy exists in a cluster at any given time for a particular ClientID. weblogic.management.configuration.JMSConstants.CLIENT_ID_POLICY_UNRESTRICTED:  Connections created using this policy can specify any ClientID, even when other restricted or unrestricted connections already use the same ClientID.  "
      ::= { jmsConsumerRuntimeEntry 60  }
   
   
   jmsDestinationRuntimeTable OBJECT-TYPE
      SYNTAX      SEQUENCE OF JmsDestinationRuntimeEntry
      MAX-ACCESS  not-accessible
      STATUS      current
      DESCRIPTION "This class is used for monitoring a WebLogic JMS destination (topic or queue). "
      ::= { wls 220  }
      
   
   jmsDestinationRuntimeEntry OBJECT-TYPE
      SYNTAX      JmsDestinationRuntimeEntry
      MAX-ACCESS  not-accessible
      STATUS      current
      DESCRIPTION "Entry of jmsDestinationRuntimeTable"
      INDEX { jmsDestinationRuntimeIndex}
      ::= { jmsDestinationRuntimeTable 1 }
      
   JmsDestinationRuntimeEntry ::=
      SEQUENCE
      {
         jmsDestinationRuntimeIndex DisplayString,
         jmsDestinationRuntimeObjectName DisplayString,
         jmsDestinationRuntimeType DisplayString,
         jmsDestinationRuntimeName DisplayString,
         jmsDestinationRuntimeParent DisplayString,
         jmsDestinationRuntimeConsumersCurrentCount Counter64,
         jmsDestinationRuntimeConsumersHighCount Counter64,
         jmsDestinationRuntimeConsumersTotalCount Counter64,
         jmsDestinationRuntimeMessagesCurrentCount Counter64,
         jmsDestinationRuntimeMessagesPendingCount Counter64,
         jmsDestinationRuntimeMessagesHighCount Counter64,
         jmsDestinationRuntimeMessagesReceivedCount Counter64,
         jmsDestinationRuntimeMessagesThresholdTime Counter64,
         jmsDestinationRuntimeBytesCurrentCount Counter64,
         jmsDestinationRuntimeBytesPendingCount Counter64,
         jmsDestinationRuntimeBytesHighCount Counter64,
         jmsDestinationRuntimeBytesReceivedCount Counter64,
         jmsDestinationRuntimeBytesThresholdTime Counter64,
         jmsDestinationRuntimeProductionPaused OCTET STRING,
         jmsDestinationRuntimeInsertionPaused OCTET STRING,
         jmsDestinationRuntimeConsumptionPausedState OCTET STRING,
         jmsDestinationRuntimeConsumptionPaused OCTET STRING,
         jmsDestinationRuntimeState OCTET STRING,
         jmsDestinationRuntimeInsertionPausedState OCTET STRING,
         jmsDestinationRuntimeDestinationType OCTET STRING,
         jmsDestinationRuntimeProductionPausedState OCTET STRING,
         jmsDestinationRuntimeMessagesDeletedCurrentCount Counter64,
         jmsDestinationRuntimePaused OCTET STRING,
         jmsDestinationRuntimeMessagesMovedCurrentCount Counter64,
         jmsDestinationRuntimeSubscriptionMessagesLimit Counter64
      }
      
   
   jmsDestinationRuntimeIndex OBJECT-TYPE
      SYNTAX      DisplayString (SIZE (1..16))
      MAX-ACCESS  read-only
      STATUS      current
      DESCRIPTION "Unique value directed from ObjectName which is used as table index"
      ::= { jmsDestinationRuntimeEntry 1  }
   
   
   jmsDestinationRuntimeObjectName OBJECT-TYPE
      SYNTAX      DisplayString (SIZE (1..256))
      MAX-ACCESS  read-only
      STATUS      current
      DESCRIPTION "JMX-standard MBean name"
      ::= { jmsDestinationRuntimeEntry 5  }
   
   
   jmsDestinationRuntimeType OBJECT-TYPE
      SYNTAX      DisplayString (SIZE (1..64))
      MAX-ACCESS  read-only
      STATUS      current
      DESCRIPTION "Returns the type of the MBean. "
      ::= { jmsDestinationRuntimeEntry 10  }
   
   
   jmsDestinationRuntimeName OBJECT-TYPE
      SYNTAX      DisplayString (SIZE (1..64))
      MAX-ACCESS  read-only
      STATUS      current
      DESCRIPTION "The name of this configuration. WebLogic Server uses an MBean to implement and persist the configuration. "
      ::= { jmsDestinationRuntimeEntry 15  }
   
   
   jmsDestinationRuntimeParent OBJECT-TYPE
      SYNTAX      DisplayString (SIZE (1..256))
      MAX-ACCESS  read-only
      STATUS      current
      DESCRIPTION "BEA-proprietary Parent object's identification, with syntax
      <type>:<name>"
      ::= { jmsDestinationRuntimeEntry 20  }
   
   
   jmsDestinationRuntimeConsumersCurrentCount OBJECT-TYPE
      SYNTAX      Counter64
      MAX-ACCESS  read-only
      STATUS      current
      DESCRIPTION "The current number of consumers accessing this destination. "
      ::= { jmsDestinationRuntimeEntry 25  }
   
   
   jmsDestinationRuntimeConsumersHighCount OBJECT-TYPE
      SYNTAX      Counter64
      MAX-ACCESS  read-only
      STATUS      current
      DESCRIPTION "The peak number of consumers accessing this destination since the last reset. "
      ::= { jmsDestinationRuntimeEntry 30  }
   
   
   jmsDestinationRuntimeConsumersTotalCount OBJECT-TYPE
      SYNTAX      Counter64
      MAX-ACCESS  read-only
      STATUS      current
      DESCRIPTION "The total number of consumers accessing this destination since the last reset. "
      ::= { jmsDestinationRuntimeEntry 35  }
   
   
   jmsDestinationRuntimeMessagesCurrentCount OBJECT-TYPE
      SYNTAX      Counter64
      MAX-ACCESS  read-only
      STATUS      current
      DESCRIPTION "The current number of messages in the destination. This does not include the pending messages. "
      ::= { jmsDestinationRuntimeEntry 40  }
   
   
   jmsDestinationRuntimeMessagesPendingCount OBJECT-TYPE
      SYNTAX      Counter64
      MAX-ACCESS  read-only
      STATUS      current
      DESCRIPTION "The number of pending messages in the destination.  Pending messages are over and above the current number of messages. A pending message is one that has either been sent in a transaction and not committed, or that has been received and not committed or acknowledged. "
      ::= { jmsDestinationRuntimeEntry 45  }
   
   
   jmsDestinationRuntimeMessagesHighCount OBJECT-TYPE
      SYNTAX      Counter64
      MAX-ACCESS  read-only
      STATUS      current
      DESCRIPTION "The peak number of messages in the destination since the last reset. "
      ::= { jmsDestinationRuntimeEntry 50  }
   
   
   jmsDestinationRuntimeMessagesReceivedCount OBJECT-TYPE
      SYNTAX      Counter64
      MAX-ACCESS  read-only
      STATUS      current
      DESCRIPTION "The number of messages received in this destination since the last reset. "
      ::= { jmsDestinationRuntimeEntry 55  }
   
   
   jmsDestinationRuntimeMessagesThresholdTime OBJECT-TYPE
      SYNTAX      Counter64
      MAX-ACCESS  read-only
      STATUS      current
      DESCRIPTION "The amount of time in the threshold condition since the last reset. "
      ::= { jmsDestinationRuntimeEntry 60  }
   
   
   jmsDestinationRuntimeBytesCurrentCount OBJECT-TYPE
      SYNTAX      Counter64
      MAX-ACCESS  read-only
      STATUS      current
      DESCRIPTION "The current number of bytes stored in the destination. This does not include the pending bytes. "
      ::= { jmsDestinationRuntimeEntry 65  }
   
   
   jmsDestinationRuntimeBytesPendingCount OBJECT-TYPE
      SYNTAX      Counter64
      MAX-ACCESS  read-only
      STATUS      current
      DESCRIPTION "The number of pending bytes stored in the destination.  Pending bytes are over and above the current number of bytes. "
      ::= { jmsDestinationRuntimeEntry 70  }
   
   
   jmsDestinationRuntimeBytesHighCount OBJECT-TYPE
      SYNTAX      Counter64
      MAX-ACCESS  read-only
      STATUS      current
      DESCRIPTION "The peak number of bytes stored in the destination since the last reset. "
      ::= { jmsDestinationRuntimeEntry 75  }
   
   
   jmsDestinationRuntimeBytesReceivedCount OBJECT-TYPE
      SYNTAX      Counter64
      MAX-ACCESS  read-only
      STATUS      current
      DESCRIPTION "The number of bytes received in this destination since the last reset. "
      ::= { jmsDestinationRuntimeEntry 80  }
   
   
   jmsDestinationRuntimeBytesThresholdTime OBJECT-TYPE
      SYNTAX      Counter64
      MAX-ACCESS  read-only
      STATUS      current
      DESCRIPTION "The amount of time in the threshold condition since the last reset. "
      ::= { jmsDestinationRuntimeEntry 85  }
   
   
   jmsDestinationRuntimeProductionPaused OBJECT-TYPE
      SYNTAX      OCTET STRING
      MAX-ACCESS  read-only
      STATUS      current
      DESCRIPTION "Indicates the ProductionPause state of the destination. "
      ::= { jmsDestinationRuntimeEntry 91  }
   
   
   jmsDestinationRuntimeInsertionPaused OBJECT-TYPE
      SYNTAX      OCTET STRING
      MAX-ACCESS  read-only
      STATUS      current
      DESCRIPTION "Indicates the InsertionPause state of the destination. "
      ::= { jmsDestinationRuntimeEntry 92  }
   
   
   jmsDestinationRuntimeConsumptionPausedState OBJECT-TYPE
      SYNTAX      OCTET STRING
      MAX-ACCESS  read-only
      STATUS      current
      DESCRIPTION "The current consumption pause state of the destination. "
      ::= { jmsDestinationRuntimeEntry 93  }
   
   
   jmsDestinationRuntimeConsumptionPaused OBJECT-TYPE
      SYNTAX      OCTET STRING
      MAX-ACCESS  read-only
      STATUS      current
      DESCRIPTION "Indicates the consumption Pause state of the destination. "
      ::= { jmsDestinationRuntimeEntry 94  }
   
   
   jmsDestinationRuntimeState OBJECT-TYPE
      SYNTAX      OCTET STRING
      MAX-ACCESS  read-only
      STATUS      current
      DESCRIPTION "The operational state of the destination as a String. "
      ::= { jmsDestinationRuntimeEntry 95  }
   
   
   jmsDestinationRuntimeInsertionPausedState OBJECT-TYPE
      SYNTAX      OCTET STRING
      MAX-ACCESS  read-only
      STATUS      current
      DESCRIPTION "The current insertion pause state of the destination. "
      ::= { jmsDestinationRuntimeEntry 96  }
   
   
   jmsDestinationRuntimeDestinationType OBJECT-TYPE
      SYNTAX      OCTET STRING
      MAX-ACCESS  read-only
      STATUS      current
      DESCRIPTION "The destination type, either weblogic.management.configuration.JMSConstants.DESTINATION_TYPE_QUEUE or weblogic.management.configuration.JMSConstants.DESTINATION_TYPE_TOPIC depending upon whether the destination is a queue or topic. "
      ::= { jmsDestinationRuntimeEntry 97  }
   
   
   jmsDestinationRuntimeProductionPausedState OBJECT-TYPE
      SYNTAX      OCTET STRING
      MAX-ACCESS  read-only
      STATUS      current
      DESCRIPTION "The current production pause state of the destination. "
      ::= { jmsDestinationRuntimeEntry 98  }
   
   
   jmsDestinationRuntimeMessagesDeletedCurrentCount OBJECT-TYPE
      SYNTAX      Counter64
      MAX-ACCESS  read-only
      STATUS      current
      DESCRIPTION "Returns the number of messages that have been deleted from the destination. "
      ::= { jmsDestinationRuntimeEntry 99  }
   
   
   jmsDestinationRuntimePaused OBJECT-TYPE
      SYNTAX      OCTET STRING
      MAX-ACCESS  read-only
      STATUS      current
      DESCRIPTION "Indicates whether or not the destination is paused at the current time. "
      ::= { jmsDestinationRuntimeEntry 100  }
   
   
   jmsDestinationRuntimeMessagesMovedCurrentCount OBJECT-TYPE
      SYNTAX      Counter64
      MAX-ACCESS  read-only
      STATUS      current
      DESCRIPTION "Returns the number of messages that have been moved from the destination. "
      ::= { jmsDestinationRuntimeEntry 101  }
   
   
   jmsDestinationRuntimeSubscriptionMessagesLimit OBJECT-TYPE
      SYNTAX      Counter64
      MAX-ACCESS  read-only
      STATUS      current
      DESCRIPTION "The effective messages limit on topic subscriptions (not applicable to queues). A '-1' indicates that no limit is configured or active. "
      ::= { jmsDestinationRuntimeEntry 102  }
   
   
   jmsProducerRuntimeTable OBJECT-TYPE
      SYNTAX      SEQUENCE OF JmsProducerRuntimeEntry
      MAX-ACCESS  not-accessible
      STATUS      current
      DESCRIPTION "This class is used for monitoring a WebLogic JMS producer. "
      ::= { wls 230  }
      
   
   jmsProducerRuntimeEntry OBJECT-TYPE
      SYNTAX      JmsProducerRuntimeEntry
      MAX-ACCESS  not-accessible
      STATUS      current
      DESCRIPTION "Entry of jmsProducerRuntimeTable"
      INDEX { jmsProducerRuntimeIndex}
      ::= { jmsProducerRuntimeTable 1 }
      
   JmsProducerRuntimeEntry ::=
      SEQUENCE
      {
         jmsProducerRuntimeIndex DisplayString,
         jmsProducerRuntimeObjectName DisplayString,
         jmsProducerRuntimeType DisplayString,
         jmsProducerRuntimeName DisplayString,
         jmsProducerRuntimeParent DisplayString,
         jmsProducerRuntimeMessagesPendingCount Counter64,
         jmsProducerRuntimeMessagesSentCount Counter64,
         jmsProducerRuntimeBytesPendingCount Counter64,
         jmsProducerRuntimeBytesSentCount Counter64
      }
      
   
   jmsProducerRuntimeIndex OBJECT-TYPE
      SYNTAX      DisplayString (SIZE (1..16))
      MAX-ACCESS  read-only
      STATUS      current
      DESCRIPTION "Unique value directed from ObjectName which is used as table index"
      ::= { jmsProducerRuntimeEntry 1  }
   
   
   jmsProducerRuntimeObjectName OBJECT-TYPE
      SYNTAX      DisplayString (SIZE (1..256))
      MAX-ACCESS  read-only
      STATUS      current
      DESCRIPTION "JMX-standard MBean name"
      ::= { jmsProducerRuntimeEntry 5  }
   
   
   jmsProducerRuntimeType OBJECT-TYPE
      SYNTAX      DisplayString (SIZE (1..64))
      MAX-ACCESS  read-only
      STATUS      current
      DESCRIPTION "Returns the type of the MBean. "
      ::= { jmsProducerRuntimeEntry 10  }
   
   
   jmsProducerRuntimeName OBJECT-TYPE
      SYNTAX      DisplayString (SIZE (1..64))
      MAX-ACCESS  read-only
      STATUS      current
      DESCRIPTION "The name of this configuration. WebLogic Server uses an MBean to implement and persist the configuration. "
      ::= { jmsProducerRuntimeEntry 15  }
   
   
   jmsProducerRuntimeParent OBJECT-TYPE
      SYNTAX      DisplayString (SIZE (1..256))
      MAX-ACCESS  read-only
      STATUS      current
      DESCRIPTION "BEA-proprietary Parent object's identification, with syntax
      <type>:<name>"
      ::= { jmsProducerRuntimeEntry 20  }
   
   
   jmsProducerRuntimeMessagesPendingCount OBJECT-TYPE
      SYNTAX      Counter64
      MAX-ACCESS  read-only
      STATUS      current
      DESCRIPTION "The number of messages pending (uncommitted and unacknowledged) by this producer. "
      ::= { jmsProducerRuntimeEntry 25  }
   
   
   jmsProducerRuntimeMessagesSentCount OBJECT-TYPE
      SYNTAX      Counter64
      MAX-ACCESS  read-only
      STATUS      current
      DESCRIPTION "The number of messages sent by this producer since the last reset. "
      ::= { jmsProducerRuntimeEntry 30  }
   
   
   jmsProducerRuntimeBytesPendingCount OBJECT-TYPE
      SYNTAX      Counter64
      MAX-ACCESS  read-only
      STATUS      current
      DESCRIPTION "The number of bytes pending (uncommitted and unacknowledged) by this producer. "
      ::= { jmsProducerRuntimeEntry 35  }
   
   
   jmsProducerRuntimeBytesSentCount OBJECT-TYPE
      SYNTAX      Counter64
      MAX-ACCESS  read-only
      STATUS      current
      DESCRIPTION "The number of bytes sent by this producer since the last reset. "
      ::= { jmsProducerRuntimeEntry 40  }
   
   
   jmsPooledConnectionRuntimeTable OBJECT-TYPE
      SYNTAX      SEQUENCE OF JmsPooledConnectionRuntimeEntry
      MAX-ACCESS  not-accessible
      STATUS      current
      DESCRIPTION "This class is used for monitoring pooled JMS connections. A pooled JMS connection is a session pool used by EJBs and servlets that use a resource-reference element in their EJB or Servlet deployment descriptor to define their JMS connection factories. "
      ::= { wls 231  }
      
   
   jmsPooledConnectionRuntimeEntry OBJECT-TYPE
      SYNTAX      JmsPooledConnectionRuntimeEntry
      MAX-ACCESS  not-accessible
      STATUS      current
      DESCRIPTION "Entry of jmsPooledConnectionRuntimeTable"
      INDEX { jmsPooledConnectionRuntimeIndex}
      ::= { jmsPooledConnectionRuntimeTable 1 }
      
   JmsPooledConnectionRuntimeEntry ::=
      SEQUENCE
      {
         jmsPooledConnectionRuntimeIndex DisplayString,
         jmsPooledConnectionRuntimeObjectName DisplayString,
         jmsPooledConnectionRuntimeType DisplayString,
         jmsPooledConnectionRuntimeName DisplayString,
         jmsPooledConnectionRuntimeParent DisplayString,
         jmsPooledConnectionRuntimeAverageReserved INTEGER,
         jmsPooledConnectionRuntimeCreationDelayTime INTEGER,
         jmsPooledConnectionRuntimeCurrCapacity INTEGER,
         jmsPooledConnectionRuntimeHighestNumAvailable INTEGER,
         jmsPooledConnectionRuntimeHighestNumReserved INTEGER,
         jmsPooledConnectionRuntimeNumAvailable INTEGER,
         jmsPooledConnectionRuntimeHighestNumWaiters Counter32,
         jmsPooledConnectionRuntimeHighestWaitSeconds INTEGER,
         jmsPooledConnectionRuntimeMaxCapacity INTEGER,
         jmsPooledConnectionRuntimeNumConnectionObjects INTEGER,
         jmsPooledConnectionRuntimeNumFailuresToRefresh INTEGER,
         jmsPooledConnectionRuntimeNumLeaked INTEGER,
         jmsPooledConnectionRuntimeNumReserved INTEGER,
         jmsPooledConnectionRuntimeNumUnavailable INTEGER,
         jmsPooledConnectionRuntimeNumWaiters INTEGER,
         jmsPooledConnectionRuntimeTotalNumAllocated INTEGER,
         jmsPooledConnectionRuntimeTotalNumDestroyed INTEGER,
         jmsPooledConnectionRuntimeHighestNumUnavailable INTEGER
      }
      
   
   jmsPooledConnectionRuntimeIndex OBJECT-TYPE
      SYNTAX      DisplayString (SIZE (1..16))
      MAX-ACCESS  read-only
      STATUS      current
      DESCRIPTION "Unique value directed from ObjectName which is used as table index"
      ::= { jmsPooledConnectionRuntimeEntry 1  }
   
   
   jmsPooledConnectionRuntimeObjectName OBJECT-TYPE
      SYNTAX      DisplayString (SIZE (1..256))
      MAX-ACCESS  read-only
      STATUS      current
      DESCRIPTION "JMX-standard MBean name"
      ::= { jmsPooledConnectionRuntimeEntry 5  }
   
   
   jmsPooledConnectionRuntimeType OBJECT-TYPE
      SYNTAX      DisplayString (SIZE (1..64))
      MAX-ACCESS  read-only
      STATUS      current
      DESCRIPTION "Returns the type of the MBean. "
      ::= { jmsPooledConnectionRuntimeEntry 10  }
   
   
   jmsPooledConnectionRuntimeName OBJECT-TYPE
      SYNTAX      DisplayString (SIZE (1..64))
      MAX-ACCESS  read-only
      STATUS      current
      DESCRIPTION "The name of this configuration. WebLogic Server uses an MBean to implement and persist the configuration. "
      ::= { jmsPooledConnectionRuntimeEntry 15  }
   
   
   jmsPooledConnectionRuntimeParent OBJECT-TYPE
      SYNTAX      DisplayString (SIZE (1..256))
      MAX-ACCESS  read-only
      STATUS      current
      DESCRIPTION "BEA-proprietary Parent object's identification, with syntax
      <type>:<name>"
      ::= { jmsPooledConnectionRuntimeEntry 20  }
   
   
   jmsPooledConnectionRuntimeAverageReserved OBJECT-TYPE
      SYNTAX      INTEGER
      MAX-ACCESS  read-only
      STATUS      current
      DESCRIPTION "The average number of JMS sessions that have been in use in this instance of the session pool since it was instantiated. This generally happens when an EJB or servlet is deployed that requires the session pool. "
      ::= { jmsPooledConnectionRuntimeEntry 21  }
   
   
   jmsPooledConnectionRuntimeCreationDelayTime OBJECT-TYPE
      SYNTAX      INTEGER
      MAX-ACCESS  read-only
      STATUS      current
      DESCRIPTION "The average amount of time that it takes to create each JMS session in the session pool. "
      ::= { jmsPooledConnectionRuntimeEntry 22  }
   
   
   jmsPooledConnectionRuntimeCurrCapacity OBJECT-TYPE
      SYNTAX      INTEGER
      MAX-ACCESS  read-only
      STATUS      current
      DESCRIPTION "The current capacity of the session pool, which is always less than or equal to the maximum capacity of JMS sessions. "
      ::= { jmsPooledConnectionRuntimeEntry 23  }
   
   
   jmsPooledConnectionRuntimeHighestNumAvailable OBJECT-TYPE
      SYNTAX      INTEGER
      MAX-ACCESS  read-only
      STATUS      current
      DESCRIPTION "The highest number of available JMS sessions in this instance of the session pool since it was instantiated. "
      ::= { jmsPooledConnectionRuntimeEntry 24  }
   
   
   jmsPooledConnectionRuntimeHighestNumReserved OBJECT-TYPE
      SYNTAX      INTEGER
      MAX-ACCESS  read-only
      STATUS      current
      DESCRIPTION "The highest number of concurrent JMS sessions reserved for this instance of the session pool since it was instantiated. "
      ::= { jmsPooledConnectionRuntimeEntry 25  }
   
   
   jmsPooledConnectionRuntimeNumAvailable OBJECT-TYPE
      SYNTAX      INTEGER
      MAX-ACCESS  read-only
      STATUS      current
      DESCRIPTION "The number of available JMS sessions in the session pool that are not currently in use. "
      ::= { jmsPooledConnectionRuntimeEntry 26  }
   
   
   jmsPooledConnectionRuntimeHighestNumWaiters OBJECT-TYPE
      SYNTAX      Counter32
      MAX-ACCESS  read-only
      STATUS      current
      DESCRIPTION "The highest number of threads waiting to retrieve a JMS session in this instance of the session pool since it was instantiated. "
      ::= { jmsPooledConnectionRuntimeEntry 27  }
   
   
   jmsPooledConnectionRuntimeHighestWaitSeconds OBJECT-TYPE
      SYNTAX      INTEGER
      MAX-ACCESS  read-only
      STATUS      current
      DESCRIPTION "The highest number of seconds that an application waited to retrieve a JMS session in this instance of the session pool since it was instantiated. "
      ::= { jmsPooledConnectionRuntimeEntry 28  }
   
   
   jmsPooledConnectionRuntimeMaxCapacity OBJECT-TYPE
      SYNTAX      INTEGER
      MAX-ACCESS  read-only
      STATUS      current
      DESCRIPTION "The maximum number of JMS sessions that can be allocated using the session pool. "
      ::= { jmsPooledConnectionRuntimeEntry 29  }
   
   
   jmsPooledConnectionRuntimeNumConnectionObjects OBJECT-TYPE
      SYNTAX      INTEGER
      MAX-ACCESS  read-only
      STATUS      current
      DESCRIPTION "The number of JMS connections that back this session pool. This value may be greater than one if different sessions were created using different combinations of a username and password to contact the JMS server. "
      ::= { jmsPooledConnectionRuntimeEntry 30  }
   
   
   jmsPooledConnectionRuntimeNumFailuresToRefresh OBJECT-TYPE
      SYNTAX      INTEGER
      MAX-ACCESS  read-only
      STATUS      current
      DESCRIPTION "The number of failed attempts to create a JMS session in the session pool. "
      ::= { jmsPooledConnectionRuntimeEntry 31  }
   
   
   jmsPooledConnectionRuntimeNumLeaked OBJECT-TYPE
      SYNTAX      INTEGER
      MAX-ACCESS  read-only
      STATUS      current
      DESCRIPTION "The number of JMS sessions that were removed from the session pool, but were not returned. "
      ::= { jmsPooledConnectionRuntimeEntry 32  }
   
   
   jmsPooledConnectionRuntimeNumReserved OBJECT-TYPE
      SYNTAX      INTEGER
      MAX-ACCESS  read-only
      STATUS      current
      DESCRIPTION "The number of JMS sessions that are currently in use. "
      ::= { jmsPooledConnectionRuntimeEntry 33  }
   
   
   jmsPooledConnectionRuntimeNumUnavailable OBJECT-TYPE
      SYNTAX      INTEGER
      MAX-ACCESS  read-only
      STATUS      current
      DESCRIPTION "The number of JMS sessions in the session pool that are not currently usable for some reason. "
      ::= { jmsPooledConnectionRuntimeEntry 34  }
   
   
   jmsPooledConnectionRuntimeNumWaiters OBJECT-TYPE
      SYNTAX      INTEGER
      MAX-ACCESS  read-only
      STATUS      current
      DESCRIPTION "The number of threads waiting to retrieve a JMS session from the session pool. "
      ::= { jmsPooledConnectionRuntimeEntry 35  }
   
   
   jmsPooledConnectionRuntimeTotalNumAllocated OBJECT-TYPE
      SYNTAX      INTEGER
      MAX-ACCESS  read-only
      STATUS      current
      DESCRIPTION "The total number of JMS sessions allocated by this session pool in this instance of the session pool since it was instantiated. "
      ::= { jmsPooledConnectionRuntimeEntry 36  }
   
   
   jmsPooledConnectionRuntimeTotalNumDestroyed OBJECT-TYPE
      SYNTAX      INTEGER
      MAX-ACCESS  read-only
      STATUS      current
      DESCRIPTION "The total number of JMS sessions that were created and then destroyed in this instance of the session pool since it was instantiated. "
      ::= { jmsPooledConnectionRuntimeEntry 37  }
   
   
   jmsPooledConnectionRuntimeHighestNumUnavailable OBJECT-TYPE
      SYNTAX      INTEGER
      MAX-ACCESS  read-only
      STATUS      current
      DESCRIPTION "The highest number of unusable JMS sessions in this instance of the session pool since it was instantiated. "
      ::= { jmsPooledConnectionRuntimeEntry 38  }
   
   
   jmsRuntimeTable OBJECT-TYPE
      SYNTAX      SEQUENCE OF JmsRuntimeEntry
      MAX-ACCESS  not-accessible
      STATUS      current
      DESCRIPTION "This class is used for monitoring a WebLogic JMS service. "
      ::= { wls 240  }
      
   
   jmsRuntimeEntry OBJECT-TYPE
      SYNTAX      JmsRuntimeEntry
      MAX-ACCESS  not-accessible
      STATUS      current
      DESCRIPTION "Entry of jmsRuntimeTable"
      INDEX { jmsRuntimeIndex}
      ::= { jmsRuntimeTable 1 }
      
   JmsRuntimeEntry ::=
      SEQUENCE
      {
         jmsRuntimeIndex      DisplayString,
         jmsRuntimeObjectName DisplayString,
         jmsRuntimeType       DisplayString,
         jmsRuntimeName       DisplayString,
         jmsRuntimeParent     DisplayString,
         jmsRuntimeConnectionsCurrentCount Counter64,
         jmsRuntimeConnectionsHighCount Counter64,
         jmsRuntimeConnectionsTotalCount Counter64,
         jmsRuntimeJMSServersCurrentCount Counter64,
         jmsRuntimeJMSServersHighCount Counter64,
         jmsRuntimeJMSServersTotalCount Counter64,
         jmsRuntimeHealthState OCTET STRING
      }
      
   
   jmsRuntimeIndex OBJECT-TYPE
      SYNTAX      DisplayString (SIZE (1..16))
      MAX-ACCESS  read-only
      STATUS      current
      DESCRIPTION "Unique value directed from ObjectName which is used as table index"
      ::= { jmsRuntimeEntry 1  }
   
   
   jmsRuntimeObjectName OBJECT-TYPE
      SYNTAX      DisplayString (SIZE (1..256))
      MAX-ACCESS  read-only
      STATUS      current
      DESCRIPTION "JMX-standard MBean name"
      ::= { jmsRuntimeEntry 5  }
   
   
   jmsRuntimeType OBJECT-TYPE
      SYNTAX      DisplayString (SIZE (1..64))
      MAX-ACCESS  read-only
      STATUS      current
      DESCRIPTION "Returns the type of the MBean. "
      ::= { jmsRuntimeEntry 10  }
   
   
   jmsRuntimeName OBJECT-TYPE
      SYNTAX      DisplayString (SIZE (1..64))
      MAX-ACCESS  read-only
      STATUS      current
      DESCRIPTION "The name of this configuration. WebLogic Server uses an MBean to implement and persist the configuration. "
      ::= { jmsRuntimeEntry 15  }
   
   
   jmsRuntimeParent OBJECT-TYPE
      SYNTAX      DisplayString (SIZE (1..256))
      MAX-ACCESS  read-only
      STATUS      current
      DESCRIPTION "BEA-proprietary Parent object's identification, with syntax
      <type>:<name>"
      ::= { jmsRuntimeEntry 20  }
   
   
   jmsRuntimeConnectionsCurrentCount OBJECT-TYPE
      SYNTAX      Counter64
      MAX-ACCESS  read-only
      STATUS      current
      DESCRIPTION "The current number of connections to WebLogic Server server. "
      ::= { jmsRuntimeEntry 30  }
   
   
   jmsRuntimeConnectionsHighCount OBJECT-TYPE
      SYNTAX      Counter64
      MAX-ACCESS  read-only
      STATUS      current
      DESCRIPTION "The highest number of connections to this WebLogic Server since the last reset. "
      ::= { jmsRuntimeEntry 35  }
   
   
   jmsRuntimeConnectionsTotalCount OBJECT-TYPE
      SYNTAX      Counter64
      MAX-ACCESS  read-only
      STATUS      current
      DESCRIPTION "The total number of connections made to this WebLogic Server since the last reset. "
      ::= { jmsRuntimeEntry 40  }
   
   
   jmsRuntimeJMSServersCurrentCount OBJECT-TYPE
      SYNTAX      Counter64
      MAX-ACCESS  read-only
      STATUS      current
      DESCRIPTION "The current number of JMS servers that are deployed on this WebLogic Server instance. "
      ::= { jmsRuntimeEntry 50  }
   
   
   jmsRuntimeJMSServersHighCount OBJECT-TYPE
      SYNTAX      Counter64
      MAX-ACCESS  read-only
      STATUS      current
      DESCRIPTION "The highest number of JMS servers that were deployed on this WebLogic Server instance since this server was started. "
      ::= { jmsRuntimeEntry 55  }
   
   
   jmsRuntimeJMSServersTotalCount OBJECT-TYPE
      SYNTAX      Counter64
      MAX-ACCESS  read-only
      STATUS      current
      DESCRIPTION "The total number of JMS servers that were deployed on this WebLogic Server instance since this server was started. "
      ::= { jmsRuntimeEntry 60  }
   
   
   jmsRuntimeHealthState OBJECT-TYPE
      SYNTAX      OCTET STRING
      MAX-ACCESS  read-only
      STATUS      current
      DESCRIPTION "The health state of this JMS service. "
      ::= { jmsRuntimeEntry 61  }
   
   
   jmsServerRuntimeTable OBJECT-TYPE
      SYNTAX      SEQUENCE OF JmsServerRuntimeEntry
      MAX-ACCESS  not-accessible
      STATUS      current
      DESCRIPTION "This class is used for monitoring a WebLogic JMS server. "
      ::= { wls 250  }
      
   
   jmsServerRuntimeEntry OBJECT-TYPE
      SYNTAX      JmsServerRuntimeEntry
      MAX-ACCESS  not-accessible
      STATUS      current
      DESCRIPTION "Entry of jmsServerRuntimeTable"
      INDEX { jmsServerRuntimeIndex}
      ::= { jmsServerRuntimeTable 1 }
      
   JmsServerRuntimeEntry ::=
      SEQUENCE
      {
         jmsServerRuntimeIndex DisplayString,
         jmsServerRuntimeObjectName DisplayString,
         jmsServerRuntimeType DisplayString,
         jmsServerRuntimeName DisplayString,
         jmsServerRuntimeParent DisplayString,
         jmsServerRuntimeSessionPoolsCurrentCount Counter64,
         jmsServerRuntimeSessionPoolsHighCount Counter64,
         jmsServerRuntimeSessionPoolsTotalCount Counter64,
         jmsServerRuntimeDestinationsCurrentCount Counter64,
         jmsServerRuntimeDestinationsHighCount Counter64,
         jmsServerRuntimeDestinationsTotalCount Counter64,
         jmsServerRuntimeMessagesCurrentCount Counter64,
         jmsServerRuntimeMessagesPendingCount Counter64,
         jmsServerRuntimeMessagesHighCount Counter64,
         jmsServerRuntimeMessagesReceivedCount Counter64,
         jmsServerRuntimeMessagesThresholdTime Counter64,
         jmsServerRuntimeBytesCurrentCount Counter64,
         jmsServerRuntimeBytesPendingCount Counter64,
         jmsServerRuntimeBytesHighCount Counter64,
         jmsServerRuntimeBytesReceivedCount Counter64,
         jmsServerRuntimeBytesThresholdTime Counter64,
         jmsServerRuntimeMessagesPagedInTotalCount INTEGER,
         jmsServerRuntimeProductionPaused OCTET STRING,
         jmsServerRuntimeInsertionPaused OCTET STRING,
         jmsServerRuntimeConsumptionPausedState OCTET STRING,
         jmsServerRuntimeConsumptionPaused OCTET STRING,
         jmsServerRuntimeBytesPageableCurrentCount Counter64,
         jmsServerRuntimeMessagesPagedOutTotalCount INTEGER,
         jmsServerRuntimeInsertionPausedState OCTET STRING,
         jmsServerRuntimeMessagesPageableCurrentCount INTEGER,
         jmsServerRuntimeProductionPausedState OCTET STRING,
         jmsServerRuntimeBytesPagedOutTotalCount Counter64,
         jmsServerRuntimeBytesPagedInTotalCount Counter64,
         jmsServerRuntimeTransactions OCTET STRING,
         jmsServerRuntimePendingTransactions OCTET STRING,
         jmsServerRuntimePagingAllocatedWindowBufferBytes Counter64,
         jmsServerRuntimePagingPhysicalWriteCount Counter64,
         jmsServerRuntimePagingAllocatedIoBufferBytes Counter64,
         jmsServerRuntimeHealthState OCTET STRING
      }
      
   
   jmsServerRuntimeIndex OBJECT-TYPE
      SYNTAX      DisplayString (SIZE (1..16))
      MAX-ACCESS  read-only
      STATUS      current
      DESCRIPTION "Unique value directed from ObjectName which is used as table index"
      ::= { jmsServerRuntimeEntry 1  }
   
   
   jmsServerRuntimeObjectName OBJECT-TYPE
      SYNTAX      DisplayString (SIZE (1..256))
      MAX-ACCESS  read-only
      STATUS      current
      DESCRIPTION "JMX-standard MBean name"
      ::= { jmsServerRuntimeEntry 5  }
   
   
   jmsServerRuntimeType OBJECT-TYPE
      SYNTAX      DisplayString (SIZE (1..64))
      MAX-ACCESS  read-only
      STATUS      current
      DESCRIPTION "Returns the type of the MBean. "
      ::= { jmsServerRuntimeEntry 10  }
   
   
   jmsServerRuntimeName OBJECT-TYPE
      SYNTAX      DisplayString (SIZE (1..64))
      MAX-ACCESS  read-only
      STATUS      current
      DESCRIPTION "The name of this configuration. WebLogic Server uses an MBean to implement and persist the configuration. "
      ::= { jmsServerRuntimeEntry 15  }
   
   
   jmsServerRuntimeParent OBJECT-TYPE
      SYNTAX      DisplayString (SIZE (1..256))
      MAX-ACCESS  read-only
      STATUS      current
      DESCRIPTION "BEA-proprietary Parent object's identification, with syntax
      <type>:<name>"
      ::= { jmsServerRuntimeEntry 20  }
   
   
   jmsServerRuntimeSessionPoolsCurrentCount OBJECT-TYPE
      SYNTAX      Counter64
      MAX-ACCESS  read-only
      STATUS      current
      DESCRIPTION "The current number of session pools instantiated on this JMS server. "
      ::= { jmsServerRuntimeEntry 30  }
   
   
   jmsServerRuntimeSessionPoolsHighCount OBJECT-TYPE
      SYNTAX      Counter64
      MAX-ACCESS  read-only
      STATUS      current
      DESCRIPTION "The peak number of session pools instantiated on this JMS server since the last reset. "
      ::= { jmsServerRuntimeEntry 35  }
   
   
   jmsServerRuntimeSessionPoolsTotalCount OBJECT-TYPE
      SYNTAX      Counter64
      MAX-ACCESS  read-only
      STATUS      current
      DESCRIPTION "The number of session pools instantiated on this JMS server since the last reset. "
      ::= { jmsServerRuntimeEntry 40  }
   
   
   jmsServerRuntimeDestinationsCurrentCount OBJECT-TYPE
      SYNTAX      Counter64
      MAX-ACCESS  read-only
      STATUS      current
      DESCRIPTION "The current number of destinations for this JMS server. "
      ::= { jmsServerRuntimeEntry 50  }
   
   
   jmsServerRuntimeDestinationsHighCount OBJECT-TYPE
      SYNTAX      Counter64
      MAX-ACCESS  read-only
      STATUS      current
      DESCRIPTION "The peak number of destinations on this JMS server since the last reset. "
      ::= { jmsServerRuntimeEntry 55  }
   
   
   jmsServerRuntimeDestinationsTotalCount OBJECT-TYPE
      SYNTAX      Counter64
      MAX-ACCESS  read-only
      STATUS      current
      DESCRIPTION "The number of destinations instantiated on this JMS server since the last reset. "
      ::= { jmsServerRuntimeEntry 60  }
   
   
   jmsServerRuntimeMessagesCurrentCount OBJECT-TYPE
      SYNTAX      Counter64
      MAX-ACCESS  read-only
      STATUS      current
      DESCRIPTION "The current number of messages stored on this JMS server. This number does not include the pending messages. "
      ::= { jmsServerRuntimeEntry 65  }
   
   
   jmsServerRuntimeMessagesPendingCount OBJECT-TYPE
      SYNTAX      Counter64
      MAX-ACCESS  read-only
      STATUS      current
      DESCRIPTION "The current number of messages pending (unacknowledged or uncommitted) stored on this JMS server.  Pending messages are over and above the current number of messages. "
      ::= { jmsServerRuntimeEntry 70  }
   
   
   jmsServerRuntimeMessagesHighCount OBJECT-TYPE
      SYNTAX      Counter64
      MAX-ACCESS  read-only
      STATUS      current
      DESCRIPTION "The peak number of messages stored in the JMS server since the last reset. "
      ::= { jmsServerRuntimeEntry 75  }
   
   
   jmsServerRuntimeMessagesReceivedCount OBJECT-TYPE
      SYNTAX      Counter64
      MAX-ACCESS  read-only
      STATUS      current
      DESCRIPTION "The number of messages received on this destination since the last reset. "
      ::= { jmsServerRuntimeEntry 80  }
   
   
   jmsServerRuntimeMessagesThresholdTime OBJECT-TYPE
      SYNTAX      Counter64
      MAX-ACCESS  read-only
      STATUS      current
      DESCRIPTION "The amount of time in the threshold condition since the last reset. "
      ::= { jmsServerRuntimeEntry 85  }
   
   
   jmsServerRuntimeBytesCurrentCount OBJECT-TYPE
      SYNTAX      Counter64
      MAX-ACCESS  read-only
      STATUS      current
      DESCRIPTION "The current number of bytes stored on this JMS server.  This number does not include the pending bytes. "
      ::= { jmsServerRuntimeEntry 90  }
   
   
   jmsServerRuntimeBytesPendingCount OBJECT-TYPE
      SYNTAX      Counter64
      MAX-ACCESS  read-only
      STATUS      current
      DESCRIPTION "The current number of bytes pending (unacknowledged or uncommitted) stored on this JMS server.  Pending bytes are over and above the current number of bytes. "
      ::= { jmsServerRuntimeEntry 95  }
   
   
   jmsServerRuntimeBytesHighCount OBJECT-TYPE
      SYNTAX      Counter64
      MAX-ACCESS  read-only
      STATUS      current
      DESCRIPTION "The peak number of bytes stored in the JMS server since the last reset. "
      ::= { jmsServerRuntimeEntry 100  }
   
   
   jmsServerRuntimeBytesReceivedCount OBJECT-TYPE
      SYNTAX      Counter64
      MAX-ACCESS  read-only
      STATUS      current
      DESCRIPTION "The number of bytes received on this JMS server since the last reset. "
      ::= { jmsServerRuntimeEntry 105  }
   
   
   jmsServerRuntimeBytesThresholdTime OBJECT-TYPE
      SYNTAX      Counter64
      MAX-ACCESS  read-only
      STATUS      current
      DESCRIPTION "The amount of time in the threshold condition since the last reset. "
      ::= { jmsServerRuntimeEntry 110  }
   
   
   jmsServerRuntimeMessagesPagedInTotalCount OBJECT-TYPE
      SYNTAX      INTEGER
      MAX-ACCESS  read-only
      STATUS      current
      DESCRIPTION "Return the total number of messages that were read from the paging directory since the JMS server was started. "
      ::= { jmsServerRuntimeEntry 111  }
   
   
   jmsServerRuntimeProductionPaused OBJECT-TYPE
      SYNTAX      OCTET STRING
      MAX-ACCESS  read-only
      STATUS      current
      DESCRIPTION "Returns the current production paused state of the JMSServer as boolean value. "
      ::= { jmsServerRuntimeEntry 112  }
   
   
   jmsServerRuntimeInsertionPaused OBJECT-TYPE
      SYNTAX      OCTET STRING
      MAX-ACCESS  read-only
      STATUS      current
      DESCRIPTION "Returns the current insertion paused state of the JMSServer as boolean value. "
      ::= { jmsServerRuntimeEntry 113  }
   
   
   jmsServerRuntimeConsumptionPausedState OBJECT-TYPE
      SYNTAX      OCTET STRING
      MAX-ACCESS  read-only
      STATUS      current
      DESCRIPTION "Returns the current consumption paused state of the JMSServer as string value. "
      ::= { jmsServerRuntimeEntry 114  }
   
   
   jmsServerRuntimeConsumptionPaused OBJECT-TYPE
      SYNTAX      OCTET STRING
      MAX-ACCESS  read-only
      STATUS      current
      DESCRIPTION "Returns the current consumption paused state of the JMSServer as boolean value. "
      ::= { jmsServerRuntimeEntry 115  }
   
   
   jmsServerRuntimeBytesPageableCurrentCount OBJECT-TYPE
      SYNTAX      Counter64
      MAX-ACCESS  read-only
      STATUS      current
      DESCRIPTION "Return the total number of bytes in all the messages that are currently available to be paged out, but which have not yet been paged out. The JMS server attempts to keep this number smaller than the 'MessageBufferSize' parameter. "
      ::= { jmsServerRuntimeEntry 116  }
   
   
   jmsServerRuntimeMessagesPagedOutTotalCount OBJECT-TYPE
      SYNTAX      INTEGER
      MAX-ACCESS  read-only
      STATUS      current
      DESCRIPTION "Return the total number of messages that were written to the paging directory since the JMS server was started. "
      ::= { jmsServerRuntimeEntry 117  }
   
   
   jmsServerRuntimeInsertionPausedState OBJECT-TYPE
      SYNTAX      OCTET STRING
      MAX-ACCESS  read-only
      STATUS      current
      DESCRIPTION "Returns the current insertion paused state of the JMSServer as string value. "
      ::= { jmsServerRuntimeEntry 118  }
   
   
   jmsServerRuntimeMessagesPageableCurrentCount OBJECT-TYPE
      SYNTAX      INTEGER
      MAX-ACCESS  read-only
      STATUS      current
      DESCRIPTION "Return the number of messages that are currently available for paging in this JMS server but have not yet been paged out. Note that due to internal implementation details, this count may be zero even if 'PageableByteCurrentCount' is zero. "
      ::= { jmsServerRuntimeEntry 119  }
   
   
   jmsServerRuntimeProductionPausedState OBJECT-TYPE
      SYNTAX      OCTET STRING
      MAX-ACCESS  read-only
      STATUS      current
      DESCRIPTION "Returns the current production paused state of the JMSServer as string value. "
      ::= { jmsServerRuntimeEntry 120  }
   
   
   jmsServerRuntimeBytesPagedOutTotalCount OBJECT-TYPE
      SYNTAX      Counter64
      MAX-ACCESS  read-only
      STATUS      current
      DESCRIPTION "Return the total number of bytes that were written to the paging directory since the JMS server was started. "
      ::= { jmsServerRuntimeEntry 121  }
   
   
   jmsServerRuntimeBytesPagedInTotalCount OBJECT-TYPE
      SYNTAX      Counter64
      MAX-ACCESS  read-only
      STATUS      current
      DESCRIPTION "Return the total number of bytes that were read from the paging directory since the JMS server was started. "
      ::= { jmsServerRuntimeEntry 122  }
   
   
   jmsServerRuntimeTransactions OBJECT-TYPE
      SYNTAX      OCTET STRING
      MAX-ACCESS  read-only
      STATUS      current
      DESCRIPTION "Returns an array of Xids representing transaction branches that exist on this JMS server in any state. "
      ::= { jmsServerRuntimeEntry 123  }
   
   
   jmsServerRuntimePendingTransactions OBJECT-TYPE
      SYNTAX      OCTET STRING
      MAX-ACCESS  read-only
      STATUS      current
      DESCRIPTION "Returns an array of Xids representing transaction branches that exist onthis JMS server in the pending state, i.e. branches that have been prepared by the transaction manager but not yet committed or rolled back. "
      ::= { jmsServerRuntimeEntry 124  }
   
   
   jmsServerRuntimePagingAllocatedWindowBufferBytes OBJECT-TYPE
      SYNTAX      Counter64
      MAX-ACCESS  read-only
      STATUS      current
      DESCRIPTION "See PersistentStoreRuntimeMBean.AllocatedWindowBufferBytes "
      ::= { jmsServerRuntimeEntry 125  }
   
   
   jmsServerRuntimePagingPhysicalWriteCount OBJECT-TYPE
      SYNTAX      Counter64
      MAX-ACCESS  read-only
      STATUS      current
      DESCRIPTION "See PersistentStoreRuntimeMBean.PhysicalWriteCount "
      ::= { jmsServerRuntimeEntry 126  }
   
   
   jmsServerRuntimePagingAllocatedIoBufferBytes OBJECT-TYPE
      SYNTAX      Counter64
      MAX-ACCESS  read-only
      STATUS      current
      DESCRIPTION "See PersistentStoreRuntimeMBean.AllocatedIoBufferBytes "
      ::= { jmsServerRuntimeEntry 127  }
   
   
   jmsServerRuntimeHealthState OBJECT-TYPE
      SYNTAX      OCTET STRING
      MAX-ACCESS  read-only
      STATUS      current
      DESCRIPTION "The health state of this JMS server. "
      ::= { jmsServerRuntimeEntry 128  }
   
   
   jmsSessionPoolRuntimeTable OBJECT-TYPE
      SYNTAX      SEQUENCE OF JmsSessionPoolRuntimeEntry
      MAX-ACCESS  not-accessible
      STATUS      current
      DESCRIPTION "This class is used for monitoring a WebLogic JMS session pool. "
      ::= { wls 260  }
      
   
   jmsSessionPoolRuntimeEntry OBJECT-TYPE
      SYNTAX      JmsSessionPoolRuntimeEntry
      MAX-ACCESS  not-accessible
      STATUS      current
      DESCRIPTION "Entry of jmsSessionPoolRuntimeTable"
      INDEX { jmsSessionPoolRuntimeIndex}
      ::= { jmsSessionPoolRuntimeTable 1 }
      
   JmsSessionPoolRuntimeEntry ::=
      SEQUENCE
      {
         jmsSessionPoolRuntimeIndex DisplayString,
         jmsSessionPoolRuntimeObjectName DisplayString,
         jmsSessionPoolRuntimeType DisplayString,
         jmsSessionPoolRuntimeName DisplayString,
         jmsSessionPoolRuntimeParent DisplayString,
         jmsSessionPoolRuntimeConnectionConsumersCurrentCount Counter64,
         jmsSessionPoolRuntimeConnectionConsumersHighCount Counter64,
         jmsSessionPoolRuntimeConnectionConsumersTotalCount Counter64
      }
      
   
   jmsSessionPoolRuntimeIndex OBJECT-TYPE
      SYNTAX      DisplayString (SIZE (1..16))
      MAX-ACCESS  read-only
      STATUS      current
      DESCRIPTION "Unique value directed from ObjectName which is used as table index"
      ::= { jmsSessionPoolRuntimeEntry 1  }
   
   
   jmsSessionPoolRuntimeObjectName OBJECT-TYPE
      SYNTAX      DisplayString (SIZE (1..256))
      MAX-ACCESS  read-only
      STATUS      current
      DESCRIPTION "JMX-standard MBean name"
      ::= { jmsSessionPoolRuntimeEntry 5  }
   
   
   jmsSessionPoolRuntimeType OBJECT-TYPE
      SYNTAX      DisplayString (SIZE (1..64))
      MAX-ACCESS  read-only
      STATUS      current
      DESCRIPTION "Returns the type of the MBean. "
      ::= { jmsSessionPoolRuntimeEntry 10  }
   
   
   jmsSessionPoolRuntimeName OBJECT-TYPE
      SYNTAX      DisplayString (SIZE (1..64))
      MAX-ACCESS  read-only
      STATUS      current
      DESCRIPTION "The name of this configuration. WebLogic Server uses an MBean to implement and persist the configuration. "
      ::= { jmsSessionPoolRuntimeEntry 15  }
   
   
   jmsSessionPoolRuntimeParent OBJECT-TYPE
      SYNTAX      DisplayString (SIZE (1..256))
      MAX-ACCESS  read-only
      STATUS      current
      DESCRIPTION "BEA-proprietary Parent object's identification, with syntax
      <type>:<name>"
      ::= { jmsSessionPoolRuntimeEntry 20  }
   
   
   jmsSessionPoolRuntimeConnectionConsumersCurrentCount OBJECT-TYPE
      SYNTAX      Counter64
      MAX-ACCESS  read-only
      STATUS      current
      DESCRIPTION "The current number of connection consumers for this session pool. "
      ::= { jmsSessionPoolRuntimeEntry 35  }
   
   
   jmsSessionPoolRuntimeConnectionConsumersHighCount OBJECT-TYPE
      SYNTAX      Counter64
      MAX-ACCESS  read-only
      STATUS      current
      DESCRIPTION "The peak number of simultaneous connection consumers for this session pool. "
      ::= { jmsSessionPoolRuntimeEntry 40  }
   
   
   jmsSessionPoolRuntimeConnectionConsumersTotalCount OBJECT-TYPE
      SYNTAX      Counter64
      MAX-ACCESS  read-only
      STATUS      current
      DESCRIPTION "The total number of connection consumers made by this session pool since the last reset. "
      ::= { jmsSessionPoolRuntimeEntry 45  }
   
   
   jmsSessionRuntimeTable OBJECT-TYPE
      SYNTAX      SEQUENCE OF JmsSessionRuntimeEntry
      MAX-ACCESS  not-accessible
      STATUS      current
      DESCRIPTION "This class is used for monitoring a WebLogic JMS session. "
      ::= { wls 270  }
      
   
   jmsSessionRuntimeEntry OBJECT-TYPE
      SYNTAX      JmsSessionRuntimeEntry
      MAX-ACCESS  not-accessible
      STATUS      current
      DESCRIPTION "Entry of jmsSessionRuntimeTable"
      INDEX { jmsSessionRuntimeIndex}
      ::= { jmsSessionRuntimeTable 1 }
      
   JmsSessionRuntimeEntry ::=
      SEQUENCE
      {
         jmsSessionRuntimeIndex DisplayString,
         jmsSessionRuntimeObjectName DisplayString,
         jmsSessionRuntimeType DisplayString,
         jmsSessionRuntimeName DisplayString,
         jmsSessionRuntimeParent DisplayString,
         jmsSessionRuntimeConsumersCurrentCount Counter64,
         jmsSessionRuntimeConsumersHighCount Counter64,
         jmsSessionRuntimeConsumersTotalCount Counter64,
         jmsSessionRuntimeProducersCurrentCount Counter64,
         jmsSessionRuntimeProducersHighCount Counter64,
         jmsSessionRuntimeProducersTotalCount Counter64,
         jmsSessionRuntimeTransacted INTEGER,
         jmsSessionRuntimeAcknowledgeMode DisplayString,
         jmsSessionRuntimeMessagesPendingCount Counter64,
         jmsSessionRuntimeMessagesSentCount Counter64,
         jmsSessionRuntimeMessagesReceivedCount Counter64,
         jmsSessionRuntimeBytesPendingCount Counter64,
         jmsSessionRuntimeBytesSentCount Counter64,
         jmsSessionRuntimeBytesReceivedCount Counter64
      }
      
   
   jmsSessionRuntimeIndex OBJECT-TYPE
      SYNTAX      DisplayString (SIZE (1..16))
      MAX-ACCESS  read-only
      STATUS      current
      DESCRIPTION "Unique value directed from ObjectName which is used as table index"
      ::= { jmsSessionRuntimeEntry 1  }
   
   
   jmsSessionRuntimeObjectName OBJECT-TYPE
      SYNTAX      DisplayString (SIZE (1..256))
      MAX-ACCESS  read-only
      STATUS      current
      DESCRIPTION "JMX-standard MBean name"
      ::= { jmsSessionRuntimeEntry 5  }
   
   
   jmsSessionRuntimeType OBJECT-TYPE
      SYNTAX      DisplayString (SIZE (1..64))
      MAX-ACCESS  read-only
      STATUS      current
      DESCRIPTION "Returns the type of the MBean. "
      ::= { jmsSessionRuntimeEntry 10  }
   
   
   jmsSessionRuntimeName OBJECT-TYPE
      SYNTAX      DisplayString (SIZE (1..64))
      MAX-ACCESS  read-only
      STATUS      current
      DESCRIPTION "The name of this configuration. WebLogic Server uses an MBean to implement and persist the configuration. "
      ::= { jmsSessionRuntimeEntry 15  }
   
   
   jmsSessionRuntimeParent OBJECT-TYPE
      SYNTAX      DisplayString (SIZE (1..256))
      MAX-ACCESS  read-only
      STATUS      current
      DESCRIPTION "BEA-proprietary Parent object's identification, with syntax
      <type>:<name>"
      ::= { jmsSessionRuntimeEntry 20  }
   
   
   jmsSessionRuntimeConsumersCurrentCount OBJECT-TYPE
      SYNTAX      Counter64
      MAX-ACCESS  read-only
      STATUS      current
      DESCRIPTION "The current number of consumers for this session. "
      ::= { jmsSessionRuntimeEntry 30  }
   
   
   jmsSessionRuntimeConsumersHighCount OBJECT-TYPE
      SYNTAX      Counter64
      MAX-ACCESS  read-only
      STATUS      current
      DESCRIPTION "The peak number of consumers for this session since the last reset. "
      ::= { jmsSessionRuntimeEntry 35  }
   
   
   jmsSessionRuntimeConsumersTotalCount OBJECT-TYPE
      SYNTAX      Counter64
      MAX-ACCESS  read-only
      STATUS      current
      DESCRIPTION "The number of consumers instantiated by this session since the last reset. "
      ::= { jmsSessionRuntimeEntry 40  }
   
   
   jmsSessionRuntimeProducersCurrentCount OBJECT-TYPE
      SYNTAX      Counter64
      MAX-ACCESS  read-only
      STATUS      current
      DESCRIPTION "The current number of producers for this session. "
      ::= { jmsSessionRuntimeEntry 50  }
   
   
   jmsSessionRuntimeProducersHighCount OBJECT-TYPE
      SYNTAX      Counter64
      MAX-ACCESS  read-only
      STATUS      current
      DESCRIPTION "The peak number of producers for this session since the last reset. "
      ::= { jmsSessionRuntimeEntry 55  }
   
   
   jmsSessionRuntimeProducersTotalCount OBJECT-TYPE
      SYNTAX      Counter64
      MAX-ACCESS  read-only
      STATUS      current
      DESCRIPTION "The number of producers for this session since the last reset. "
      ::= { jmsSessionRuntimeEntry 60  }
   
   
   jmsSessionRuntimeTransacted OBJECT-TYPE
      SYNTAX      INTEGER
                  {
                     true(1),
                     false(2)
                  }
      
      MAX-ACCESS  read-only
      STATUS      current
      DESCRIPTION "Indicates whether the session is transacted. "
      ::= { jmsSessionRuntimeEntry 65  }
   
   
   jmsSessionRuntimeAcknowledgeMode OBJECT-TYPE
      SYNTAX      DisplayString (SIZE (1..32))
      MAX-ACCESS  read-only
      STATUS      current
      DESCRIPTION "The acknowledge mode as one of the following:   AUTO_ACKNOWLEDGE  CLIENT_ACKNOWLEDGE  DUPS_OK_ACKNOWLEDGE  NO_ACKNOWLEDGE  "
      ::= { jmsSessionRuntimeEntry 70  }
   
   
   jmsSessionRuntimeMessagesPendingCount OBJECT-TYPE
      SYNTAX      Counter64
      MAX-ACCESS  read-only
      STATUS      current
      DESCRIPTION "The number of messages pending (uncommitted and unacknowledged) for this session. "
      ::= { jmsSessionRuntimeEntry 75  }
   
   
   jmsSessionRuntimeMessagesSentCount OBJECT-TYPE
      SYNTAX      Counter64
      MAX-ACCESS  read-only
      STATUS      current
      DESCRIPTION "The number of bytes sent by this session since the last reset. "
      ::= { jmsSessionRuntimeEntry 80  }
   
   
   jmsSessionRuntimeMessagesReceivedCount OBJECT-TYPE
      SYNTAX      Counter64
      MAX-ACCESS  read-only
      STATUS      current
      DESCRIPTION "The number of messages received by this session since the last reset. "
      ::= { jmsSessionRuntimeEntry 85  }
   
   
   jmsSessionRuntimeBytesPendingCount OBJECT-TYPE
      SYNTAX      Counter64
      MAX-ACCESS  read-only
      STATUS      current
      DESCRIPTION "The number of bytes pending (uncommitted and unacknowledged) for this session. "
      ::= { jmsSessionRuntimeEntry 90  }
   
   
   jmsSessionRuntimeBytesSentCount OBJECT-TYPE
      SYNTAX      Counter64
      MAX-ACCESS  read-only
      STATUS      current
      DESCRIPTION "The number of bytes sent by this session since the last reset. "
      ::= { jmsSessionRuntimeEntry 95  }
   
   
   jmsSessionRuntimeBytesReceivedCount OBJECT-TYPE
      SYNTAX      Counter64
      MAX-ACCESS  read-only
      STATUS      current
      DESCRIPTION "The number of bytes received by this session since the last reset. "
      ::= { jmsSessionRuntimeEntry 100  }
   
   
   jmsComponentRuntimeTable OBJECT-TYPE
      SYNTAX      SEQUENCE OF JmsComponentRuntimeEntry
      MAX-ACCESS  not-accessible
      STATUS      current
      DESCRIPTION "This is the top level interface for all runtime information collected for an JMS module. "
      ::= { wls 271  }
      
   
   jmsComponentRuntimeEntry OBJECT-TYPE
      SYNTAX      JmsComponentRuntimeEntry
      MAX-ACCESS  not-accessible
      STATUS      current
      DESCRIPTION "Entry of jmsComponentRuntimeTable"
      INDEX { jmsComponentRuntimeIndex}
      ::= { jmsComponentRuntimeTable 1 }
      
   JmsComponentRuntimeEntry ::=
      SEQUENCE
      {
         jmsComponentRuntimeIndex DisplayString,
         jmsComponentRuntimeObjectName DisplayString,
         jmsComponentRuntimeType DisplayString,
         jmsComponentRuntimeName DisplayString,
         jmsComponentRuntimeParent DisplayString,
         jmsComponentRuntimeModuleId DisplayString,
         jmsComponentRuntimeDeploymentState INTEGER
      }
      
   
   jmsComponentRuntimeIndex OBJECT-TYPE
      SYNTAX      DisplayString (SIZE (1..16))
      MAX-ACCESS  read-only
      STATUS      current
      DESCRIPTION "Unique value directed from ObjectName which is used as table index"
      ::= { jmsComponentRuntimeEntry 1  }
   
   
   jmsComponentRuntimeObjectName OBJECT-TYPE
      SYNTAX      DisplayString (SIZE (1..256))
      MAX-ACCESS  read-only
      STATUS      current
      DESCRIPTION "JMX-standard MBean name"
      ::= { jmsComponentRuntimeEntry 5  }
   
   
   jmsComponentRuntimeType OBJECT-TYPE
      SYNTAX      DisplayString (SIZE (1..64))
      MAX-ACCESS  read-only
      STATUS      current
      DESCRIPTION "Returns the type of the MBean. "
      ::= { jmsComponentRuntimeEntry 10  }
   
   
   jmsComponentRuntimeName OBJECT-TYPE
      SYNTAX      DisplayString (SIZE (1..64))
      MAX-ACCESS  read-only
      STATUS      current
      DESCRIPTION "The name of this configuration. WebLogic Server uses an MBean to implement and persist the configuration. "
      ::= { jmsComponentRuntimeEntry 15  }
   
   
   jmsComponentRuntimeParent OBJECT-TYPE
      SYNTAX      DisplayString (SIZE (1..256))
      MAX-ACCESS  read-only
      STATUS      current
      DESCRIPTION "BEA-proprietary Parent object's identification, with syntax
      <type>:<name>"
      ::= { jmsComponentRuntimeEntry 20  }
   
   
   jmsComponentRuntimeModuleId OBJECT-TYPE
      SYNTAX      DisplayString (SIZE (1..256))
      MAX-ACCESS  read-only
      STATUS      current
      DESCRIPTION "Returns the identifier for this Component.  The identifier is unique within the application.  Typical modules will use the URI for their id.  Web Modules will return their context-root since the web-uri may not be unique within an EAR. "
      ::= { jmsComponentRuntimeEntry 25  }
   
   
   jmsComponentRuntimeDeploymentState OBJECT-TYPE
      SYNTAX      INTEGER
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jmsComponentRuntimeEntry 30  }
   
   
   joltConnectionPoolRuntimeTable OBJECT-TYPE
      SYNTAX      SEQUENCE OF JoltConnectionPoolRuntimeEntry
      MAX-ACCESS  not-accessible
      STATUS      current
      DESCRIPTION "This class is used for monitoring a WebLogic Jolt Connection Pool "
      ::= { wls 280  }
      
   
   joltConnectionPoolRuntimeEntry OBJECT-TYPE
      SYNTAX      JoltConnectionPoolRuntimeEntry
      MAX-ACCESS  not-accessible
      STATUS      current
      DESCRIPTION "Entry of joltConnectionPoolRuntimeTable"
      INDEX { joltConnectionPoolRuntimeIndex}
      ::= { joltConnectionPoolRuntimeTable 1 }
      
   JoltConnectionPoolRuntimeEntry ::=
      SEQUENCE
      {
         joltConnectionPoolRuntimeIndex DisplayString,
         joltConnectionPoolRuntimeObjectName DisplayString,
         joltConnectionPoolRuntimeType DisplayString,
         joltConnectionPoolRuntimeName DisplayString,
         joltConnectionPoolRuntimeParent DisplayString,
         joltConnectionPoolRuntimePoolName DisplayString,
         joltConnectionPoolRuntimeMaxCapacity INTEGER,
         joltConnectionPoolRuntimePoolState DisplayString,
         joltConnectionPoolRuntimeSecurityContextPropagation INTEGER
      }
      
   
   joltConnectionPoolRuntimeIndex OBJECT-TYPE
      SYNTAX      DisplayString (SIZE (1..16))
      MAX-ACCESS  read-only
      STATUS      current
      DESCRIPTION "Unique value directed from ObjectName which is used as table index"
      ::= { joltConnectionPoolRuntimeEntry 1  }
   
   
   joltConnectionPoolRuntimeObjectName OBJECT-TYPE
      SYNTAX      DisplayString (SIZE (1..256))
      MAX-ACCESS  read-only
      STATUS      current
      DESCRIPTION "JMX-standard MBean name"
      ::= { joltConnectionPoolRuntimeEntry 5  }
   
   
   joltConnectionPoolRuntimeType OBJECT-TYPE
      SYNTAX      DisplayString (SIZE (1..64))
      MAX-ACCESS  read-only
      STATUS      current
      DESCRIPTION "Returns the type of the MBean. "
      ::= { joltConnectionPoolRuntimeEntry 10  }
   
   
   joltConnectionPoolRuntimeName OBJECT-TYPE
      SYNTAX      DisplayString (SIZE (1..64))
      MAX-ACCESS  read-only
      STATUS      current
      DESCRIPTION "The name of this configuration. WebLogic Server uses an MBean to implement and persist the configuration. "
      ::= { joltConnectionPoolRuntimeEntry 15  }
   
   
   joltConnectionPoolRuntimeParent OBJECT-TYPE
      SYNTAX      DisplayString (SIZE (1..256))
      MAX-ACCESS  read-only
      STATUS      current
      DESCRIPTION "BEA-proprietary Parent object's identification, with syntax
      <type>:<name>"
      ::= { joltConnectionPoolRuntimeEntry 20  }
   
   
   joltConnectionPoolRuntimePoolName OBJECT-TYPE
      SYNTAX      DisplayString (SIZE (1..64))
      MAX-ACCESS  read-only
      STATUS      current
      DESCRIPTION "The configured name of this Jolt pool. "
      ::= { joltConnectionPoolRuntimeEntry 25  }
   
   
   joltConnectionPoolRuntimeMaxCapacity OBJECT-TYPE
      SYNTAX      INTEGER
      MAX-ACCESS  read-only
      STATUS      current
      DESCRIPTION "The maximum connections configured for this Jolt pool. "
      ::= { joltConnectionPoolRuntimeEntry 30  }
   
   
   joltConnectionPoolRuntimePoolState OBJECT-TYPE
      SYNTAX      DisplayString (SIZE (1..16))
      MAX-ACCESS  read-only
      STATUS      current
      DESCRIPTION "The pool state as one of 'Active' 'Suspended'. "
      ::= { joltConnectionPoolRuntimeEntry 35  }
   
   
   joltConnectionPoolRuntimeSecurityContextPropagation OBJECT-TYPE
      SYNTAX      INTEGER
                  {
                     true(1),
                     false(2)
                  }
      
      MAX-ACCESS  read-only
      STATUS      current
      DESCRIPTION "Indicates whether the security context is propagated. "
      ::= { joltConnectionPoolRuntimeEntry 40  }
   
   
   joltConnectionRuntimeTable OBJECT-TYPE
      SYNTAX      SEQUENCE OF JoltConnectionRuntimeEntry
      MAX-ACCESS  not-accessible
      STATUS      current
      DESCRIPTION "This class is used for monitoring individual WebLogic Jolt connections "
      ::= { wls 290  }
      
   
   joltConnectionRuntimeEntry OBJECT-TYPE
      SYNTAX      JoltConnectionRuntimeEntry
      MAX-ACCESS  not-accessible
      STATUS      current
      DESCRIPTION "Entry of joltConnectionRuntimeTable"
      INDEX { joltConnectionRuntimeIndex}
      ::= { joltConnectionRuntimeTable 1 }
      
   JoltConnectionRuntimeEntry ::=
      SEQUENCE
      {
         joltConnectionRuntimeIndex DisplayString,
         joltConnectionRuntimeObjectName DisplayString,
         joltConnectionRuntimeType DisplayString,
         joltConnectionRuntimeName DisplayString,
         joltConnectionRuntimeParent DisplayString,
         joltConnectionRuntimeAddress DisplayString,
         joltConnectionRuntimeLastAccessTime DisplayString,
         joltConnectionRuntimeAlive INTEGER,
         joltConnectionRuntimeRequestCount INTEGER,
         joltConnectionRuntimePendingRequestCount INTEGER,
         joltConnectionRuntimeErrorCount INTEGER,
         joltConnectionRuntimeInTransaction INTEGER
      }
      
   
   joltConnectionRuntimeIndex OBJECT-TYPE
      SYNTAX      DisplayString (SIZE (1..16))
      MAX-ACCESS  read-only
      STATUS      current
      DESCRIPTION "Unique value directed from ObjectName which is used as table index"
      ::= { joltConnectionRuntimeEntry 1  }
   
   
   joltConnectionRuntimeObjectName OBJECT-TYPE
      SYNTAX      DisplayString (SIZE (1..256))
      MAX-ACCESS  read-only
      STATUS      current
      DESCRIPTION "JMX-standard MBean name"
      ::= { joltConnectionRuntimeEntry 5  }
   
   
   joltConnectionRuntimeType OBJECT-TYPE
      SYNTAX      DisplayString (SIZE (1..64))
      MAX-ACCESS  read-only
      STATUS      current
      DESCRIPTION "Returns the type of the MBean. "
      ::= { joltConnectionRuntimeEntry 10  }
   
   
   joltConnectionRuntimeName OBJECT-TYPE
      SYNTAX      DisplayString (SIZE (1..64))
      MAX-ACCESS  read-only
      STATUS      current
      DESCRIPTION "The name of this configuration. WebLogic Server uses an MBean to implement and persist the configuration. "
      ::= { joltConnectionRuntimeEntry 15  }
   
   
   joltConnectionRuntimeParent OBJECT-TYPE
      SYNTAX      DisplayString (SIZE (1..256))
      MAX-ACCESS  read-only
      STATUS      current
      DESCRIPTION "BEA-proprietary Parent object's identification, with syntax
      <type>:<name>"
      ::= { joltConnectionRuntimeEntry 20  }
   
   
   joltConnectionRuntimeAddress OBJECT-TYPE
      SYNTAX      DisplayString (SIZE (1..256))
      MAX-ACCESS  read-only
      STATUS      current
      DESCRIPTION "The connection Address. "
      ::= { joltConnectionRuntimeEntry 25  }
   
   
   joltConnectionRuntimeLastAccessTime OBJECT-TYPE
      SYNTAX      DisplayString (SIZE (1..32))
      MAX-ACCESS  read-only
      STATUS      current
      DESCRIPTION "The Last Access Date and Time. "
      ::= { joltConnectionRuntimeEntry 30  }
   
   
   joltConnectionRuntimeAlive OBJECT-TYPE
      SYNTAX      INTEGER
                  {
                     true(1),
                     false(2)
                  }
      
      MAX-ACCESS  read-only
      STATUS      current
      DESCRIPTION "The Connection Alive indicator. "
      ::= { joltConnectionRuntimeEntry 35  }
   
   
   joltConnectionRuntimeRequestCount OBJECT-TYPE
      SYNTAX      INTEGER
      MAX-ACCESS  read-only
      STATUS      current
      DESCRIPTION "The Request Count. "
      ::= { joltConnectionRuntimeEntry 40  }
   
   
   joltConnectionRuntimePendingRequestCount OBJECT-TYPE
      SYNTAX      INTEGER
      MAX-ACCESS  read-only
      STATUS      current
      DESCRIPTION "The Pending Request Count. "
      ::= { joltConnectionRuntimeEntry 45  }
   
   
   joltConnectionRuntimeErrorCount OBJECT-TYPE
      SYNTAX      INTEGER
      MAX-ACCESS  read-only
      STATUS      current
      DESCRIPTION "The Request Error Count. "
      ::= { joltConnectionRuntimeEntry 50  }
   
   
   joltConnectionRuntimeInTransaction OBJECT-TYPE
      SYNTAX      INTEGER
                  {
                     true(1),
                     false(2)
                  }
      
      MAX-ACCESS  read-only
      STATUS      current
      DESCRIPTION "The Connection in Transaction indicator. "
      ::= { joltConnectionRuntimeEntry 55  }
   
   
   joltConnectionServiceRuntimeTable OBJECT-TYPE
      SYNTAX      SEQUENCE OF JoltConnectionServiceRuntimeEntry
      MAX-ACCESS  not-accessible
      STATUS      current
      DESCRIPTION "This class is used for monitoring a WebLogic Jolt component "
      ::= { wls 300  }
      
   
   joltConnectionServiceRuntimeEntry OBJECT-TYPE
      SYNTAX      JoltConnectionServiceRuntimeEntry
      MAX-ACCESS  not-accessible
      STATUS      current
      DESCRIPTION "Entry of joltConnectionServiceRuntimeTable"
      INDEX { joltConnectionServiceRuntimeIndex}
      ::= { joltConnectionServiceRuntimeTable 1 }
      
   JoltConnectionServiceRuntimeEntry ::=
      SEQUENCE
      {
         joltConnectionServiceRuntimeIndex DisplayString,
         joltConnectionServiceRuntimeObjectName DisplayString,
         joltConnectionServiceRuntimeType DisplayString,
         joltConnectionServiceRuntimeName DisplayString,
         joltConnectionServiceRuntimeParent DisplayString,
         joltConnectionServiceRuntimeConnectionPoolCount INTEGER
      }
      
   
   joltConnectionServiceRuntimeIndex OBJECT-TYPE
      SYNTAX      DisplayString (SIZE (1..16))
      MAX-ACCESS  read-only
      STATUS      current
      DESCRIPTION "Unique value directed from ObjectName which is used as table index"
      ::= { joltConnectionServiceRuntimeEntry 1  }
   
   
   joltConnectionServiceRuntimeObjectName OBJECT-TYPE
      SYNTAX      DisplayString (SIZE (1..256))
      MAX-ACCESS  read-only
      STATUS      current
      DESCRIPTION "JMX-standard MBean name"
      ::= { joltConnectionServiceRuntimeEntry 5  }
   
   
   joltConnectionServiceRuntimeType OBJECT-TYPE
      SYNTAX      DisplayString (SIZE (1..64))
      MAX-ACCESS  read-only
      STATUS      current
      DESCRIPTION "Returns the type of the MBean. "
      ::= { joltConnectionServiceRuntimeEntry 10  }
   
   
   joltConnectionServiceRuntimeName OBJECT-TYPE
      SYNTAX      DisplayString (SIZE (1..64))
      MAX-ACCESS  read-only
      STATUS      current
      DESCRIPTION "The name of this configuration. WebLogic Server uses an MBean to implement and persist the configuration. "
      ::= { joltConnectionServiceRuntimeEntry 15  }
   
   
   joltConnectionServiceRuntimeParent OBJECT-TYPE
      SYNTAX      DisplayString (SIZE (1..256))
      MAX-ACCESS  read-only
      STATUS      current
      DESCRIPTION "BEA-proprietary Parent object's identification, with syntax
      <type>:<name>"
      ::= { joltConnectionServiceRuntimeEntry 20  }
   
   
   joltConnectionServiceRuntimeConnectionPoolCount OBJECT-TYPE
      SYNTAX      INTEGER
      MAX-ACCESS  read-only
      STATUS      current
      DESCRIPTION "The number of configured Jolt connection pools. "
      ::= { joltConnectionServiceRuntimeEntry 25  }
   
   
   jrockitRuntimeTable OBJECT-TYPE
      SYNTAX      SEQUENCE OF JrockitRuntimeEntry
      MAX-ACCESS  not-accessible
      STATUS      current
      DESCRIPTION "This table is used for monitoring a WebLogic Jolt component"
      ::= { wls 302  }
      
   
   jrockitRuntimeEntry OBJECT-TYPE
      SYNTAX      JrockitRuntimeEntry
      MAX-ACCESS  not-accessible
      STATUS      current
      DESCRIPTION "Entry of jrockitRuntimeTable"
      INDEX { jrockitRuntimeIndex}
      ::= { jrockitRuntimeTable 1 }
      
   JrockitRuntimeEntry ::=
      SEQUENCE
      {
         jrockitRuntimeIndex  DisplayString,
         jrockitRuntimeObjectName DisplayString,
         jrockitRuntimeType   DisplayString,
         jrockitRuntimeName   DisplayString,
         jrockitRuntimeParent DisplayString,
         jrockitRuntimeAllProcessorsAverageLoad DisplayString,
         jrockitRuntimeFreeHeap Counter64,
         jrockitRuntimeFreePhysicalMemory Counter64,
         jrockitRuntimeGcAlgorithm DisplayString,
         jrockitRuntimeJVMDescription DisplayString,
         jrockitRuntimeJvmProcessorLoad DisplayString,
         jrockitRuntimeLastGCEnd Counter64,
         jrockitRuntimeLastGCStart Counter64,
         jrockitRuntimeNumberOfDaemonThreads INTEGER,
         jrockitRuntimeNumberOfProcessors INTEGER,
         jrockitRuntimeThreadStackDump DisplayString,
         jrockitRuntimeTotalGarbageCollectionCount Counter64,
         jrockitRuntimeTotalGarbageCollectionTime Counter64,
         jrockitRuntimeTotalHeap Counter64,
         jrockitRuntimeTotalNumberOfThreads INTEGER,
         jrockitRuntimeTotalNurserySize Counter64,
         jrockitRuntimeTotalPhysicalMemory Counter64,
         jrockitRuntimeUptime Counter64,
         jrockitRuntimeUsedHeap Counter64,
         jrockitRuntimeUsedPhysicalMemory Counter64,
         jrockitRuntimeVendor DisplayString,
         jrockitRuntimeVersion DisplayString,
         jrockitRuntimeConcurrent INTEGER,
         jrockitRuntimeGCHandlesCompaction INTEGER,
         jrockitRuntimeGenerational INTEGER,
         jrockitRuntimeIncremental INTEGER,
         jrockitRuntimeParallel INTEGER,
         jrockitRuntimeJavaVendor OCTET STRING,
         jrockitRuntimeHeapSizeCurrent Counter64,
         jrockitRuntimeHeapFreePercent INTEGER,
         jrockitRuntimeHeapSizeMax Counter64,
         jrockitRuntimeOSName OCTET STRING,
         jrockitRuntimeJavaVersion OCTET STRING,
         jrockitRuntimeOSVersion OCTET STRING,
         jrockitRuntimeHeapFreeCurrent Counter64,
         jrockitRuntimeJavaVMVendor OCTET STRING
      }
      
   
   jrockitRuntimeIndex OBJECT-TYPE
      SYNTAX      DisplayString (SIZE (1..16))
      MAX-ACCESS  read-only
      STATUS      current
      DESCRIPTION "Unique value directed from ObjectName which is used as table index"
      ::= { jrockitRuntimeEntry 1  }
   
   
   jrockitRuntimeObjectName OBJECT-TYPE
      SYNTAX      DisplayString (SIZE (1..256))
      MAX-ACCESS  read-only
      STATUS      current
      DESCRIPTION "JMX-standard MBean name"
      ::= { jrockitRuntimeEntry 5  }
   
   
   jrockitRuntimeType OBJECT-TYPE
      SYNTAX      DisplayString (SIZE (1..64))
      MAX-ACCESS  read-only
      STATUS      current
      DESCRIPTION "BEA-proprietary MBean type"
      ::= { jrockitRuntimeEntry 10  }
   
   
   jrockitRuntimeName OBJECT-TYPE
      SYNTAX      DisplayString (SIZE (1..64))
      MAX-ACCESS  read-only
      STATUS      current
      DESCRIPTION "BEA-proprietary MBean name"
      ::= { jrockitRuntimeEntry 15  }
   
   
   jrockitRuntimeParent OBJECT-TYPE
      SYNTAX      DisplayString (SIZE (1..256))
      MAX-ACCESS  read-only
      STATUS      current
      DESCRIPTION "BEA-proprietary Parent object's identification, with syntax
      <type>:<name>"
      ::= { jrockitRuntimeEntry 20  }
   
   
   jrockitRuntimeAllProcessorsAverageLoad OBJECT-TYPE
      SYNTAX      DisplayString (SIZE (1..64))
      MAX-ACCESS  read-only
      STATUS      current
      DESCRIPTION "represents a snapshot of the average load of all processors"
      ::= { jrockitRuntimeEntry 21  }
   
   
   jrockitRuntimeFreeHeap OBJECT-TYPE
      SYNTAX      Counter64
      MAX-ACCESS  read-only
      STATUS      current
      DESCRIPTION "Bytes of free Java heap memory."
      ::= { jrockitRuntimeEntry 22  }
   
   
   jrockitRuntimeFreePhysicalMemory OBJECT-TYPE
      SYNTAX      Counter64
      MAX-ACCESS  read-only
      STATUS      current
      DESCRIPTION "Bytes of free physical memory"
      ::= { jrockitRuntimeEntry 23  }
   
   
   jrockitRuntimeGcAlgorithm OBJECT-TYPE
      SYNTAX      DisplayString
      MAX-ACCESS  read-only
      STATUS      current
      DESCRIPTION "Type of garbage collector being used by the VM"
      ::= { jrockitRuntimeEntry 24  }
   
   
   jrockitRuntimeJVMDescription OBJECT-TYPE
      SYNTAX      DisplayString
      MAX-ACCESS  read-only
      STATUS      current
      DESCRIPTION "A description of the JVM as a String."
      ::= { jrockitRuntimeEntry 25  }
   
   
   jrockitRuntimeJvmProcessorLoad OBJECT-TYPE
      SYNTAX      DisplayString (SIZE (1..64))
      MAX-ACCESS  read-only
      STATUS      current
      DESCRIPTION "double that indicates the average load that the VM is placing on all processors."
      ::= { jrockitRuntimeEntry 26  }
   
   
   jrockitRuntimeLastGCEnd OBJECT-TYPE
      SYNTAX      Counter64
      MAX-ACCESS  read-only
      STATUS      current
      DESCRIPTION "the time the last GC ended."
      ::= { jrockitRuntimeEntry 27  }
   
   
   jrockitRuntimeLastGCStart OBJECT-TYPE
      SYNTAX      Counter64
      MAX-ACCESS  read-only
      STATUS      current
      DESCRIPTION "The time the last GC started"
      ::= { jrockitRuntimeEntry 28  }
   
   
   jrockitRuntimeNumberOfDaemonThreads OBJECT-TYPE
      SYNTAX      INTEGER
      MAX-ACCESS  read-only
      STATUS      current
      DESCRIPTION "the total number of daemon Java threads running in the VM."
      ::= { jrockitRuntimeEntry 29  }
   
   
   jrockitRuntimeNumberOfProcessors OBJECT-TYPE
      SYNTAX      INTEGER
      MAX-ACCESS  read-only
      STATUS      current
      DESCRIPTION "he number of processors on the VM's host computer."
      ::= { jrockitRuntimeEntry 30  }
   
   
   jrockitRuntimeThreadStackDump OBJECT-TYPE
      SYNTAX      DisplayString
      MAX-ACCESS  read-only
      STATUS      current
      DESCRIPTION "a stack dump of all live threads in the VM"
      ::= { jrockitRuntimeEntry 31  }
   
   
   jrockitRuntimeTotalGarbageCollectionCount OBJECT-TYPE
      SYNTAX      Counter64
      MAX-ACCESS  read-only
      STATUS      current
      DESCRIPTION "The number of GCs perfomed so far"
      ::= { jrockitRuntimeEntry 32  }
   
   
   jrockitRuntimeTotalGarbageCollectionTime OBJECT-TYPE
      SYNTAX      Counter64
      MAX-ACCESS  read-only
      STATUS      current
      DESCRIPTION "Indicates the number of milliseconds that the Virtual Machine has spent on all garbage collection runs since the VM was started."
      ::= { jrockitRuntimeEntry 33  }
   
   
   jrockitRuntimeTotalHeap OBJECT-TYPE
      SYNTAX      Counter64
      MAX-ACCESS  read-only
      STATUS      current
      DESCRIPTION "Bytes of memory allocated to the Java heap"
      ::= { jrockitRuntimeEntry 34  }
   
   
   jrockitRuntimeTotalNumberOfThreads OBJECT-TYPE
      SYNTAX      INTEGER
      MAX-ACCESS  read-only
      STATUS      current
      DESCRIPTION "the number of Java threads running in the VM"
      ::= { jrockitRuntimeEntry 35  }
   
   
   jrockitRuntimeTotalNurserySize OBJECT-TYPE
      SYNTAX      Counter64
      MAX-ACCESS  read-only
      STATUS      current
      DESCRIPTION "Bytes allocated to the nursery"
      ::= { jrockitRuntimeEntry 36  }
   
   
   jrockitRuntimeTotalPhysicalMemory OBJECT-TYPE
      SYNTAX      Counter64
      MAX-ACCESS  read-only
      STATUS      current
      DESCRIPTION "Bytes of physical memory on the host computer"
      ::= { jrockitRuntimeEntry 37  }
   
   
   jrockitRuntimeUptime OBJECT-TYPE
      SYNTAX      Counter64
      MAX-ACCESS  read-only
      STATUS      current
      DESCRIPTION "The uptime (in milliseconds) of the VM"
      ::= { jrockitRuntimeEntry 38  }
   
   
   jrockitRuntimeUsedHeap OBJECT-TYPE
      SYNTAX      Counter64
      MAX-ACCESS  read-only
      STATUS      current
      DESCRIPTION "Bytes of Java heap memory that is being used"
      ::= { jrockitRuntimeEntry 39  }
   
   
   jrockitRuntimeUsedPhysicalMemory OBJECT-TYPE
      SYNTAX      Counter64
      MAX-ACCESS  read-only
      STATUS      current
      DESCRIPTION "Bytes of physical memory being used."
      ::= { jrockitRuntimeEntry 40  }
   
   
   jrockitRuntimeVendor OBJECT-TYPE
      SYNTAX      DisplayString
      MAX-ACCESS  read-only
      STATUS      current
      DESCRIPTION "The name of the vendor as a String"
      ::= { jrockitRuntimeEntry 41  }
   
   
   jrockitRuntimeVersion OBJECT-TYPE
      SYNTAX      DisplayString
      MAX-ACCESS  read-only
      STATUS      current
      DESCRIPTION "The current version of the JVM as a String"
      ::= { jrockitRuntimeEntry 42  }
   
   
   jrockitRuntimeConcurrent OBJECT-TYPE
      SYNTAX      INTEGER
      MAX-ACCESS  read-only
      STATUS      current
      DESCRIPTION "true if this GC runs in a separate concurrent thread."
      ::= { jrockitRuntimeEntry 43  }
   
   
   jrockitRuntimeGCHandlesCompaction OBJECT-TYPE
      SYNTAX      INTEGER
      MAX-ACCESS  read-only
      STATUS      current
      DESCRIPTION "true if this garbage collector compacts the Java heap"
      ::= { jrockitRuntimeEntry 44  }
   
   
   jrockitRuntimeGenerational OBJECT-TYPE
      SYNTAX      INTEGER
      MAX-ACCESS  read-only
      STATUS      current
      DESCRIPTION "true if this GC has a nursery."
      ::= { jrockitRuntimeEntry 45  }
   
   
   jrockitRuntimeIncremental OBJECT-TYPE
      SYNTAX      INTEGER
      MAX-ACCESS  read-only
      STATUS      current
      DESCRIPTION "true if this GC is incremental"
      ::= { jrockitRuntimeEntry 46  }
   
   
   jrockitRuntimeParallel OBJECT-TYPE
      SYNTAX      INTEGER
      MAX-ACCESS  read-only
      STATUS      current
      DESCRIPTION "true if this GC runs in parallel on multiple processors"
      ::= { jrockitRuntimeEntry 47  }
   
   
   jrockitRuntimeJavaVendor OBJECT-TYPE
      SYNTAX      OCTET STRING
      MAX-ACCESS  read-only
      STATUS      current
      DESCRIPTION "Returns the vendor of Java.  The vendor of Java that this server runs."
      ::= { jrockitRuntimeEntry 48  }
   
   
   jrockitRuntimeHeapSizeCurrent OBJECT-TYPE
      SYNTAX      Counter64
      MAX-ACCESS  read-only
      STATUS      current
      DESCRIPTION "The current size (in bytes) of the JVM heap."
      ::= { jrockitRuntimeEntry 49  }
   
   
   jrockitRuntimeHeapFreePercent OBJECT-TYPE
      SYNTAX      INTEGER
      MAX-ACCESS  read-only
      STATUS      current
      DESCRIPTION "Percentage of the maximum memory that is free."
      ::= { jrockitRuntimeEntry 50  }
   
   
   jrockitRuntimeHeapSizeMax OBJECT-TYPE
      SYNTAX      Counter64
      MAX-ACCESS  read-only
      STATUS      current
      DESCRIPTION "The maximum free memory configured for this JVM."
      ::= { jrockitRuntimeEntry 51  }
   
   
   jrockitRuntimeOSName OBJECT-TYPE
      SYNTAX      OCTET STRING
      MAX-ACCESS  read-only
      STATUS      current
      DESCRIPTION "Returns the operating system on which the JVM is running.  The operating system on which the JVM is running."
      ::= { jrockitRuntimeEntry 52  }
   
   
   jrockitRuntimeJavaVersion OBJECT-TYPE
      SYNTAX      OCTET STRING
      MAX-ACCESS  read-only
      STATUS      current
      DESCRIPTION "The Java version of the JVM."
      ::= { jrockitRuntimeEntry 53  }
   
   
   jrockitRuntimeOSVersion OBJECT-TYPE
      SYNTAX      OCTET STRING
      MAX-ACCESS  read-only
      STATUS      current
      DESCRIPTION "The version of the operating system on which the JVM is running."
      ::= { jrockitRuntimeEntry 54  }
   
   
   jrockitRuntimeHeapFreeCurrent OBJECT-TYPE
      SYNTAX      Counter64
      MAX-ACCESS  read-only
      STATUS      current
      DESCRIPTION "The current amount of memory (in bytes) that is available in the JVM heap."
      ::= { jrockitRuntimeEntry 55  }
   
   
   jrockitRuntimeJavaVMVendor OBJECT-TYPE
      SYNTAX      OCTET STRING
      MAX-ACCESS  read-only
      STATUS      current
      DESCRIPTION "Returns the vendor of the JVM.  The vendor of the JVM that this server runs.  system property java.vm.vendor is returned"
      ::= { jrockitRuntimeEntry 56  }
   
   
   jtaRuntimeTable OBJECT-TYPE
      SYNTAX      SEQUENCE OF JtaRuntimeEntry
      MAX-ACCESS  not-accessible
      STATUS      current
      DESCRIPTION "This interface is used for accessing transaction runtime characteristics within a WebLogic server. "
      ::= { wls 310  }
      
   
   jtaRuntimeEntry OBJECT-TYPE
      SYNTAX      JtaRuntimeEntry
      MAX-ACCESS  not-accessible
      STATUS      current
      DESCRIPTION "Entry of jtaRuntimeTable"
      INDEX { jtaRuntimeIndex}
      ::= { jtaRuntimeTable 1 }
      
   JtaRuntimeEntry ::=
      SEQUENCE
      {
         jtaRuntimeIndex      DisplayString,
         jtaRuntimeObjectName DisplayString,
         jtaRuntimeType       DisplayString,
         jtaRuntimeName       DisplayString,
         jtaRuntimeParent     DisplayString,
         jtaRuntimeTransactionTotalCount Counter64,
         jtaRuntimeTransactionCommittedTotalCount Counter64,
         jtaRuntimeTransactionRolledBackTotalCount Counter64,
         jtaRuntimeTransactionHeuristicsTotalCount Counter64,
         jtaRuntimeTransactionRolledBackResourceTotalCount Counter64,
         jtaRuntimeTransactionRolledBackAppTotalCount Counter64,
         jtaRuntimeTransactionRolledBackSystemTotalCount Counter64,
         jtaRuntimeSecondsActiveTotalCount Counter64,
         jtaRuntimeTransactionRolledBackTimeoutTotalCount Counter64,
         jtaRuntimeActiveTransactionsTotalCount INTEGER,
         jtaRuntimeTransactionAbandonedTotalCount Counter64,
         jtaRuntimeRegisteredNonXAResourceNames OCTET STRING,
         jtaRuntimeRegisteredResourceNames OCTET STRING,
         jtaRuntimeTransactionNoResourcesCommittedTotalCount Counter64,
         jtaRuntimeTransactionReadOnlyOnePhaseCommittedTotalCount Counter64,
         jtaRuntimeTransactionTwoPhaseCommittedTotalCount Counter64,
         jtaRuntimeTransactionLLRCommittedTotalCount Counter64,
         jtaRuntimeTransactionOneResourceOnePhaseCommittedTotalCount Counter64,
         jtaRuntimeHealthState OCTET STRING,
         jtaRuntimeTransactionTwoPhaseCommittedNotLoggedTotalCount Counter64,
         jtaRuntimeTransactionTwoPhaseCommittedLoggedTotalCount Counter64
      }
      
   
   jtaRuntimeIndex OBJECT-TYPE
      SYNTAX      DisplayString (SIZE (1..16))
      MAX-ACCESS  read-only
      STATUS      current
      DESCRIPTION "Unique value directed from ObjectName which is used as table index"
      ::= { jtaRuntimeEntry 1  }
   
   
   jtaRuntimeObjectName OBJECT-TYPE
      SYNTAX      DisplayString (SIZE (1..256))
      MAX-ACCESS  read-only
      STATUS      current
      DESCRIPTION "JMX-standard MBean name"
      ::= { jtaRuntimeEntry 5  }
   
   
   jtaRuntimeType OBJECT-TYPE
      SYNTAX      DisplayString (SIZE (1..64))
      MAX-ACCESS  read-only
      STATUS      current
      DESCRIPTION "Returns the type of the MBean. "
      ::= { jtaRuntimeEntry 10  }
   
   
   jtaRuntimeName OBJECT-TYPE
      SYNTAX      DisplayString (SIZE (1..64))
      MAX-ACCESS  read-only
      STATUS      current
      DESCRIPTION "The name of this configuration. WebLogic Server uses an MBean to implement and persist the configuration. "
      ::= { jtaRuntimeEntry 15  }
   
   
   jtaRuntimeParent OBJECT-TYPE
      SYNTAX      DisplayString (SIZE (1..256))
      MAX-ACCESS  read-only
      STATUS      current
      DESCRIPTION "BEA-proprietary Parent object's identification, with syntax
      <type>:<name>"
      ::= { jtaRuntimeEntry 20  }
   
   
   jtaRuntimeTransactionTotalCount OBJECT-TYPE
      SYNTAX      Counter64
      MAX-ACCESS  read-only
      STATUS      current
      DESCRIPTION "The total number of transactions processed. This total includes all committed, rolled back, and heuristic transaction completions since the server was started. "
      ::= { jtaRuntimeEntry 25  }
   
   
   jtaRuntimeTransactionCommittedTotalCount OBJECT-TYPE
      SYNTAX      Counter64
      MAX-ACCESS  read-only
      STATUS      current
      DESCRIPTION "The total number of transactions committed since the server was started. "
      ::= { jtaRuntimeEntry 30  }
   
   
   jtaRuntimeTransactionRolledBackTotalCount OBJECT-TYPE
      SYNTAX      Counter64
      MAX-ACCESS  read-only
      STATUS      current
      DESCRIPTION "The number of transactions that were rolled back since the server was started. "
      ::= { jtaRuntimeEntry 35  }
   
   
   jtaRuntimeTransactionHeuristicsTotalCount OBJECT-TYPE
      SYNTAX      Counter64
      MAX-ACCESS  read-only
      STATUS      current
      DESCRIPTION "The number of transactions that completed with a heuristic status since the server was started. "
      ::= { jtaRuntimeEntry 40  }
   
   
   jtaRuntimeTransactionRolledBackResourceTotalCount OBJECT-TYPE
      SYNTAX      Counter64
      MAX-ACCESS  read-only
      STATUS      current
      DESCRIPTION "The number of transactions that were rolled back due to a resource error. "
      ::= { jtaRuntimeEntry 45  }
   
   
   jtaRuntimeTransactionRolledBackAppTotalCount OBJECT-TYPE
      SYNTAX      Counter64
      MAX-ACCESS  read-only
      STATUS      current
      DESCRIPTION "The number of transactions that were rolled back due to an application error. "
      ::= { jtaRuntimeEntry 50  }
   
   
   jtaRuntimeTransactionRolledBackSystemTotalCount OBJECT-TYPE
      SYNTAX      Counter64
      MAX-ACCESS  read-only
      STATUS      current
      DESCRIPTION "The number of transactions that were rolled back due to an internal system error. "
      ::= { jtaRuntimeEntry 55  }
   
   
   jtaRuntimeSecondsActiveTotalCount OBJECT-TYPE
      SYNTAX      Counter64
      MAX-ACCESS  read-only
      STATUS      current
      DESCRIPTION "The total number of seconds that transactions were active for all committed transactions. "
      ::= { jtaRuntimeEntry 60  }
   
   
   jtaRuntimeTransactionRolledBackTimeoutTotalCount OBJECT-TYPE
      SYNTAX      Counter64
      MAX-ACCESS  read-only
      STATUS      current
      DESCRIPTION "The number of transactions that were rolled back due to a timeout expiration. "
      ::= { jtaRuntimeEntry 65  }
   
   
   jtaRuntimeActiveTransactionsTotalCount OBJECT-TYPE
      SYNTAX      INTEGER
      MAX-ACCESS  read-only
      STATUS      current
      DESCRIPTION "The number of active transactions on the server. "
      ::= { jtaRuntimeEntry 76  }
   
   
   jtaRuntimeTransactionAbandonedTotalCount OBJECT-TYPE
      SYNTAX      Counter64
      MAX-ACCESS  read-only
      STATUS      current
      DESCRIPTION "The total number of transactions that were abandoned since the server was started. "
      ::= { jtaRuntimeEntry 77  }
   
   
   jtaRuntimeRegisteredNonXAResourceNames OBJECT-TYPE
      SYNTAX      OCTET STRING
      MAX-ACCESS  read-only
      STATUS      current
      DESCRIPTION "An array of NonXA resource names that are registered with the transaction manager. "
      ::= { jtaRuntimeEntry 78  }
   
   
   jtaRuntimeRegisteredResourceNames OBJECT-TYPE
      SYNTAX      OCTET STRING
      MAX-ACCESS  read-only
      STATUS      current
      DESCRIPTION "An array of XA resource names that are registered with the transaction manager. "
      ::= { jtaRuntimeEntry 79  }
   
   
   jtaRuntimeTransactionNoResourcesCommittedTotalCount OBJECT-TYPE
      SYNTAX      Counter64
      MAX-ACCESS  read-only
      STATUS      current
      DESCRIPTION "The total number of transactions with no enlisted resources that were committed since the server was started. "
      ::= { jtaRuntimeEntry 80  }
   
   
   jtaRuntimeTransactionReadOnlyOnePhaseCommittedTotalCount OBJECT-TYPE
      SYNTAX      Counter64
      MAX-ACCESS  read-only
      STATUS      current
      DESCRIPTION "The total number of transactions with more than one enlisted resource that were one-phase committed due to read-only optimization since the server was started. "
      ::= { jtaRuntimeEntry 81  }
   
   
   jtaRuntimeTransactionTwoPhaseCommittedTotalCount OBJECT-TYPE
      SYNTAX      Counter64
      MAX-ACCESS  read-only
      STATUS      current
      DESCRIPTION "The total number of transactions with more than one enlisted resource that were two-phase committed since the server was started. "
      ::= { jtaRuntimeEntry 82  }
   
   
   jtaRuntimeTransactionLLRCommittedTotalCount OBJECT-TYPE
      SYNTAX      Counter64
      MAX-ACCESS  read-only
      STATUS      current
      DESCRIPTION "The total number of LLR transactions that were committed since the server was started. "
      ::= { jtaRuntimeEntry 83  }
   
   
   jtaRuntimeTransactionOneResourceOnePhaseCommittedTotalCount OBJECT-TYPE
      SYNTAX      Counter64
      MAX-ACCESS  read-only
      STATUS      current
      DESCRIPTION "The total number of transactions with only one enlisted resource that were one-phase committed since the server was started. "
      ::= { jtaRuntimeEntry 84  }
   
   
   jtaRuntimeHealthState OBJECT-TYPE
      SYNTAX      OCTET STRING
      MAX-ACCESS  read-only
      STATUS      current
      DESCRIPTION "The health state of the JTA subsystem. for state values.   "
      ::= { jtaRuntimeEntry 85  }
   
   
   jtaRuntimeTransactionTwoPhaseCommittedNotLoggedTotalCount OBJECT-TYPE
      SYNTAX      Counter64
      MAX-ACCESS  read-only
      STATUS      current
      DESCRIPTION "The total number of two phase commited transactions that were committed without TLog since the server was started. "
      ::= { jtaRuntimeEntry 86  }
   
   
   jtaRuntimeTransactionTwoPhaseCommittedLoggedTotalCount OBJECT-TYPE
      SYNTAX      Counter64
      MAX-ACCESS  read-only
      STATUS      current
      DESCRIPTION "The total number of two phase commit transactions that were committed with TLog since the server was started. "
      ::= { jtaRuntimeEntry 87  }
   
   
   jtaRecoveryRuntimeTable OBJECT-TYPE
      SYNTAX      SEQUENCE OF JtaRecoveryRuntimeEntry
      MAX-ACCESS  not-accessible
      STATUS      current
      DESCRIPTION "This interface is used for accessing transaction runtime characteristics for recovered transactions that are associated with a particular Transaction Recovery Service. "
      ::= { wls 311  }
      
   
   jtaRecoveryRuntimeEntry OBJECT-TYPE
      SYNTAX      JtaRecoveryRuntimeEntry
      MAX-ACCESS  not-accessible
      STATUS      current
      DESCRIPTION "Entry of jtaRecoveryRuntimeTable"
      INDEX { jtaRecoveryRuntimeIndex}
      ::= { jtaRecoveryRuntimeTable 1 }
      
   JtaRecoveryRuntimeEntry ::=
      SEQUENCE
      {
         jtaRecoveryRuntimeIndex DisplayString,
         jtaRecoveryRuntimeObjectName DisplayString,
         jtaRecoveryRuntimeType DisplayString,
         jtaRecoveryRuntimeName DisplayString,
         jtaRecoveryRuntimeParent DisplayString,
         jtaRecoveryRuntimeInitialRecoveredTransactionTotalCount INTEGER,
         jtaRecoveryRuntimeRecoveredTransactionCompletionPercent INTEGER,
         jtaRecoveryRuntimeActive INTEGER,
         jtaRecoveryRuntimeInitialRecoveredUnloggedTransactionTotalCount INTEGER,
         jtaRecoveryRuntimeRecoveredUnloggedTransactionCompletionPercent INTEGER
      }
      
   
   jtaRecoveryRuntimeIndex OBJECT-TYPE
      SYNTAX      DisplayString (SIZE (1..16))
      MAX-ACCESS  read-only
      STATUS      current
      DESCRIPTION "Unique value directed from ObjectName which is used as table index"
      ::= { jtaRecoveryRuntimeEntry 1  }
   
   
   jtaRecoveryRuntimeObjectName OBJECT-TYPE
      SYNTAX      DisplayString (SIZE (1..256))
      MAX-ACCESS  read-only
      STATUS      current
      DESCRIPTION "JMX-standard MBean name"
      ::= { jtaRecoveryRuntimeEntry 5  }
   
   
   jtaRecoveryRuntimeType OBJECT-TYPE
      SYNTAX      DisplayString (SIZE (1..64))
      MAX-ACCESS  read-only
      STATUS      current
      DESCRIPTION "Returns the type of the MBean. "
      ::= { jtaRecoveryRuntimeEntry 10  }
   
   
   jtaRecoveryRuntimeName OBJECT-TYPE
      SYNTAX      DisplayString (SIZE (1..64))
      MAX-ACCESS  read-only
      STATUS      current
      DESCRIPTION "The name of this configuration. WebLogic Server uses an MBean to implement and persist the configuration. "
      ::= { jtaRecoveryRuntimeEntry 15  }
   
   
   jtaRecoveryRuntimeParent OBJECT-TYPE
      SYNTAX      DisplayString (SIZE (1..256))
      MAX-ACCESS  read-only
      STATUS      current
      DESCRIPTION "BEA-proprietary Parent object's identification, with syntax
      <type>:<name>"
      ::= { jtaRecoveryRuntimeEntry 20  }
   
   
   jtaRecoveryRuntimeInitialRecoveredTransactionTotalCount OBJECT-TYPE
      SYNTAX      INTEGER
      MAX-ACCESS  read-only
      STATUS      current
      DESCRIPTION "The total number of transactions that are recovered from the transaction log initially. "
      ::= { jtaRecoveryRuntimeEntry 25  }
   
   
   jtaRecoveryRuntimeRecoveredTransactionCompletionPercent OBJECT-TYPE
      SYNTAX      INTEGER
      MAX-ACCESS  read-only
      STATUS      current
      DESCRIPTION "The percentage of transactions that are recovered from the transaction log initially. "
      ::= { jtaRecoveryRuntimeEntry 30  }
   
   
   jtaRecoveryRuntimeActive OBJECT-TYPE
      SYNTAX      INTEGER
      MAX-ACCESS  read-only
      STATUS      current
      DESCRIPTION "Indicates whether the Transaction Recovery Service is currently activated on this server. "
      ::= { jtaRecoveryRuntimeEntry 35  }
   
   
   jtaRecoveryRuntimeInitialRecoveredUnloggedTransactionTotalCount OBJECT-TYPE
      SYNTAX      INTEGER
      MAX-ACCESS  read-only
      STATUS      current
      DESCRIPTION "The total number of transactions that are recovered from the no transaction log initially. "
      ::= { jtaRecoveryRuntimeEntry 36  }
   
   
   jtaRecoveryRuntimeRecoveredUnloggedTransactionCompletionPercent OBJECT-TYPE
      SYNTAX      INTEGER
      MAX-ACCESS  read-only
      STATUS      current
      DESCRIPTION "The percentage of transactions that are recovered from the no transaction log initially. "
      ::= { jtaRecoveryRuntimeEntry 37  }
   
   
   libraryRuntimeTable OBJECT-TYPE
      SYNTAX      SEQUENCE OF LibraryRuntimeEntry
      MAX-ACCESS  not-accessible
      STATUS      current
      DESCRIPTION "RuntimeMBean for library deployments. "
      ::= { wls 320  }
      
   
   libraryRuntimeEntry OBJECT-TYPE
      SYNTAX      LibraryRuntimeEntry
      MAX-ACCESS  not-accessible
      STATUS      current
      DESCRIPTION "Entry of libraryRuntimeTable"
      INDEX { libraryRuntimeIndex}
      ::= { libraryRuntimeTable 1 }
      
   LibraryRuntimeEntry ::=
      SEQUENCE
      {
         libraryRuntimeIndex  DisplayString,
         libraryRuntimeObjectName DisplayString,
         libraryRuntimeType   DisplayString,
         libraryRuntimeName   DisplayString,
         libraryRuntimeParent DisplayString,
         libraryRuntimeLibraryName DisplayString,
         libraryRuntimeSpecificationVersion DisplayString,
         libraryRuntimeImplementationVersion DisplayString,
         libraryRuntimeReferenced INTEGER,
         libraryRuntimeLibraryIdentifier OCTET STRING,
         libraryRuntimePartitionName OCTET STRING
      }
      
   
   libraryRuntimeIndex OBJECT-TYPE
      SYNTAX      DisplayString (SIZE (1..16))
      MAX-ACCESS  read-only
      STATUS      current
      DESCRIPTION "Unique value directed from ObjectName which is used as table index"
      ::= { libraryRuntimeEntry 1  }
   
   
   libraryRuntimeObjectName OBJECT-TYPE
      SYNTAX      DisplayString (SIZE (1..256))
      MAX-ACCESS  read-only
      STATUS      current
      DESCRIPTION "JMX-standard MBean name"
      ::= { libraryRuntimeEntry 5  }
   
   
   libraryRuntimeType OBJECT-TYPE
      SYNTAX      DisplayString (SIZE (1..64))
      MAX-ACCESS  read-only
      STATUS      current
      DESCRIPTION "Returns the type of the MBean. "
      ::= { libraryRuntimeEntry 10  }
   
   
   libraryRuntimeName OBJECT-TYPE
      SYNTAX      DisplayString (SIZE (1..64))
      MAX-ACCESS  read-only
      STATUS      current
      DESCRIPTION "The name of this configuration. WebLogic Server uses an MBean to implement and persist the configuration. "
      ::= { libraryRuntimeEntry 15  }
   
   
   libraryRuntimeParent OBJECT-TYPE
      SYNTAX      DisplayString (SIZE (1..256))
      MAX-ACCESS  read-only
      STATUS      current
      DESCRIPTION "BEA-proprietary Parent object's identification, with syntax
      <type>:<name>"
      ::= { libraryRuntimeEntry 20  }
   
   
   libraryRuntimeLibraryName OBJECT-TYPE
      SYNTAX      DisplayString (SIZE (1..64))
      MAX-ACCESS  read-only
      STATUS      current
      DESCRIPTION "Returns the library name. "
      ::= { libraryRuntimeEntry 25  }
   
   
   libraryRuntimeSpecificationVersion OBJECT-TYPE
      SYNTAX      DisplayString (SIZE (1..64))
      MAX-ACCESS  read-only
      STATUS      current
      DESCRIPTION "Returns the library specification version. If not set, this value is null. "
      ::= { libraryRuntimeEntry 30  }
   
   
   libraryRuntimeImplementationVersion OBJECT-TYPE
      SYNTAX      DisplayString (SIZE (1..64))
      MAX-ACCESS  read-only
      STATUS      current
      DESCRIPTION "Returns the library implementation version. If not set, this value is null. "
      ::= { libraryRuntimeEntry 35  }
   
   
   libraryRuntimeReferenced OBJECT-TYPE
      SYNTAX      INTEGER
                  {
                     true(1),
                     false(2)
                  }
      
      MAX-ACCESS  read-only
      STATUS      current
      DESCRIPTION "Returns true if this library is referenced by one or more referencers. Typically, a library referencer is a deployed application. "
      ::= { libraryRuntimeEntry 40  }
   
   
   libraryRuntimeLibraryIdentifier OBJECT-TYPE
      SYNTAX      OCTET STRING
      MAX-ACCESS  read-only
      STATUS      current
      DESCRIPTION "Returns the library identifier.  The library identifier uniquely identifies this library version across all versions of all deployed applications and deployed libraries. If the library is not versioned, the library identifier is the same as the library name. "
      ::= { libraryRuntimeEntry 41  }
   
   
   libraryRuntimePartitionName OBJECT-TYPE
      SYNTAX      OCTET STRING
      MAX-ACCESS  read-only
      STATUS      current
      DESCRIPTION "The library's partition.  Returns the partition to which this library is deployed. "
      ::= { libraryRuntimeEntry 42  }
   
   
   persistentStoreRuntimeTable OBJECT-TYPE
      SYNTAX      SEQUENCE OF PersistentStoreRuntimeEntry
      MAX-ACCESS  not-accessible
      STATUS      current
      DESCRIPTION "This class is used for monitoring a Persistent Store. "
      ::= { wls 330  }
      
   
   persistentStoreRuntimeEntry OBJECT-TYPE
      SYNTAX      PersistentStoreRuntimeEntry
      MAX-ACCESS  not-accessible
      STATUS      current
      DESCRIPTION "Entry of persistentStoreRuntimeTable"
      INDEX { persistentStoreRuntimeIndex}
      ::= { persistentStoreRuntimeTable 1 }
      
   PersistentStoreRuntimeEntry ::=
      SEQUENCE
      {
         persistentStoreRuntimeIndex DisplayString,
         persistentStoreRuntimeObjectName DisplayString,
         persistentStoreRuntimeType DisplayString,
         persistentStoreRuntimeName DisplayString,
         persistentStoreRuntimeParent DisplayString,
         persistentStoreRuntimeCreateCount Counter64,
         persistentStoreRuntimeReadCount Counter64,
         persistentStoreRuntimeUpdateCount Counter64,
         persistentStoreRuntimeDeleteCount Counter64,
         persistentStoreRuntimeObjectCount Counter64,
         persistentStoreRuntimePhysicalWriteCount Counter64,
         persistentStoreRuntimeAllocatedIoBufferBytes Counter64,
         persistentStoreRuntimeAllocatedWindowBufferBytes Counter64,
         persistentStoreRuntimeHealthState OCTET STRING
      }
      
   
   persistentStoreRuntimeIndex OBJECT-TYPE
      SYNTAX      DisplayString (SIZE (1..16))
      MAX-ACCESS  read-only
      STATUS      current
      DESCRIPTION "Unique value directed from ObjectName which is used as table index"
      ::= { persistentStoreRuntimeEntry 1  }
   
   
   persistentStoreRuntimeObjectName OBJECT-TYPE
      SYNTAX      DisplayString (SIZE (1..256))
      MAX-ACCESS  read-only
      STATUS      current
      DESCRIPTION "JMX-standard MBean name"
      ::= { persistentStoreRuntimeEntry 5  }
   
   
   persistentStoreRuntimeType OBJECT-TYPE
      SYNTAX      DisplayString (SIZE (1..64))
      MAX-ACCESS  read-only
      STATUS      current
      DESCRIPTION "Returns the type of the MBean. "
      ::= { persistentStoreRuntimeEntry 10  }
   
   
   persistentStoreRuntimeName OBJECT-TYPE
      SYNTAX      DisplayString (SIZE (1..64))
      MAX-ACCESS  read-only
      STATUS      current
      DESCRIPTION "The name of this configuration. WebLogic Server uses an MBean to implement and persist the configuration. "
      ::= { persistentStoreRuntimeEntry 15  }
   
   
   persistentStoreRuntimeParent OBJECT-TYPE
      SYNTAX      DisplayString (SIZE (1..256))
      MAX-ACCESS  read-only
      STATUS      current
      DESCRIPTION "BEA-proprietary Parent object's identification, with syntax
      <type>:<name>"
      ::= { persistentStoreRuntimeEntry 20  }
   
   
   persistentStoreRuntimeCreateCount OBJECT-TYPE
      SYNTAX      Counter64
      MAX-ACCESS  read-only
      STATUS      current
      DESCRIPTION "Number of create requests issued by this store. "
      ::= { persistentStoreRuntimeEntry 25  }
   
   
   persistentStoreRuntimeReadCount OBJECT-TYPE
      SYNTAX      Counter64
      MAX-ACCESS  read-only
      STATUS      current
      DESCRIPTION "Number of read requests issued by this store, including requests that occur during store initialization. "
      ::= { persistentStoreRuntimeEntry 30  }
   
   
   persistentStoreRuntimeUpdateCount OBJECT-TYPE
      SYNTAX      Counter64
      MAX-ACCESS  read-only
      STATUS      current
      DESCRIPTION "Number of update requests issued by this store. "
      ::= { persistentStoreRuntimeEntry 35  }
   
   
   persistentStoreRuntimeDeleteCount OBJECT-TYPE
      SYNTAX      Counter64
      MAX-ACCESS  read-only
      STATUS      current
      DESCRIPTION "Number of delete requests issued by this store. "
      ::= { persistentStoreRuntimeEntry 40  }
   
   
   persistentStoreRuntimeObjectCount OBJECT-TYPE
      SYNTAX      Counter64
      MAX-ACCESS  read-only
      STATUS      current
      DESCRIPTION "Number of objects contained in the store. "
      ::= { persistentStoreRuntimeEntry 45  }
   
   
   persistentStoreRuntimePhysicalWriteCount OBJECT-TYPE
      SYNTAX      Counter64
      MAX-ACCESS  read-only
      STATUS      current
      DESCRIPTION "Number of times the store flushed its data to durable storage. "
      ::= { persistentStoreRuntimeEntry 50  }
   
   
   persistentStoreRuntimeAllocatedIoBufferBytes OBJECT-TYPE
      SYNTAX      Counter64
      MAX-ACCESS  read-only
      STATUS      current
      DESCRIPTION "The amount of off-heap (native) memory, in bytes, reserved for file store use.  When applicable, this is a multiple of the file store configurable attribute IOBufferSize. Applies to synchronous write policies Direct-Write and Cache-Flush policies. "
      ::= { persistentStoreRuntimeEntry 51  }
   
   
   persistentStoreRuntimeAllocatedWindowBufferBytes OBJECT-TYPE
      SYNTAX      Counter64
      MAX-ACCESS  read-only
      STATUS      current
      DESCRIPTION "The amount of off-heap (native) memory, in bytes, reserved for file store window buffer use.  Applies to synchronous write policies Direct-Write-With-Cache and Disabled but only when the native wlfileio library is loaded. See file store configurable attribute MaxWindowBufferSize for more information "
      ::= { persistentStoreRuntimeEntry 52  }
   
   
   persistentStoreRuntimeHealthState OBJECT-TYPE
      SYNTAX      OCTET STRING
      MAX-ACCESS  read-only
      STATUS      current
      DESCRIPTION "Implement the HealthFeedback interface by returning the health state of this store. "
      ::= { persistentStoreRuntimeEntry 53  }
   
   
   persistentStoreConnectionRuntimeTable OBJECT-TYPE
      SYNTAX      SEQUENCE OF PersistentStoreConnectionRuntimeEntry
      MAX-ACCESS  not-accessible
      STATUS      current
      DESCRIPTION "This class is used for monitoring a Persistent Store Connection. "
      ::= { wls 331  }
      
   
   persistentStoreConnectionRuntimeEntry OBJECT-TYPE
      SYNTAX      PersistentStoreConnectionRuntimeEntry
      MAX-ACCESS  not-accessible
      STATUS      current
      DESCRIPTION "Entry of persistentStoreConnectionRuntimeTable"
      INDEX { persistentStoreConnectionRuntimeIndex}
      ::= { persistentStoreConnectionRuntimeTable 1 }
      
   PersistentStoreConnectionRuntimeEntry ::=
      SEQUENCE
      {
         persistentStoreConnectionRuntimeIndex DisplayString,
         persistentStoreConnectionRuntimeObjectName DisplayString,
         persistentStoreConnectionRuntimeType DisplayString,
         persistentStoreConnectionRuntimeName DisplayString,
         persistentStoreConnectionRuntimeParent DisplayString,
         persistentStoreConnectionRuntimeCreateCount Counter64,
         persistentStoreConnectionRuntimeReadCount Counter64,
         persistentStoreConnectionRuntimeUpdateCount Counter64,
         persistentStoreConnectionRuntimeDeleteCount Counter64,
         persistentStoreConnectionRuntimeObjectCount Counter64
      }
      
   
   persistentStoreConnectionRuntimeIndex OBJECT-TYPE
      SYNTAX      DisplayString (SIZE (1..16))
      MAX-ACCESS  read-only
      STATUS      current
      DESCRIPTION "Unique value directed from ObjectName which is used as table index"
      ::= { persistentStoreConnectionRuntimeEntry 1  }
   
   
   persistentStoreConnectionRuntimeObjectName OBJECT-TYPE
      SYNTAX      DisplayString (SIZE (1..256))
      MAX-ACCESS  read-only
      STATUS      current
      DESCRIPTION "JMX-standard MBean name"
      ::= { persistentStoreConnectionRuntimeEntry 5  }
   
   
   persistentStoreConnectionRuntimeType OBJECT-TYPE
      SYNTAX      DisplayString (SIZE (1..64))
      MAX-ACCESS  read-only
      STATUS      current
      DESCRIPTION "Returns the type of the MBean. "
      ::= { persistentStoreConnectionRuntimeEntry 10  }
   
   
   persistentStoreConnectionRuntimeName OBJECT-TYPE
      SYNTAX      DisplayString (SIZE (1..64))
      MAX-ACCESS  read-only
      STATUS      current
      DESCRIPTION "The name of this configuration. WebLogic Server uses an MBean to implement and persist the configuration. "
      ::= { persistentStoreConnectionRuntimeEntry 15  }
   
   
   persistentStoreConnectionRuntimeParent OBJECT-TYPE
      SYNTAX      DisplayString (SIZE (1..256))
      MAX-ACCESS  read-only
      STATUS      current
      DESCRIPTION "BEA-proprietary Parent object's identification, with syntax
      <type>:<name>"
      ::= { persistentStoreConnectionRuntimeEntry 20  }
   
   
   persistentStoreConnectionRuntimeCreateCount OBJECT-TYPE
      SYNTAX      Counter64
      MAX-ACCESS  read-only
      STATUS      current
      DESCRIPTION "Number of create requests issued by this connection. "
      ::= { persistentStoreConnectionRuntimeEntry 25  }
   
   
   persistentStoreConnectionRuntimeReadCount OBJECT-TYPE
      SYNTAX      Counter64
      MAX-ACCESS  read-only
      STATUS      current
      DESCRIPTION "Number of read requests issued by this connection, including requests that occur during store initialization. "
      ::= { persistentStoreConnectionRuntimeEntry 30  }
   
   
   persistentStoreConnectionRuntimeUpdateCount OBJECT-TYPE
      SYNTAX      Counter64
      MAX-ACCESS  read-only
      STATUS      current
      DESCRIPTION "Number of update requests issued by this connection. "
      ::= { persistentStoreConnectionRuntimeEntry 35  }
   
   
   persistentStoreConnectionRuntimeDeleteCount OBJECT-TYPE
      SYNTAX      Counter64
      MAX-ACCESS  read-only
      STATUS      current
      DESCRIPTION "Number of delete requests issued by this connection. "
      ::= { persistentStoreConnectionRuntimeEntry 40  }
   
   
   persistentStoreConnectionRuntimeObjectCount OBJECT-TYPE
      SYNTAX      Counter64
      MAX-ACCESS  read-only
      STATUS      current
      DESCRIPTION "Number of objects contained in the connection. "
      ::= { persistentStoreConnectionRuntimeEntry 45  }
   
   
   jvmRuntimeTable OBJECT-TYPE
      SYNTAX      SEQUENCE OF JvmRuntimeEntry
      MAX-ACCESS  not-accessible
      STATUS      current
      DESCRIPTION "Provides methods for retrieving information about the Java Virtual Machine (JVM) within with the current server instance is running. You cannot change the JVM's operating parameters while the JVM is active. Instead, use the startup options that are described in the JVM's documentation.  The WebLogic JVM contains only one of these Runtime MBeans:   If the JVM is an instance of a JRockit JDK, then the JVM contains JRockitRuntime MBean.    Otherwise, it contains the JVMRuntimeMBean.  "
      ::= { wls 340  }
      
   
   jvmRuntimeEntry OBJECT-TYPE
      SYNTAX      JvmRuntimeEntry
      MAX-ACCESS  not-accessible
      STATUS      current
      DESCRIPTION "Entry of jvmRuntimeTable"
      INDEX { jvmRuntimeIndex}
      ::= { jvmRuntimeTable 1 }
      
   JvmRuntimeEntry ::=
      SEQUENCE
      {
         jvmRuntimeIndex      DisplayString,
         jvmRuntimeObjectName DisplayString,
         jvmRuntimeType       DisplayString,
         jvmRuntimeName       DisplayString,
         jvmRuntimeParent     DisplayString,
         jvmRuntimeHeapFreeCurrent Counter64,
         jvmRuntimeHeapSizeCurrent Counter64,
         jvmRuntimeJavaVersion DisplayString,
         jvmRuntimeJavaVendor DisplayString,
         jvmRuntimeOSName     DisplayString,
         jvmRuntimeOSVersion  DisplayString,
         jvmRuntimeUptime     Counter64,
         jvmRuntimeHeapFreePercent INTEGER,
         jvmRuntimeThreadStackDump OCTET STRING,
         jvmRuntimeHeapSizeMax Counter64,
         jvmRuntimeJavaVMVendor OCTET STRING
      }
      
   
   jvmRuntimeIndex OBJECT-TYPE
      SYNTAX      DisplayString (SIZE (1..16))
      MAX-ACCESS  read-only
      STATUS      current
      DESCRIPTION "Unique value directed from ObjectName which is used as table index"
      ::= { jvmRuntimeEntry 1  }
   
   
   jvmRuntimeObjectName OBJECT-TYPE
      SYNTAX      DisplayString (SIZE (1..256))
      MAX-ACCESS  read-only
      STATUS      current
      DESCRIPTION "JMX-standard MBean name"
      ::= { jvmRuntimeEntry 5  }
   
   
   jvmRuntimeType OBJECT-TYPE
      SYNTAX      DisplayString (SIZE (1..64))
      MAX-ACCESS  read-only
      STATUS      current
      DESCRIPTION "Returns the type of the MBean. "
      ::= { jvmRuntimeEntry 10  }
   
   
   jvmRuntimeName OBJECT-TYPE
      SYNTAX      DisplayString (SIZE (1..64))
      MAX-ACCESS  read-only
      STATUS      current
      DESCRIPTION "The name of this configuration. WebLogic Server uses an MBean to implement and persist the configuration. "
      ::= { jvmRuntimeEntry 15  }
   
   
   jvmRuntimeParent OBJECT-TYPE
      SYNTAX      DisplayString (SIZE (1..256))
      MAX-ACCESS  read-only
      STATUS      current
      DESCRIPTION "BEA-proprietary Parent object's identification, with syntax
      <type>:<name>"
      ::= { jvmRuntimeEntry 20  }
   
   
   jvmRuntimeHeapFreeCurrent OBJECT-TYPE
      SYNTAX      Counter64
      MAX-ACCESS  read-only
      STATUS      current
      DESCRIPTION "The current amount of memory (in bytes) that is available in the JVM heap. "
      ::= { jvmRuntimeEntry 25  }
   
   
   jvmRuntimeHeapSizeCurrent OBJECT-TYPE
      SYNTAX      Counter64
      MAX-ACCESS  read-only
      STATUS      current
      DESCRIPTION "The current size (in bytes) of the JVM heap. "
      ::= { jvmRuntimeEntry 30  }
   
   
   jvmRuntimeJavaVersion OBJECT-TYPE
      SYNTAX      DisplayString (SIZE (1..32))
      MAX-ACCESS  read-only
      STATUS      current
      DESCRIPTION "The Java version of the JVM. "
      ::= { jvmRuntimeEntry 35  }
   
   
   jvmRuntimeJavaVendor OBJECT-TYPE
      SYNTAX      DisplayString (SIZE (1..32))
      MAX-ACCESS  read-only
      STATUS      current
      DESCRIPTION "Returns the vendor of Java.  The vendor of Java that this server runs. "
      ::= { jvmRuntimeEntry 40  }
   
   
   jvmRuntimeOSName OBJECT-TYPE
      SYNTAX      DisplayString (SIZE (1..32))
      MAX-ACCESS  read-only
      STATUS      current
      DESCRIPTION "Returns the operating system on which the JVM is running.  The operating system on which the JVM is running. "
      ::= { jvmRuntimeEntry 45  }
   
   
   jvmRuntimeOSVersion OBJECT-TYPE
      SYNTAX      DisplayString (SIZE (1..32))
      MAX-ACCESS  read-only
      STATUS      current
      DESCRIPTION "The version of the operating system on which the JVM is running. "
      ::= { jvmRuntimeEntry 50  }
   
   
   jvmRuntimeUptime OBJECT-TYPE
      SYNTAX      Counter64
      MAX-ACCESS  read-only
      STATUS      current
      DESCRIPTION "The number of milliseconds that the Virtual Machine has been running. "
      ::= { jvmRuntimeEntry 51  }
   
   
   jvmRuntimeHeapFreePercent OBJECT-TYPE
      SYNTAX      INTEGER
      MAX-ACCESS  read-only
      STATUS      current
      DESCRIPTION "Percentage of the maximum memory that is free. "
      ::= { jvmRuntimeEntry 52  }
   
   
   jvmRuntimeThreadStackDump OBJECT-TYPE
      SYNTAX      OCTET STRING
      MAX-ACCESS  read-only
      STATUS      current
      DESCRIPTION "JVM thread dump. Thread dump is available only on 1.5 VM "
      ::= { jvmRuntimeEntry 53  }
   
   
   jvmRuntimeHeapSizeMax OBJECT-TYPE
      SYNTAX      Counter64
      MAX-ACCESS  read-only
      STATUS      current
      DESCRIPTION "The maximum free memory configured for this JVM. "
      ::= { jvmRuntimeEntry 54  }
   
   
   jvmRuntimeJavaVMVendor OBJECT-TYPE
      SYNTAX      OCTET STRING
      MAX-ACCESS  read-only
      STATUS      current
      DESCRIPTION "Returns the vendor of the JVM.  The vendor of the JVM that this server runs.  system property java.vm.vendor is returned "
      ::= { jvmRuntimeEntry 55  }
   
   
   logBroadcasterRuntimeTable OBJECT-TYPE
      SYNTAX      SEQUENCE OF LogBroadcasterRuntimeEntry
      MAX-ACCESS  not-accessible
      STATUS      current
      DESCRIPTION "This MBean broadcasts JMX notifications for each log message generated in the local WLS server. There is exactly one implementation of this MBean in each WLS server. JMX listeners can register to this MBean and receive log notifications. The type of the notification generated is WebLogicLogNotification. "
      ::= { wls 350  }
      
   
   logBroadcasterRuntimeEntry OBJECT-TYPE
      SYNTAX      LogBroadcasterRuntimeEntry
      MAX-ACCESS  not-accessible
      STATUS      current
      DESCRIPTION "Entry of logBroadcasterRuntimeTable"
      INDEX { logBroadcasterRuntimeIndex}
      ::= { logBroadcasterRuntimeTable 1 }
      
   LogBroadcasterRuntimeEntry ::=
      SEQUENCE
      {
         logBroadcasterRuntimeIndex DisplayString,
         logBroadcasterRuntimeObjectName DisplayString,
         logBroadcasterRuntimeType DisplayString,
         logBroadcasterRuntimeName DisplayString,
         logBroadcasterRuntimeParent DisplayString,
         logBroadcasterRuntimeMessagesLogged Counter64
      }
      
   
   logBroadcasterRuntimeIndex OBJECT-TYPE
      SYNTAX      DisplayString (SIZE (1..16))
      MAX-ACCESS  read-only
      STATUS      current
      DESCRIPTION "Unique value directed from ObjectName which is used as table index"
      ::= { logBroadcasterRuntimeEntry 1  }
   
   
   logBroadcasterRuntimeObjectName OBJECT-TYPE
      SYNTAX      DisplayString (SIZE (1..256))
      MAX-ACCESS  read-only
      STATUS      current
      DESCRIPTION "JMX-standard MBean name"
      ::= { logBroadcasterRuntimeEntry 5  }
   
   
   logBroadcasterRuntimeType OBJECT-TYPE
      SYNTAX      DisplayString (SIZE (1..64))
      MAX-ACCESS  read-only
      STATUS      current
      DESCRIPTION "Returns the type of the MBean. "
      ::= { logBroadcasterRuntimeEntry 10  }
   
   
   logBroadcasterRuntimeName OBJECT-TYPE
      SYNTAX      DisplayString (SIZE (1..64))
      MAX-ACCESS  read-only
      STATUS      current
      DESCRIPTION "The name of this configuration. WebLogic Server uses an MBean to implement and persist the configuration. "
      ::= { logBroadcasterRuntimeEntry 15  }
   
   
   logBroadcasterRuntimeParent OBJECT-TYPE
      SYNTAX      DisplayString (SIZE (1..256))
      MAX-ACCESS  read-only
      STATUS      current
      DESCRIPTION "BEA-proprietary Parent object's identification, with syntax
      <type>:<name>"
      ::= { logBroadcasterRuntimeEntry 20  }
   
   
   logBroadcasterRuntimeMessagesLogged OBJECT-TYPE
      SYNTAX      Counter64
      MAX-ACCESS  read-only
      STATUS      current
      DESCRIPTION "The total number of log messages that this WebLogic Server instance has generated. "
      ::= { logBroadcasterRuntimeEntry 25  }
   
   
   messageDrivenEJBRuntimeTable OBJECT-TYPE
      SYNTAX      SEQUENCE OF MessageDrivenEJBRuntimeEntry
      MAX-ACCESS  not-accessible
      STATUS      current
      DESCRIPTION "This interface contains accessor methods for all EJB runtime information collected for a Message Driven Bean. "
      ::= { wls 351  }
      
   
   messageDrivenEJBRuntimeEntry OBJECT-TYPE
      SYNTAX      MessageDrivenEJBRuntimeEntry
      MAX-ACCESS  not-accessible
      STATUS      current
      DESCRIPTION "Entry of messageDrivenEJBRuntimeTable"
      INDEX { messageDrivenEJBRuntimeIndex}
      ::= { messageDrivenEJBRuntimeTable 1 }
      
   MessageDrivenEJBRuntimeEntry ::=
      SEQUENCE
      {
         messageDrivenEJBRuntimeIndex DisplayString,
         messageDrivenEJBRuntimeObjectName DisplayString,
         messageDrivenEJBRuntimeType DisplayString,
         messageDrivenEJBRuntimeName DisplayString,
         messageDrivenEJBRuntimeParent DisplayString,
         messageDrivenEJBRuntimeJMSConnectionAlive INTEGER,
         messageDrivenEJBRuntimeLastExceptionAsString OCTET STRING,
         messageDrivenEJBRuntimeDestination OCTET STRING,
         messageDrivenEJBRuntimeMDBStatus OCTET STRING,
         messageDrivenEJBRuntimeEJBName OCTET STRING,
         messageDrivenEJBRuntimeConnectionStatus OCTET STRING,
         messageDrivenEJBRuntimeSuspendCount INTEGER,
         messageDrivenEJBRuntimeProcessedMessageCount Counter64,
         messageDrivenEJBRuntimeJmsClientID OCTET STRING,
         messageDrivenEJBRuntimeHealthState OCTET STRING
      }
      
   
   messageDrivenEJBRuntimeIndex OBJECT-TYPE
      SYNTAX      DisplayString (SIZE (1..16))
      MAX-ACCESS  read-only
      STATUS      current
      DESCRIPTION "Unique value directed from ObjectName which is used as table index"
      ::= { messageDrivenEJBRuntimeEntry 1  }
   
   
   messageDrivenEJBRuntimeObjectName OBJECT-TYPE
      SYNTAX      DisplayString (SIZE (1..256))
      MAX-ACCESS  read-only
      STATUS      current
      DESCRIPTION "JMX-standard MBean name"
      ::= { messageDrivenEJBRuntimeEntry 5  }
   
   
   messageDrivenEJBRuntimeType OBJECT-TYPE
      SYNTAX      DisplayString (SIZE (1..64))
      MAX-ACCESS  read-only
      STATUS      current
      DESCRIPTION "Returns the type of the MBean. "
      ::= { messageDrivenEJBRuntimeEntry 10  }
   
   
   messageDrivenEJBRuntimeName OBJECT-TYPE
      SYNTAX      DisplayString (SIZE (1..64))
      MAX-ACCESS  read-only
      STATUS      current
      DESCRIPTION "The name of this configuration. WebLogic Server uses an MBean to implement and persist the configuration. "
      ::= { messageDrivenEJBRuntimeEntry 15  }
   
   
   messageDrivenEJBRuntimeParent OBJECT-TYPE
      SYNTAX      DisplayString (SIZE (1..256))
      MAX-ACCESS  read-only
      STATUS      current
      DESCRIPTION "BEA-proprietary Parent object's identification, with syntax
      <type>:<name>"
      ::= { messageDrivenEJBRuntimeEntry 20  }
   
   
   messageDrivenEJBRuntimeJMSConnectionAlive OBJECT-TYPE
      SYNTAX      INTEGER
      MAX-ACCESS  read-only
      STATUS      current
      DESCRIPTION "Provides information about whether the Message Driven Bean is currently connected to the JMS destination it is mapped to.  Returns whether the Message Driven Bean is currently connected to the JMS destination it is mapped to. "
      ::= { messageDrivenEJBRuntimeEntry 25  }
   
   
   messageDrivenEJBRuntimeLastExceptionAsString OBJECT-TYPE
      SYNTAX      OCTET STRING
      MAX-ACCESS  read-only
      STATUS      current
      DESCRIPTION "Provides the last exception as String this MDB encountered "
      ::= { messageDrivenEJBRuntimeEntry 26  }
   
   
   messageDrivenEJBRuntimeDestination OBJECT-TYPE
      SYNTAX      OCTET STRING
      MAX-ACCESS  read-only
      STATUS      current
      DESCRIPTION "Provides a count of the Message Driven Bean destination "
      ::= { messageDrivenEJBRuntimeEntry 27  }
   
   
   messageDrivenEJBRuntimeMDBStatus OBJECT-TYPE
      SYNTAX      OCTET STRING
      MAX-ACCESS  read-only
      STATUS      current
      DESCRIPTION "Provides the Message Driven Bean status.  MDBStatus is used after the MDB is connected to the destination. MDBStatus can be Running or Suspended. "
      ::= { messageDrivenEJBRuntimeEntry 28  }
   
   
   messageDrivenEJBRuntimeEJBName OBJECT-TYPE
      SYNTAX      OCTET STRING
      MAX-ACCESS  read-only
      STATUS      current
      DESCRIPTION "Provides the name for this EJB as defined in the javax.ejb.EJB annotation, or the ejb-name when * using the ejb-jar.xml deployment descriptor. "
      ::= { messageDrivenEJBRuntimeEntry 29  }
   
   
   messageDrivenEJBRuntimeConnectionStatus OBJECT-TYPE
      SYNTAX      OCTET STRING
      MAX-ACCESS  read-only
      STATUS      current
      DESCRIPTION "Provides the connection status for the Message Driven Bean. ConnectionStatus can be Connected or Reconnecting. "
      ::= { messageDrivenEJBRuntimeEntry 30  }
   
   
   messageDrivenEJBRuntimeSuspendCount OBJECT-TYPE
      SYNTAX      INTEGER
      MAX-ACCESS  read-only
      STATUS      current
      DESCRIPTION "Provides a count of the total number of times this MDB is suspended by the user or the EJB container. "
      ::= { messageDrivenEJBRuntimeEntry 31  }
   
   
   messageDrivenEJBRuntimeProcessedMessageCount OBJECT-TYPE
      SYNTAX      Counter64
      MAX-ACCESS  read-only
      STATUS      current
      DESCRIPTION "Provides a count of the total number of messages processed by this Message Driven Bean. "
      ::= { messageDrivenEJBRuntimeEntry 32  }
   
   
   messageDrivenEJBRuntimeJmsClientID OBJECT-TYPE
      SYNTAX      OCTET STRING
      MAX-ACCESS  read-only
      STATUS      current
      DESCRIPTION "Provides a count of the Message Driven Bean jmsClientID "
      ::= { messageDrivenEJBRuntimeEntry 33  }
   
   
   messageDrivenEJBRuntimeHealthState OBJECT-TYPE
      SYNTAX      OCTET STRING
      MAX-ACCESS  read-only
      STATUS      current
      DESCRIPTION "The health state of this MDB. "
      ::= { messageDrivenEJBRuntimeEntry 34  }
   
   
   messagingBridgeRuntimeTable OBJECT-TYPE
      SYNTAX      SEQUENCE OF MessagingBridgeRuntimeEntry
      MAX-ACCESS  not-accessible
      STATUS      current
      DESCRIPTION "This class is used for monitoring a WebLogic messaging bridge. "
      ::= { wls 354  }
      
   
   messagingBridgeRuntimeEntry OBJECT-TYPE
      SYNTAX      MessagingBridgeRuntimeEntry
      MAX-ACCESS  not-accessible
      STATUS      current
      DESCRIPTION "Entry of messagingBridgeRuntimeTable"
      INDEX { messagingBridgeRuntimeIndex}
      ::= { messagingBridgeRuntimeTable 1 }
      
   MessagingBridgeRuntimeEntry ::=
      SEQUENCE
      {
         messagingBridgeRuntimeIndex DisplayString,
         messagingBridgeRuntimeObjectName DisplayString,
         messagingBridgeRuntimeType DisplayString,
         messagingBridgeRuntimeName DisplayString,
         messagingBridgeRuntimeParent DisplayString,
         messagingBridgeRuntimeState DisplayString,
         messagingBridgeRuntimeDescription DisplayString
      }
      
   
   messagingBridgeRuntimeIndex OBJECT-TYPE
      SYNTAX      DisplayString (SIZE (1..16))
      MAX-ACCESS  read-only
      STATUS      current
      DESCRIPTION "Unique value directed from ObjectName which is used as table index"
      ::= { messagingBridgeRuntimeEntry 1  }
   
   
   messagingBridgeRuntimeObjectName OBJECT-TYPE
      SYNTAX      DisplayString (SIZE (1..256))
      MAX-ACCESS  read-only
      STATUS      current
      DESCRIPTION "JMX-standard MBean name"
      ::= { messagingBridgeRuntimeEntry 5  }
   
   
   messagingBridgeRuntimeType OBJECT-TYPE
      SYNTAX      DisplayString (SIZE (1..64))
      MAX-ACCESS  read-only
      STATUS      current
      DESCRIPTION "Returns the type of the MBean. "
      ::= { messagingBridgeRuntimeEntry 10  }
   
   
   messagingBridgeRuntimeName OBJECT-TYPE
      SYNTAX      DisplayString (SIZE (1..64))
      MAX-ACCESS  read-only
      STATUS      current
      DESCRIPTION "The name of this configuration. WebLogic Server uses an MBean to implement and persist the configuration. "
      ::= { messagingBridgeRuntimeEntry 15  }
   
   
   messagingBridgeRuntimeParent OBJECT-TYPE
      SYNTAX      DisplayString (SIZE (1..256))
      MAX-ACCESS  read-only
      STATUS      current
      DESCRIPTION "BEA-proprietary Parent object's identification, with syntax
      <type>:<name>"
      ::= { messagingBridgeRuntimeEntry 20  }
   
   
   messagingBridgeRuntimeState OBJECT-TYPE
      SYNTAX      DisplayString
      MAX-ACCESS  read-only
      STATUS      current
      DESCRIPTION "The state of the messaging bridge. "
      ::= { messagingBridgeRuntimeEntry 21  }
   
   
   messagingBridgeRuntimeDescription OBJECT-TYPE
      SYNTAX      DisplayString
      MAX-ACCESS  read-only
      STATUS      current
      DESCRIPTION "The reason, if the messaging bridge is not running. "
      ::= { messagingBridgeRuntimeEntry 22  }
   
   
   nonXAResourceRuntimeTable OBJECT-TYPE
      SYNTAX      SEQUENCE OF NonXAResourceRuntimeEntry
      MAX-ACCESS  not-accessible
      STATUS      current
      DESCRIPTION "This represents runtime statistical information about a NonXAResource "
      ::= { wls 356  }
      
   
   nonXAResourceRuntimeEntry OBJECT-TYPE
      SYNTAX      NonXAResourceRuntimeEntry
      MAX-ACCESS  not-accessible
      STATUS      current
      DESCRIPTION "Entry of nonXAResourceRuntimeTable"
      INDEX { nonXAResourceRuntimeIndex}
      ::= { nonXAResourceRuntimeTable 1 }
      
   NonXAResourceRuntimeEntry ::=
      SEQUENCE
      {
         nonXAResourceRuntimeIndex DisplayString,
         nonXAResourceRuntimeObjectName DisplayString,
         nonXAResourceRuntimeType DisplayString,
         nonXAResourceRuntimeName DisplayString,
         nonXAResourceRuntimeParent DisplayString,
         nonXAResourceRuntimeTransactionTotalCount Counter64,
         nonXAResourceRuntimeTransactionCommittedTotalCount Counter64,
         nonXAResourceRuntimeTransactionRolledBackTotalCount Counter64,
         nonXAResourceRuntimeTransactionHeuristicsTotalCount Counter64,
         nonXAResourceRuntimeNonXAResourceName DisplayString
      }
      
   
   nonXAResourceRuntimeIndex OBJECT-TYPE
      SYNTAX      DisplayString (SIZE (1..16))
      MAX-ACCESS  read-only
      STATUS      current
      DESCRIPTION "Unique value directed from ObjectName which is used as table index"
      ::= { nonXAResourceRuntimeEntry 1  }
   
   
   nonXAResourceRuntimeObjectName OBJECT-TYPE
      SYNTAX      DisplayString (SIZE (1..256))
      MAX-ACCESS  read-only
      STATUS      current
      DESCRIPTION "JMX-standard MBean name"
      ::= { nonXAResourceRuntimeEntry 5  }
   
   
   nonXAResourceRuntimeType OBJECT-TYPE
      SYNTAX      DisplayString (SIZE (1..64))
      MAX-ACCESS  read-only
      STATUS      current
      DESCRIPTION "Returns the type of the MBean. "
      ::= { nonXAResourceRuntimeEntry 10  }
   
   
   nonXAResourceRuntimeName OBJECT-TYPE
      SYNTAX      DisplayString (SIZE (1..64))
      MAX-ACCESS  read-only
      STATUS      current
      DESCRIPTION "The name of this configuration. WebLogic Server uses an MBean to implement and persist the configuration. "
      ::= { nonXAResourceRuntimeEntry 15  }
   
   
   nonXAResourceRuntimeParent OBJECT-TYPE
      SYNTAX      DisplayString (SIZE (1..256))
      MAX-ACCESS  read-only
      STATUS      current
      DESCRIPTION "BEA-proprietary Parent object's identification, with syntax
      <type>:<name>"
      ::= { nonXAResourceRuntimeEntry 20  }
   
   
   nonXAResourceRuntimeTransactionTotalCount OBJECT-TYPE
      SYNTAX      Counter64
      MAX-ACCESS  read-only
      STATUS      current
      DESCRIPTION "The total number of transactions processed. This total includes all committed, rolled back, and heuristic transaction completions since the server was started. "
      ::= { nonXAResourceRuntimeEntry 25  }
   
   
   nonXAResourceRuntimeTransactionCommittedTotalCount OBJECT-TYPE
      SYNTAX      Counter64
      MAX-ACCESS  read-only
      STATUS      current
      DESCRIPTION "The total number of transactions committed since the server was started. "
      ::= { nonXAResourceRuntimeEntry 30  }
   
   
   nonXAResourceRuntimeTransactionRolledBackTotalCount OBJECT-TYPE
      SYNTAX      Counter64
      MAX-ACCESS  read-only
      STATUS      current
      DESCRIPTION "The number of transactions that were rolled back since the server was started. "
      ::= { nonXAResourceRuntimeEntry 35  }
   
   
   nonXAResourceRuntimeTransactionHeuristicsTotalCount OBJECT-TYPE
      SYNTAX      Counter64
      MAX-ACCESS  read-only
      STATUS      current
      DESCRIPTION "The number of transactions that completed with a heuristic status since the server was started. "
      ::= { nonXAResourceRuntimeEntry 40  }
   
   
   nonXAResourceRuntimeNonXAResourceName OBJECT-TYPE
      SYNTAX      DisplayString (SIZE (1..256))
      MAX-ACCESS  read-only
      STATUS      current
      DESCRIPTION "Returns the resource name. "
      ::= { nonXAResourceRuntimeEntry 45  }
   
   
   serverRuntimeTable OBJECT-TYPE
      SYNTAX      SEQUENCE OF ServerRuntimeEntry
      MAX-ACCESS  not-accessible
      STATUS      current
      DESCRIPTION "Provides methods for retrieving runtime information about a server instance and for transitioning a server from one state to another. "
      ::= { wls 360  }
      
   
   serverRuntimeEntry OBJECT-TYPE
      SYNTAX      ServerRuntimeEntry
      MAX-ACCESS  not-accessible
      STATUS      current
      DESCRIPTION "Entry of serverRuntimeTable"
      INDEX { serverRuntimeIndex}
      ::= { serverRuntimeTable 1 }
      
   ServerRuntimeEntry ::=
      SEQUENCE
      {
         serverRuntimeIndex   DisplayString,
         serverRuntimeObjectName DisplayString,
         serverRuntimeType    DisplayString,
         serverRuntimeName    DisplayString,
         serverRuntimeParent  DisplayString,
         serverRuntimeActivationTime Counter64,
         serverRuntimeListenAddress DisplayString,
         serverRuntimeListenPort INTEGER,
         serverRuntimeSSLListenAddress DisplayString,
         serverRuntimeOpenSocketsCurrentCount INTEGER,
         serverRuntimeRestartsTotalCount INTEGER,
         serverRuntimeState   DisplayString,
         serverRuntimeWeblogicVersion DisplayString,
         serverRuntimeAdminServerHost DisplayString,
         serverRuntimeAdminServerListenPort INTEGER,
         serverRuntimeAdministrationPort INTEGER,
         serverRuntimeSocketsOpenedTotalCount Counter64,
         serverRuntimeSSLListenPort INTEGER,
         serverRuntimeAdministrationPortEnabled INTEGER,
         serverRuntimeAdminServer INTEGER,
         serverRuntimeAdminServerListenPortSecure INTEGER,
         serverRuntimeListenPortEnabled INTEGER,
         serverRuntimeSSLListenPortEnabled INTEGER,
         serverRuntimeRestartRequired OCTET STRING,
         serverRuntimeServerClasspath OCTET STRING,
         serverRuntimeCurrentMachine OCTET STRING,
         serverRuntimeAdministrationURL OCTET STRING,
         serverRuntimeDefaultURL OCTET STRING,
         serverRuntimeStateVal INTEGER,
         serverRuntimeCurrentDirectory OCTET STRING,
         serverRuntimeWeblogicHome OCTET STRING,
         serverRuntimeOracleHome OCTET STRING,
         serverRuntimeMiddlewareHome OCTET STRING,
         serverRuntimeOverallHealthState OCTET STRING,
         serverRuntimeHealthState OCTET STRING,
         serverRuntimePatchList OCTET STRING,
         serverRuntimeInSitConfigState OCTET STRING
      }
      
   
   serverRuntimeIndex OBJECT-TYPE
      SYNTAX      DisplayString (SIZE (1..16))
      MAX-ACCESS  read-only
      STATUS      current
      DESCRIPTION "Unique value directed from ObjectName which is used as table index"
      ::= { serverRuntimeEntry 1  }
   
   
   serverRuntimeObjectName OBJECT-TYPE
      SYNTAX      DisplayString (SIZE (1..256))
      MAX-ACCESS  read-only
      STATUS      current
      DESCRIPTION "JMX-standard MBean name"
      ::= { serverRuntimeEntry 5  }
   
   
   serverRuntimeType OBJECT-TYPE
      SYNTAX      DisplayString (SIZE (1..64))
      MAX-ACCESS  read-only
      STATUS      current
      DESCRIPTION "Returns the type of the MBean. "
      ::= { serverRuntimeEntry 10  }
   
   
   serverRuntimeName OBJECT-TYPE
      SYNTAX      DisplayString (SIZE (1..64))
      MAX-ACCESS  read-only
      STATUS      current
      DESCRIPTION "The name of this configuration. WebLogic Server uses an MBean to implement and persist the configuration. "
      ::= { serverRuntimeEntry 15  }
   
   
   serverRuntimeParent OBJECT-TYPE
      SYNTAX      DisplayString (SIZE (1..256))
      MAX-ACCESS  read-only
      STATUS      current
      DESCRIPTION "BEA-proprietary Parent object's identification, with syntax
      <type>:<name>"
      ::= { serverRuntimeEntry 20  }
   
   
   serverRuntimeActivationTime OBJECT-TYPE
      SYNTAX      Counter64
      MAX-ACCESS  read-only
      STATUS      current
      DESCRIPTION "The time when the server was started. "
      ::= { serverRuntimeEntry 25  }
   
   
   serverRuntimeListenAddress OBJECT-TYPE
      SYNTAX      DisplayString (SIZE (1..256))
      MAX-ACCESS  read-only
      STATUS      current
      DESCRIPTION "The address on which this server is listening for connections through the default network channel.  For example this might return the string: santiago/172.17.9.220.  You can configure other network channels for this server, and the other channels can use different listen addresses. "
      ::= { serverRuntimeEntry 30  }
   
   
   serverRuntimeListenPort OBJECT-TYPE
      SYNTAX      INTEGER
      MAX-ACCESS  read-only
      STATUS      current
      DESCRIPTION "The port on which this server is listening for connections. "
      ::= { serverRuntimeEntry 35  }
   
   
   serverRuntimeSSLListenAddress OBJECT-TYPE
      SYNTAX      DisplayString (SIZE (1..256))
      MAX-ACCESS  read-only
      STATUS      current
      DESCRIPTION "The address on which this server is listening for SSL connections. For example this might return the string: santiago/172.17.9.220 "
      ::= { serverRuntimeEntry 40  }
   
   
   serverRuntimeOpenSocketsCurrentCount OBJECT-TYPE
      SYNTAX      INTEGER
      MAX-ACCESS  read-only
      STATUS      current
      DESCRIPTION "The current number of sockets registered for socket muxing on this server. "
      ::= { serverRuntimeEntry 50  }
   
   
   serverRuntimeRestartsTotalCount OBJECT-TYPE
      SYNTAX      INTEGER
      MAX-ACCESS  read-only
      STATUS      current
      DESCRIPTION "The total number of restarts for this server since the cluster was last started. "
      ::= { serverRuntimeEntry 55  }
   
   
   serverRuntimeState OBJECT-TYPE
      SYNTAX      DisplayString (SIZE (1..16))
      MAX-ACCESS  read-only
      STATUS      current
      DESCRIPTION "The current life cycle state of this server.  For example, a server can be in a RUNNING state in which it can receive and process requests or in an ADMIN state in which it can receive only administrative requests. "
      ::= { serverRuntimeEntry 60  }
   
   
   serverRuntimeWeblogicVersion OBJECT-TYPE
      SYNTAX      DisplayString (SIZE (1..16))
      MAX-ACCESS  read-only
      STATUS      current
      DESCRIPTION "The version of this WebLogic Server instance (server). "
      ::= { serverRuntimeEntry 65  }
   
   
   serverRuntimeAdminServerHost OBJECT-TYPE
      SYNTAX      DisplayString (SIZE (1..256))
      MAX-ACCESS  read-only
      STATUS      current
      DESCRIPTION "The address on which the Administration Server is listening for connections. For example, this might return the string: santiago "
      ::= { serverRuntimeEntry 70  }
   
   
   serverRuntimeAdminServerListenPort OBJECT-TYPE
      SYNTAX      INTEGER
      MAX-ACCESS  read-only
      STATUS      current
      DESCRIPTION "The port on which the Administration Server is listening for connections. "
      ::= { serverRuntimeEntry 75  }
   
   
   serverRuntimeAdministrationPort OBJECT-TYPE
      SYNTAX      INTEGER
      MAX-ACCESS  read-only
      STATUS      current
      DESCRIPTION "The port on which this server is listening for administrative requests. "
      ::= { serverRuntimeEntry 81  }
   
   
   serverRuntimeSocketsOpenedTotalCount OBJECT-TYPE
      SYNTAX      Counter64
      MAX-ACCESS  read-only
      STATUS      current
      DESCRIPTION "The total number of registrations for socket muxing on this sever. "
      ::= { serverRuntimeEntry 82  }
   
   
   serverRuntimeSSLListenPort OBJECT-TYPE
      SYNTAX      INTEGER
      MAX-ACCESS  read-only
      STATUS      current
      DESCRIPTION "The port on which this server is listening for SSL connections. "
      ::= { serverRuntimeEntry 83  }
   
   
   serverRuntimeAdministrationPortEnabled OBJECT-TYPE
      SYNTAX      INTEGER
      MAX-ACCESS  read-only
      STATUS      current
      DESCRIPTION "Indicates whether the administration port is enabled on the server "
      ::= { serverRuntimeEntry 84  }
   
   
   serverRuntimeAdminServer OBJECT-TYPE
      SYNTAX      INTEGER
      MAX-ACCESS  read-only
      STATUS      current
      DESCRIPTION "Indicates whether the server is an Administration Server. "
      ::= { serverRuntimeEntry 85  }
   
   
   serverRuntimeAdminServerListenPortSecure OBJECT-TYPE
      SYNTAX      INTEGER
      MAX-ACCESS  read-only
      STATUS      current
      DESCRIPTION "Indicates whether the port that the server uses for administrative traffic is configured to use a secure protocol. "
      ::= { serverRuntimeEntry 86  }
   
   
   serverRuntimeListenPortEnabled OBJECT-TYPE
      SYNTAX      INTEGER
      MAX-ACCESS  read-only
      STATUS      current
      DESCRIPTION "Indicates whether the default listen port is enabled on the server. "
      ::= { serverRuntimeEntry 87  }
   
   
   serverRuntimeSSLListenPortEnabled OBJECT-TYPE
      SYNTAX      INTEGER
      MAX-ACCESS  read-only
      STATUS      current
      DESCRIPTION "Indicates whether the default SSL listen port is enabled on the server "
      ::= { serverRuntimeEntry 88  }
   
   
   serverRuntimeRestartRequired OBJECT-TYPE
      SYNTAX      OCTET STRING
      MAX-ACCESS  read-only
      STATUS      current
      DESCRIPTION "Indicates whether the server must be restarted in order to activate configuration changes. "
      ::= { serverRuntimeEntry 89  }
   
   
   serverRuntimeServerClasspath OBJECT-TYPE
      SYNTAX      OCTET STRING
      MAX-ACCESS  read-only
      STATUS      current
      DESCRIPTION "Get the classpath for this server including domain/lib contents that are automatically picked up and appended to the classpath. "
      ::= { serverRuntimeEntry 90  }
   
   
   serverRuntimeCurrentMachine OBJECT-TYPE
      SYNTAX      OCTET STRING
      MAX-ACCESS  read-only
      STATUS      current
      DESCRIPTION "Return the machine on which the server is running. This will be different from the configuration if the server gets migrated automatically. "
      ::= { serverRuntimeEntry 91  }
   
   
   serverRuntimeAdministrationURL OBJECT-TYPE
      SYNTAX      OCTET STRING
      MAX-ACCESS  read-only
      STATUS      current
      DESCRIPTION "The URL that the server and its clients use for administrative connections.  If no administration channel is enabled, then this method returns the URL for connections through the default channel. If the default channel is de-activated, this method returns the URL for a secure channel. If no secure channel is enabled, the method returns null.  The returned URL will be consistent with dynamic channel updates. "
      ::= { serverRuntimeEntry 92  }
   
   
   serverRuntimeDefaultURL OBJECT-TYPE
      SYNTAX      OCTET STRING
      MAX-ACCESS  read-only
      STATUS      current
      DESCRIPTION "The URL that clients use to connect to this server's default network channel.  The returned value indicates the default protocol, listen address and listen port:  protocol://listen-address:listen-port  Note: The default protocol, listen address and listen port are persisted in the domain's config.xml file, however when a server instance is started, command-line options can override these persisted values. This getDefaultURL method returns the URL values that are currently being used, not necessarily the values that are specified in config.xml.  The returned URL will be consistent with dynamic channel updates. "
      ::= { serverRuntimeEntry 93  }
   
   
   serverRuntimeStateVal OBJECT-TYPE
      SYNTAX      INTEGER
      MAX-ACCESS  read-only
      STATUS      current
      DESCRIPTION "Returns current state of the server as in integer. {@link weblogic.management.runtime.ServerStates} has more information about the available server states "
      ::= { serverRuntimeEntry 94  }
   
   
   serverRuntimeCurrentDirectory OBJECT-TYPE
      SYNTAX      OCTET STRING
      MAX-ACCESS  read-only
      STATUS      current
      DESCRIPTION "The absolute path of the directory from which the server was started.  This may be used in conjunction with other relative paths in ServerMBean to compute full paths. "
      ::= { serverRuntimeEntry 95  }
   
   
   serverRuntimeWeblogicHome OBJECT-TYPE
      SYNTAX      OCTET STRING
      MAX-ACCESS  read-only
      STATUS      current
      DESCRIPTION "The directory where the WebLogic Server instance (server) is installed, without the trailing '/server'. "
      ::= { serverRuntimeEntry 96  }
   
   
   serverRuntimeOracleHome OBJECT-TYPE
      SYNTAX      OCTET STRING
      MAX-ACCESS  read-only
      STATUS      current
      DESCRIPTION "The directory where Oracle products are installed. Deprecated since 10.3.3 "
      ::= { serverRuntimeEntry 97  }
   
   
   serverRuntimeMiddlewareHome OBJECT-TYPE
      SYNTAX      OCTET STRING
      MAX-ACCESS  read-only
      STATUS      current
      DESCRIPTION "The Oracle Middleware installation directory.  "
      ::= { serverRuntimeEntry 98  }
   
   
   serverRuntimeOverallHealthState OBJECT-TYPE
      SYNTAX      OCTET STRING
      MAX-ACCESS  read-only
      STATUS      current
      DESCRIPTION " Determine the overall health state of this server, taking into account the health of each of its subsystems. "
      ::= { serverRuntimeEntry 99  }
   
   
   serverRuntimeHealthState OBJECT-TYPE
      SYNTAX      OCTET STRING
      MAX-ACCESS  read-only
      STATUS      current
      DESCRIPTION "The health state of the server as reported by the server's self-health monitoring.  For example, the server can report if it is overloaded by too many requests, if it needs more memory resources, or if it will soon fail for other reasons. "
      ::= { serverRuntimeEntry 100  }
   
   
   serverRuntimePatchList OBJECT-TYPE
      SYNTAX      OCTET STRING
      MAX-ACCESS  read-only
      STATUS      current
      DESCRIPTION "Returns information about installed patches on the server as an array of Strings. Each element of the array describes a patch, which is of the form: BugNumber;PatchID;DateApplied;Description "
      ::= { serverRuntimeEntry 101  }
   
   
   serverRuntimeInSitConfigState OBJECT-TYPE
      SYNTAX      OCTET STRING
      MAX-ACCESS  read-only
      STATUS      current
      DESCRIPTION "Returns true if sitconfig is applied. "
      ::= { serverRuntimeEntry 102  }
   
   
   serverLifeCycleRuntimeTable OBJECT-TYPE
      SYNTAX      SEQUENCE OF ServerLifeCycleRuntimeEntry
      MAX-ACCESS  not-accessible
      STATUS      current
      DESCRIPTION "Provides methods that transition servers from one state to another. This class is instantiated only on the Administration Server, but you can use it to transition the states of Managed Servers as well as Administration Servers.  You cannot use it to start an Administration Server, and if you want to use it to start Managed Servers, you must first set up a Node Manager on each Managed Server's host machine.  If you want to use the methods that transition a server into the ADMIN state, you must first set up an administration channel for that server. "
      ::= { wls 361  }
      
   
   serverLifeCycleRuntimeEntry OBJECT-TYPE
      SYNTAX      ServerLifeCycleRuntimeEntry
      MAX-ACCESS  not-accessible
      STATUS      current
      DESCRIPTION "Entry of serverLifeCycleRuntimeTable"
      INDEX { serverLifeCycleRuntimeIndex}
      ::= { serverLifeCycleRuntimeTable 1 }
      
   ServerLifeCycleRuntimeEntry ::=
      SEQUENCE
      {
         serverLifeCycleRuntimeIndex DisplayString,
         serverLifeCycleRuntimeObjectName DisplayString,
         serverLifeCycleRuntimeType DisplayString,
         serverLifeCycleRuntimeName DisplayString,
         serverLifeCycleRuntimeParent DisplayString,
         serverLifeCycleRuntimeState DisplayString,
         serverLifeCycleRuntimeNodeManagerRestartCount INTEGER,
         serverLifeCycleRuntimeMiddlewareHome OCTET STRING,
         serverLifeCycleRuntimeWeblogicHome OCTET STRING
      }
      
   
   serverLifeCycleRuntimeIndex OBJECT-TYPE
      SYNTAX      DisplayString (SIZE (1..16))
      MAX-ACCESS  read-only
      STATUS      current
      DESCRIPTION "Unique value directed from ObjectName which is used as table index"
      ::= { serverLifeCycleRuntimeEntry 1  }
   
   
   serverLifeCycleRuntimeObjectName OBJECT-TYPE
      SYNTAX      DisplayString (SIZE (1..256))
      MAX-ACCESS  read-only
      STATUS      current
      DESCRIPTION "JMX-standard MBean name"
      ::= { serverLifeCycleRuntimeEntry 5  }
   
   
   serverLifeCycleRuntimeType OBJECT-TYPE
      SYNTAX      DisplayString (SIZE (1..64))
      MAX-ACCESS  read-only
      STATUS      current
      DESCRIPTION "Returns the type of the MBean. "
      ::= { serverLifeCycleRuntimeEntry 10  }
   
   
   serverLifeCycleRuntimeName OBJECT-TYPE
      SYNTAX      DisplayString (SIZE (1..64))
      MAX-ACCESS  read-only
      STATUS      current
      DESCRIPTION "The name of this configuration. WebLogic Server uses an MBean to implement and persist the configuration. "
      ::= { serverLifeCycleRuntimeEntry 15  }
   
   
   serverLifeCycleRuntimeParent OBJECT-TYPE
      SYNTAX      DisplayString (SIZE (1..256))
      MAX-ACCESS  read-only
      STATUS      current
      DESCRIPTION "BEA-proprietary Parent object's identification, with syntax
      <type>:<name>"
      ::= { serverLifeCycleRuntimeEntry 20  }
   
   
   serverLifeCycleRuntimeState OBJECT-TYPE
      SYNTAX      DisplayString
      MAX-ACCESS  read-only
      STATUS      current
      DESCRIPTION "The current state of the server. "
      ::= { serverLifeCycleRuntimeEntry 25  }
   
   
   serverLifeCycleRuntimeNodeManagerRestartCount OBJECT-TYPE
      SYNTAX      INTEGER
      MAX-ACCESS  read-only
      STATUS      current
      DESCRIPTION "Number of times the server has been restarted using the NodeManager since creation. The first start does not count. The count is valid only if the NodeManager is used to start and restart the server everytime. "
      ::= { serverLifeCycleRuntimeEntry 31  }
   
   
   serverLifeCycleRuntimeMiddlewareHome OBJECT-TYPE
      SYNTAX      OCTET STRING
      MAX-ACCESS  read-only
      STATUS      current
      DESCRIPTION "The Oracle Middleware installation directory.  "
      ::= { serverLifeCycleRuntimeEntry 32  }
   
   
   serverLifeCycleRuntimeWeblogicHome OBJECT-TYPE
      SYNTAX      OCTET STRING
      MAX-ACCESS  read-only
      STATUS      current
      DESCRIPTION "The directory where the WebLogic Server instance (server) is installed, without the trailing '/server'. "
      ::= { serverLifeCycleRuntimeEntry 33  }
   
   
   manReplicationRuntimeTable OBJECT-TYPE
      SYNTAX      SEQUENCE OF ManReplicationRuntimeEntry
      MAX-ACCESS  not-accessible
      STATUS      current
      DESCRIPTION "RuntimeMBean for MAN Replication "
      ::= { wls 362  }
      
   
   manReplicationRuntimeEntry OBJECT-TYPE
      SYNTAX      ManReplicationRuntimeEntry
      MAX-ACCESS  not-accessible
      STATUS      current
      DESCRIPTION "Entry of MANReplicationRuntimeTable"
      INDEX { manReplicationRuntimeIndex}
      ::= { manReplicationRuntimeTable 1 }
      
   ManReplicationRuntimeEntry ::=
      SEQUENCE
      {
         manReplicationRuntimeIndex DisplayString,
         manReplicationRuntimeObjectName DisplayString,
         manReplicationRuntimeType DisplayString,
         manReplicationRuntimeName DisplayString,
         manReplicationRuntimeParent DisplayString,
         manReplicationRuntimeSecondaryServerName DisplayString,
         manReplicationRuntimeSecondaryServerDetails DisplayString,
         manReplicationRuntimePrimaryCount Counter64,
         manReplicationRuntimeSecondaryCount Counter64,
         manReplicationRuntimeRemoteClusterReachable INTEGER,
         manReplicationRuntimeDetailedSecondariesDistribution OCTET STRING,
         manReplicationRuntimeActiveServersInRemoteCluster OCTET STRING
      }
      
   
   manReplicationRuntimeIndex OBJECT-TYPE
      SYNTAX      DisplayString (SIZE (1..16))
      MAX-ACCESS  read-only
      STATUS      current
      DESCRIPTION "Unique value directed from ObjectName which is used as table index"
      ::= { manReplicationRuntimeEntry 1  }
   
   
   manReplicationRuntimeObjectName OBJECT-TYPE
      SYNTAX      DisplayString (SIZE (1..256))
      MAX-ACCESS  read-only
      STATUS      current
      DESCRIPTION "JMX-standard MBean name"
      ::= { manReplicationRuntimeEntry 5  }
   
   
   manReplicationRuntimeType OBJECT-TYPE
      SYNTAX      DisplayString (SIZE (1..64))
      MAX-ACCESS  read-only
      STATUS      current
      DESCRIPTION "Returns the type of the MBean. "
      ::= { manReplicationRuntimeEntry 10  }
   
   
   manReplicationRuntimeName OBJECT-TYPE
      SYNTAX      DisplayString (SIZE (1..64))
      MAX-ACCESS  read-only
      STATUS      current
      DESCRIPTION "The name of this configuration. WebLogic Server uses an MBean to implement and persist the configuration. "
      ::= { manReplicationRuntimeEntry 15  }
   
   
   manReplicationRuntimeParent OBJECT-TYPE
      SYNTAX      DisplayString (SIZE (1..256))
      MAX-ACCESS  read-only
      STATUS      current
      DESCRIPTION "BEA-proprietary Parent object's identification, with syntax
      <type>:<name>"
      ::= { manReplicationRuntimeEntry 20  }
   
   
   manReplicationRuntimeSecondaryServerName OBJECT-TYPE
      SYNTAX      DisplayString (SIZE (1..128))
      MAX-ACCESS  read-only
      STATUS      current
      DESCRIPTION " Answer the name of the secondary server  "
      ::= { manReplicationRuntimeEntry 25  }
   
   
   manReplicationRuntimeSecondaryServerDetails OBJECT-TYPE
      SYNTAX      DisplayString (SIZE (1..256))
      MAX-ACCESS  read-only
      STATUS      current
      DESCRIPTION " "
      ::= { manReplicationRuntimeEntry 30  }
   
   
   manReplicationRuntimePrimaryCount OBJECT-TYPE
      SYNTAX      Counter64
      MAX-ACCESS  read-only
      STATUS      current
      DESCRIPTION "Provides the number of object that the local server hosts as primaries.  Answer the number of object that the local server hosts as primaries. "
      ::= { manReplicationRuntimeEntry 35  }
   
   
   manReplicationRuntimeSecondaryCount OBJECT-TYPE
      SYNTAX      Counter64
      MAX-ACCESS  read-only
      STATUS      current
      DESCRIPTION "Answer the number of object that the local server hosts as secondaries. "
      ::= { manReplicationRuntimeEntry 40  }
   
   
   manReplicationRuntimeRemoteClusterReachable OBJECT-TYPE
      SYNTAX      INTEGER
                  {
                     true(1),
                     false(2)
                  }
      
      MAX-ACCESS  read-only
      STATUS      current
      DESCRIPTION "Answer if the remote cluster is reachable or not. "
      ::= { manReplicationRuntimeEntry 45  }
   
   
   manReplicationRuntimeDetailedSecondariesDistribution OBJECT-TYPE
      SYNTAX      OCTET STRING
      MAX-ACCESS  read-only
      STATUS      current
      DESCRIPTION "Provides the names of the remote servers (such as myserver) for which the local server is hosting secondary objects. The name is appended with a number to indicate the number of secondaries hosted on behalf of that server. "
      ::= { manReplicationRuntimeEntry 46  }
   
   
   manReplicationRuntimeActiveServersInRemoteCluster OBJECT-TYPE
      SYNTAX      OCTET STRING
      MAX-ACCESS  read-only
      STATUS      current
      DESCRIPTION " "
      ::= { manReplicationRuntimeEntry 47  }
   
   
   maxThreadsConstraintRuntimeTable OBJECT-TYPE
      SYNTAX      SEQUENCE OF MaxThreadsConstraintRuntimeEntry
      MAX-ACCESS  not-accessible
      STATUS      current
      DESCRIPTION "Runtime information for MaxThreadsConstraint "
      ::= { wls 363  }
      
   
   maxThreadsConstraintRuntimeEntry OBJECT-TYPE
      SYNTAX      MaxThreadsConstraintRuntimeEntry
      MAX-ACCESS  not-accessible
      STATUS      current
      DESCRIPTION "Entry of maxThreadsConstraintRuntimeTable"
      INDEX { maxThreadsConstraintRuntimeIndex}
      ::= { maxThreadsConstraintRuntimeTable 1 }
      
   MaxThreadsConstraintRuntimeEntry ::=
      SEQUENCE
      {
         maxThreadsConstraintRuntimeIndex DisplayString,
         maxThreadsConstraintRuntimeObjectName DisplayString,
         maxThreadsConstraintRuntimeType DisplayString,
         maxThreadsConstraintRuntimeName DisplayString,
         maxThreadsConstraintRuntimeParent DisplayString,
         maxThreadsConstraintRuntimeExecutingRequests INTEGER,
         maxThreadsConstraintRuntimeDeferredRequests INTEGER,
         maxThreadsConstraintRuntimeConfiguredCount INTEGER,
         maxThreadsConstraintRuntimeCount INTEGER
      }
      
   
   maxThreadsConstraintRuntimeIndex OBJECT-TYPE
      SYNTAX      DisplayString (SIZE (1..16))
      MAX-ACCESS  read-only
      STATUS      current
      DESCRIPTION "Unique value directed from ObjectName which is used as table index"
      ::= { maxThreadsConstraintRuntimeEntry 1  }
   
   
   maxThreadsConstraintRuntimeObjectName OBJECT-TYPE
      SYNTAX      DisplayString (SIZE (1..256))
      MAX-ACCESS  read-only
      STATUS      current
      DESCRIPTION "JMX-standard MBean name"
      ::= { maxThreadsConstraintRuntimeEntry 5  }
   
   
   maxThreadsConstraintRuntimeType OBJECT-TYPE
      SYNTAX      DisplayString (SIZE (1..64))
      MAX-ACCESS  read-only
      STATUS      current
      DESCRIPTION "Returns the type of the MBean. "
      ::= { maxThreadsConstraintRuntimeEntry 10  }
   
   
   maxThreadsConstraintRuntimeName OBJECT-TYPE
      SYNTAX      DisplayString (SIZE (1..64))
      MAX-ACCESS  read-only
      STATUS      current
      DESCRIPTION "The name of this configuration. WebLogic Server uses an MBean to implement and persist the configuration. "
      ::= { maxThreadsConstraintRuntimeEntry 15  }
   
   
   maxThreadsConstraintRuntimeParent OBJECT-TYPE
      SYNTAX      DisplayString (SIZE (1..256))
      MAX-ACCESS  read-only
      STATUS      current
      DESCRIPTION "BEA-proprietary Parent object's identification, with syntax
      <type>:<name>"
      ::= { maxThreadsConstraintRuntimeEntry 20  }
   
   
   maxThreadsConstraintRuntimeExecutingRequests OBJECT-TYPE
      SYNTAX      INTEGER
      MAX-ACCESS  read-only
      STATUS      current
      DESCRIPTION "Number of requests that are currently executing. "
      ::= { maxThreadsConstraintRuntimeEntry 25  }
   
   
   maxThreadsConstraintRuntimeDeferredRequests OBJECT-TYPE
      SYNTAX      INTEGER
      MAX-ACCESS  read-only
      STATUS      current
      DESCRIPTION "Number of requests that are denied a thread for execution because the constraint is exceeded. "
      ::= { maxThreadsConstraintRuntimeEntry 30  }
   
   
   maxThreadsConstraintRuntimeConfiguredCount OBJECT-TYPE
      SYNTAX      INTEGER
      MAX-ACCESS  read-only
      STATUS      current
      DESCRIPTION "The configured count, or maximum concurrency value. "
      ::= { maxThreadsConstraintRuntimeEntry 31  }
   
   
   maxThreadsConstraintRuntimeCount OBJECT-TYPE
      SYNTAX      INTEGER
      MAX-ACCESS  read-only
      STATUS      current
      DESCRIPTION "The current maximum concurrency value. This could be different from the configured value as Resource Consumption Management could dynamically reduce the allowed maximum concurrency value based on configured RCM policies and actual thread usage by the partition "
      ::= { maxThreadsConstraintRuntimeEntry 32  }
   
   
   minThreadsConstraintRuntimeTable OBJECT-TYPE
      SYNTAX      SEQUENCE OF MinThreadsConstraintRuntimeEntry
      MAX-ACCESS  not-accessible
      STATUS      current
      DESCRIPTION "Monitoring information for MinThreadsConstraint "
      ::= { wls 364  }
      
   
   minThreadsConstraintRuntimeEntry OBJECT-TYPE
      SYNTAX      MinThreadsConstraintRuntimeEntry
      MAX-ACCESS  not-accessible
      STATUS      current
      DESCRIPTION "Entry of minThreadsConstraintRuntimeTable"
      INDEX { minThreadsConstraintRuntimeIndex}
      ::= { minThreadsConstraintRuntimeTable 1 }
      
   MinThreadsConstraintRuntimeEntry ::=
      SEQUENCE
      {
         minThreadsConstraintRuntimeIndex DisplayString,
         minThreadsConstraintRuntimeObjectName DisplayString,
         minThreadsConstraintRuntimeType DisplayString,
         minThreadsConstraintRuntimeName DisplayString,
         minThreadsConstraintRuntimeParent DisplayString,
         minThreadsConstraintRuntimeCompletedRequests Counter64,
         minThreadsConstraintRuntimePendingRequests INTEGER,
         minThreadsConstraintRuntimeExecutingRequests INTEGER,
         minThreadsConstraintRuntimeOutOfOrderExecutionCount Counter64,
         minThreadsConstraintRuntimeMustRunCount INTEGER,
         minThreadsConstraintRuntimeMaxWaitTime Counter64,
         minThreadsConstraintRuntimeCurrentWaitTime Counter64,
         minThreadsConstraintRuntimeConfiguredCount INTEGER,
         minThreadsConstraintRuntimeCount INTEGER,
         minThreadsConstraintRuntimePartitionLimitReached OCTET STRING
      }
      
   
   minThreadsConstraintRuntimeIndex OBJECT-TYPE
      SYNTAX      DisplayString (SIZE (1..16))
      MAX-ACCESS  read-only
      STATUS      current
      DESCRIPTION "Unique value directed from ObjectName which is used as table index"
      ::= { minThreadsConstraintRuntimeEntry 1  }
   
   
   minThreadsConstraintRuntimeObjectName OBJECT-TYPE
      SYNTAX      DisplayString (SIZE (1..256))
      MAX-ACCESS  read-only
      STATUS      current
      DESCRIPTION "JMX-standard MBean name"
      ::= { minThreadsConstraintRuntimeEntry 5  }
   
   
   minThreadsConstraintRuntimeType OBJECT-TYPE
      SYNTAX      DisplayString (SIZE (1..64))
      MAX-ACCESS  read-only
      STATUS      current
      DESCRIPTION "Returns the type of the MBean. "
      ::= { minThreadsConstraintRuntimeEntry 10  }
   
   
   minThreadsConstraintRuntimeName OBJECT-TYPE
      SYNTAX      DisplayString (SIZE (1..64))
      MAX-ACCESS  read-only
      STATUS      current
      DESCRIPTION "The name of this configuration. WebLogic Server uses an MBean to implement and persist the configuration. "
      ::= { minThreadsConstraintRuntimeEntry 15  }
   
   
   minThreadsConstraintRuntimeParent OBJECT-TYPE
      SYNTAX      DisplayString (SIZE (1..256))
      MAX-ACCESS  read-only
      STATUS      current
      DESCRIPTION "BEA-proprietary Parent object's identification, with syntax
      <type>:<name>"
      ::= { minThreadsConstraintRuntimeEntry 20  }
   
   
   minThreadsConstraintRuntimeCompletedRequests OBJECT-TYPE
      SYNTAX      Counter64
      MAX-ACCESS  read-only
      STATUS      current
      DESCRIPTION "Completed request count. "
      ::= { minThreadsConstraintRuntimeEntry 25  }
   
   
   minThreadsConstraintRuntimePendingRequests OBJECT-TYPE
      SYNTAX      INTEGER
      MAX-ACCESS  read-only
      STATUS      current
      DESCRIPTION "Pending requests that are waiting for an available thread. "
      ::= { minThreadsConstraintRuntimeEntry 30  }
   
   
   minThreadsConstraintRuntimeExecutingRequests OBJECT-TYPE
      SYNTAX      INTEGER
      MAX-ACCESS  read-only
      STATUS      current
      DESCRIPTION "Number of requests that are currently executing. "
      ::= { minThreadsConstraintRuntimeEntry 35  }
   
   
   minThreadsConstraintRuntimeOutOfOrderExecutionCount OBJECT-TYPE
      SYNTAX      Counter64
      MAX-ACCESS  read-only
      STATUS      current
      DESCRIPTION "Number of requests executed out of turn to satisfy this constraint. "
      ::= { minThreadsConstraintRuntimeEntry 40  }
   
   
   minThreadsConstraintRuntimeMustRunCount OBJECT-TYPE
      SYNTAX      INTEGER
      MAX-ACCESS  read-only
      STATUS      current
      DESCRIPTION "Number of requests that must be executed to satisfy the constraint. "
      ::= { minThreadsConstraintRuntimeEntry 45  }
   
   
   minThreadsConstraintRuntimeMaxWaitTime OBJECT-TYPE
      SYNTAX      Counter64
      MAX-ACCESS  read-only
      STATUS      current
      DESCRIPTION "The max time a request had to wait for a thread, in milliseconds. Only requests whose execution is needed to satisfy the constraint are considered. "
      ::= { minThreadsConstraintRuntimeEntry 50  }
   
   
   minThreadsConstraintRuntimeCurrentWaitTime OBJECT-TYPE
      SYNTAX      Counter64
      MAX-ACCESS  read-only
      STATUS      current
      DESCRIPTION "The last measured time a request had to wait for a thread, in milliseconds. Only requests whose execution is needed to satisfy the constraint are considered. "
      ::= { minThreadsConstraintRuntimeEntry 55  }
   
   
   minThreadsConstraintRuntimeConfiguredCount OBJECT-TYPE
      SYNTAX      INTEGER
      MAX-ACCESS  read-only
      STATUS      current
      DESCRIPTION "The configured count, or minimum concurrency value. "
      ::= { minThreadsConstraintRuntimeEntry 56  }
   
   
   minThreadsConstraintRuntimeCount OBJECT-TYPE
      SYNTAX      INTEGER
      MAX-ACCESS  read-only
      STATUS      current
      DESCRIPTION "The current minimum concurrency value. This could be different from the configured value as Resource Consumption Management could dynamically reduce the allowed minimum concurrency value based on configured RCM policies and actual thread usage by the partition "
      ::= { minThreadsConstraintRuntimeEntry 57  }
   
   
   minThreadsConstraintRuntimePartitionLimitReached OBJECT-TYPE
      SYNTAX      OCTET STRING
      MAX-ACCESS  read-only
      STATUS      current
      DESCRIPTION "Whether the partition-level minimum threads constraint limit has reached, which could cause the number of executing requests to be less than the configured value in this minimum threads constraint.  "
      ::= { minThreadsConstraintRuntimeEntry 58  }
   
   
   requestClassRuntimeTable OBJECT-TYPE
      SYNTAX      SEQUENCE OF RequestClassRuntimeEntry
      MAX-ACCESS  not-accessible
      STATUS      current
      DESCRIPTION "RequestClassRuntimeMBean presents runtime information about RequestClasses. A request class represents a class of work. Work using the same request class shares the same priority. "
      ::= { wls 365  }
      
   
   requestClassRuntimeEntry OBJECT-TYPE
      SYNTAX      RequestClassRuntimeEntry
      MAX-ACCESS  not-accessible
      STATUS      current
      DESCRIPTION "Entry of requestClassRuntimeTable"
      INDEX { requestClassRuntimeIndex}
      ::= { requestClassRuntimeTable 1 }
      
   RequestClassRuntimeEntry ::=
      SEQUENCE
      {
         requestClassRuntimeIndex DisplayString,
         requestClassRuntimeObjectName DisplayString,
         requestClassRuntimeType DisplayString,
         requestClassRuntimeName DisplayString,
         requestClassRuntimeParent DisplayString,
         requestClassRuntimeCompletedCount Counter64,
         requestClassRuntimeTotalThreadUse Counter64,
         requestClassRuntimePendingRequestCount INTEGER,
         requestClassRuntimeVirtualTimeIncrement Counter64,
         requestClassRuntimeRequestClassType DisplayString
      }
      
   
   requestClassRuntimeIndex OBJECT-TYPE
      SYNTAX      DisplayString (SIZE (1..16))
      MAX-ACCESS  read-only
      STATUS      current
      DESCRIPTION "Unique value directed from ObjectName which is used as table index"
      ::= { requestClassRuntimeEntry 1  }
   
   
   requestClassRuntimeObjectName OBJECT-TYPE
      SYNTAX      DisplayString (SIZE (1..256))
      MAX-ACCESS  read-only
      STATUS      current
      DESCRIPTION "JMX-standard MBean name"
      ::= { requestClassRuntimeEntry 5  }
   
   
   requestClassRuntimeType OBJECT-TYPE
      SYNTAX      DisplayString (SIZE (1..64))
      MAX-ACCESS  read-only
      STATUS      current
      DESCRIPTION "Returns the type of the MBean. "
      ::= { requestClassRuntimeEntry 10  }
   
   
   requestClassRuntimeName OBJECT-TYPE
      SYNTAX      DisplayString (SIZE (1..64))
      MAX-ACCESS  read-only
      STATUS      current
      DESCRIPTION "The name of this configuration. WebLogic Server uses an MBean to implement and persist the configuration. "
      ::= { requestClassRuntimeEntry 15  }
   
   
   requestClassRuntimeParent OBJECT-TYPE
      SYNTAX      DisplayString (SIZE (1..256))
      MAX-ACCESS  read-only
      STATUS      current
      DESCRIPTION "BEA-proprietary Parent object's identification, with syntax
      <type>:<name>"
      ::= { requestClassRuntimeEntry 20  }
   
   
   requestClassRuntimeCompletedCount OBJECT-TYPE
      SYNTAX      Counter64
      MAX-ACCESS  read-only
      STATUS      current
      DESCRIPTION "Total number of completions since server start "
      ::= { requestClassRuntimeEntry 25  }
   
   
   requestClassRuntimeTotalThreadUse OBJECT-TYPE
      SYNTAX      Counter64
      MAX-ACCESS  read-only
      STATUS      current
      DESCRIPTION "Total amount of thread use time in millisec's used by the request class since server start. "
      ::= { requestClassRuntimeEntry 30  }
   
   
   requestClassRuntimePendingRequestCount OBJECT-TYPE
      SYNTAX      INTEGER
      MAX-ACCESS  read-only
      STATUS      current
      DESCRIPTION "Number of requests waiting for a thread to become available. "
      ::= { requestClassRuntimeEntry 35  }
   
   
   requestClassRuntimeVirtualTimeIncrement OBJECT-TYPE
      SYNTAX      Counter64
      MAX-ACCESS  read-only
      STATUS      current
      DESCRIPTION "Current priority of the request class. The priority is relative to other request class priorities. The priority is calculated dynamically frequently and can change. "
      ::= { requestClassRuntimeEntry 40  }
   
   
   requestClassRuntimeRequestClassType OBJECT-TYPE
      SYNTAX      DisplayString (SIZE (1..64))
      MAX-ACCESS  read-only
      STATUS      current
      DESCRIPTION "Returns the type of RequestClass. Either FAIR_SHARE or RESPONSE_TIME or CONTEXT "
      ::= { requestClassRuntimeEntry 45  }
   
   
   serverChannelRuntimeTable OBJECT-TYPE
      SYNTAX      SEQUENCE OF ServerChannelRuntimeEntry
      MAX-ACCESS  not-accessible
      STATUS      current
      DESCRIPTION "Runtime information for NetworkAccessPoints or 'Channels'. "
      ::= { wls 366  }
      
   
   serverChannelRuntimeEntry OBJECT-TYPE
      SYNTAX      ServerChannelRuntimeEntry
      MAX-ACCESS  not-accessible
      STATUS      current
      DESCRIPTION "Entry of serverChannelRuntimeTable"
      INDEX { serverChannelRuntimeIndex}
      ::= { serverChannelRuntimeTable 1 }
      
   ServerChannelRuntimeEntry ::=
      SEQUENCE
      {
         serverChannelRuntimeIndex DisplayString,
         serverChannelRuntimeObjectName DisplayString,
         serverChannelRuntimeType DisplayString,
         serverChannelRuntimeName DisplayString,
         serverChannelRuntimeParent DisplayString,
         serverChannelRuntimeBytesReceivedCount Counter64,
         serverChannelRuntimeBytesSentCount Counter64,
         serverChannelRuntimeChannelName DisplayString,
         serverChannelRuntimeConnectionsCount Counter64,
         serverChannelRuntimeAcceptCount Counter64,
         serverChannelRuntimeMessagesReceivedCount Counter64,
         serverChannelRuntimeMessagesSentCount Counter64,
         serverChannelRuntimePublicURL DisplayString,
         serverChannelRuntimeAssociatedVirtualTargetName OCTET STRING
      }
      
   
   serverChannelRuntimeIndex OBJECT-TYPE
      SYNTAX      DisplayString (SIZE (1..16))
      MAX-ACCESS  read-only
      STATUS      current
      DESCRIPTION "Unique value directed from ObjectName which is used as table index"
      ::= { serverChannelRuntimeEntry 1  }
   
   
   serverChannelRuntimeObjectName OBJECT-TYPE
      SYNTAX      DisplayString (SIZE (1..256))
      MAX-ACCESS  read-only
      STATUS      current
      DESCRIPTION "JMX-standard MBean name"
      ::= { serverChannelRuntimeEntry 5  }
   
   
   serverChannelRuntimeType OBJECT-TYPE
      SYNTAX      DisplayString (SIZE (1..64))
      MAX-ACCESS  read-only
      STATUS      current
      DESCRIPTION "Returns the type of the MBean. "
      ::= { serverChannelRuntimeEntry 10  }
   
   
   serverChannelRuntimeName OBJECT-TYPE
      SYNTAX      DisplayString (SIZE (1..64))
      MAX-ACCESS  read-only
      STATUS      current
      DESCRIPTION "The name of this configuration. WebLogic Server uses an MBean to implement and persist the configuration. "
      ::= { serverChannelRuntimeEntry 15  }
   
   
   serverChannelRuntimeParent OBJECT-TYPE
      SYNTAX      DisplayString (SIZE (1..256))
      MAX-ACCESS  read-only
      STATUS      current
      DESCRIPTION "BEA-proprietary Parent object's identification, with syntax
      <type>:<name>"
      ::= { serverChannelRuntimeEntry 20  }
   
   
   serverChannelRuntimeBytesReceivedCount OBJECT-TYPE
      SYNTAX      Counter64
      MAX-ACCESS  read-only
      STATUS      current
      DESCRIPTION "The total number of bytes received on this channel. "
      ::= { serverChannelRuntimeEntry 25  }
   
   
   serverChannelRuntimeBytesSentCount OBJECT-TYPE
      SYNTAX      Counter64
      MAX-ACCESS  read-only
      STATUS      current
      DESCRIPTION "The total number of bytes sent on this channel. "
      ::= { serverChannelRuntimeEntry 30  }
   
   
   serverChannelRuntimeChannelName OBJECT-TYPE
      SYNTAX      DisplayString (SIZE (1..64))
      MAX-ACCESS  read-only
      STATUS      current
      DESCRIPTION "The channel name of this channel. "
      ::= { serverChannelRuntimeEntry 35  }
   
   
   serverChannelRuntimeConnectionsCount OBJECT-TYPE
      SYNTAX      Counter64
      MAX-ACCESS  read-only
      STATUS      current
      DESCRIPTION "The number of active connections and sockets associated with this channel. "
      ::= { serverChannelRuntimeEntry 40  }
   
   
   serverChannelRuntimeAcceptCount OBJECT-TYPE
      SYNTAX      Counter64
      MAX-ACCESS  read-only
      STATUS      current
      DESCRIPTION "The number of sockets that have been accepted on this channel. This includes sockets both past and present so gives a good idea of the connection rate to the server. "
      ::= { serverChannelRuntimeEntry 45  }
   
   
   serverChannelRuntimeMessagesReceivedCount OBJECT-TYPE
      SYNTAX      Counter64
      MAX-ACCESS  read-only
      STATUS      current
      DESCRIPTION "The number of messages received on this channel. "
      ::= { serverChannelRuntimeEntry 50  }
   
   
   serverChannelRuntimeMessagesSentCount OBJECT-TYPE
      SYNTAX      Counter64
      MAX-ACCESS  read-only
      STATUS      current
      DESCRIPTION "The number of messages sent on this channel. "
      ::= { serverChannelRuntimeEntry 55  }
   
   
   serverChannelRuntimePublicURL OBJECT-TYPE
      SYNTAX      DisplayString (SIZE (1..128))
      MAX-ACCESS  read-only
      STATUS      current
      DESCRIPTION "The physical URL that this channel is listening on. "
      ::= { serverChannelRuntimeEntry 60  }
   
   
   serverChannelRuntimeAssociatedVirtualTargetName OBJECT-TYPE
      SYNTAX      OCTET STRING
      MAX-ACCESS  read-only
      STATUS      current
      DESCRIPTION "Associated virtual-target name with this channel. This may be null. "
      ::= { serverChannelRuntimeEntry 61  }
   
   
   threadPoolRuntimeTable OBJECT-TYPE
      SYNTAX      SEQUENCE OF ThreadPoolRuntimeEntry
      MAX-ACCESS  not-accessible
      STATUS      current
      DESCRIPTION "This bean is used to monitor the self-tuning queue "
      ::= { wls 367  }
      
   
   threadPoolRuntimeEntry OBJECT-TYPE
      SYNTAX      ThreadPoolRuntimeEntry
      MAX-ACCESS  not-accessible
      STATUS      current
      DESCRIPTION "Entry of threadPoolRuntimeTable"
      INDEX { threadPoolRuntimeIndex}
      ::= { threadPoolRuntimeTable 1 }
      
   ThreadPoolRuntimeEntry ::=
      SEQUENCE
      {
         threadPoolRuntimeIndex DisplayString,
         threadPoolRuntimeObjectName DisplayString,
         threadPoolRuntimeType DisplayString,
         threadPoolRuntimeName DisplayString,
         threadPoolRuntimeParent DisplayString,
         threadPoolRuntimeExecuteThreadTotalCount INTEGER,
         threadPoolRuntimeExecuteThreadIdleCount INTEGER,
         threadPoolRuntimeQueueLength INTEGER,
         threadPoolRuntimePendingUserRequestCount INTEGER,
         threadPoolRuntimeSharedCapacityForWorkManagers INTEGER,
         threadPoolRuntimeCompletedRequestCount Counter64,
         threadPoolRuntimeHoggingThreadCount INTEGER,
         threadPoolRuntimeStandbyThreadCount INTEGER,
         threadPoolRuntimeThroughput DisplayString,
         threadPoolRuntimeMinThreadsConstraintsPending INTEGER,
         threadPoolRuntimeMinThreadsConstraintsCompleted Counter64,
         threadPoolRuntimeSuspended INTEGER,
         threadPoolRuntimeStuckThreadCount INTEGER,
         threadPoolRuntimeOverloadRejectedRequestsCount INTEGER,
         threadPoolRuntimeHealthState OCTET STRING
      }
      
   
   threadPoolRuntimeIndex OBJECT-TYPE
      SYNTAX      DisplayString (SIZE (1..16))
      MAX-ACCESS  read-only
      STATUS      current
      DESCRIPTION "Unique value directed from ObjectName which is used as table index"
      ::= { threadPoolRuntimeEntry 1  }
   
   
   threadPoolRuntimeObjectName OBJECT-TYPE
      SYNTAX      DisplayString (SIZE (1..256))
      MAX-ACCESS  read-only
      STATUS      current
      DESCRIPTION "JMX-standard MBean name"
      ::= { threadPoolRuntimeEntry 5  }
   
   
   threadPoolRuntimeType OBJECT-TYPE
      SYNTAX      DisplayString (SIZE (1..64))
      MAX-ACCESS  read-only
      STATUS      current
      DESCRIPTION "Returns the type of the MBean. "
      ::= { threadPoolRuntimeEntry 10  }
   
   
   threadPoolRuntimeName OBJECT-TYPE
      SYNTAX      DisplayString (SIZE (1..64))
      MAX-ACCESS  read-only
      STATUS      current
      DESCRIPTION "The name of this configuration. WebLogic Server uses an MBean to implement and persist the configuration. "
      ::= { threadPoolRuntimeEntry 15  }
   
   
   threadPoolRuntimeParent OBJECT-TYPE
      SYNTAX      DisplayString (SIZE (1..256))
      MAX-ACCESS  read-only
      STATUS      current
      DESCRIPTION "BEA-proprietary Parent object's identification, with syntax
      <type>:<name>"
      ::= { threadPoolRuntimeEntry 20  }
   
   
   threadPoolRuntimeExecuteThreadTotalCount OBJECT-TYPE
      SYNTAX      INTEGER
      MAX-ACCESS  read-only
      STATUS      current
      DESCRIPTION "The total number of threads in the pool. "
      ::= { threadPoolRuntimeEntry 25  }
   
   
   threadPoolRuntimeExecuteThreadIdleCount OBJECT-TYPE
      SYNTAX      INTEGER
      MAX-ACCESS  read-only
      STATUS      current
      DESCRIPTION "The number of idle threads in the pool. This count does not include standby threads and stuck threads. The count indicates threads that are ready to pick up new work when it arrives "
      ::= { threadPoolRuntimeEntry 30  }
   
   
   threadPoolRuntimeQueueLength OBJECT-TYPE
      SYNTAX      INTEGER
      MAX-ACCESS  read-only
      STATUS      current
      DESCRIPTION "The number of pending requests in the priority queue. This is the total of internal system requests and user requests. "
      ::= { threadPoolRuntimeEntry 35  }
   
   
   threadPoolRuntimePendingUserRequestCount OBJECT-TYPE
      SYNTAX      INTEGER
      MAX-ACCESS  read-only
      STATUS      current
      DESCRIPTION "The number of pending user requests in the priority queue. The priority queue contains requests from internal subsystems and users. This is just the count of all user requests. "
      ::= { threadPoolRuntimeEntry 40  }
   
   
   threadPoolRuntimeSharedCapacityForWorkManagers OBJECT-TYPE
      SYNTAX      INTEGER
      MAX-ACCESS  read-only
      STATUS      current
      DESCRIPTION "Maximum amount of requests that can be accepted in the priority queue. Note that a request with higher priority will be accepted in place of a lower priority request already in the queue even after the threshold is reached. The lower priority request is kept waiting in the queue till all high priority requests are executed. Also note that further enqueues of the low priority requests are rejected right away.  "
      ::= { threadPoolRuntimeEntry 45  }
   
   
   threadPoolRuntimeCompletedRequestCount OBJECT-TYPE
      SYNTAX      Counter64
      MAX-ACCESS  read-only
      STATUS      current
      DESCRIPTION "The number of completed requests in the priority queue. "
      ::= { threadPoolRuntimeEntry 50  }
   
   
   threadPoolRuntimeHoggingThreadCount OBJECT-TYPE
      SYNTAX      INTEGER
      MAX-ACCESS  read-only
      STATUS      current
      DESCRIPTION " The threads that are being held by a request right now. These threads will either be declared as stuck after the configured timeout or will return to the pool before that. The self-tuning mechanism will backfill if necessary.  "
      ::= { threadPoolRuntimeEntry 55  }
   
   
   threadPoolRuntimeStandbyThreadCount OBJECT-TYPE
      SYNTAX      INTEGER
      MAX-ACCESS  read-only
      STATUS      current
      DESCRIPTION " The number of threads in the standby pool. Threads that are not needed to handle the present work load are designated as standby and added to the standby pool. These threads are activated when more threads are needed.  "
      ::= { threadPoolRuntimeEntry 60  }
   
   
   threadPoolRuntimeThroughput OBJECT-TYPE
      SYNTAX      DisplayString
      MAX-ACCESS  read-only
      STATUS      current
      DESCRIPTION "The mean number of requests completed per second. "
      ::= { threadPoolRuntimeEntry 65  }
   
   
   threadPoolRuntimeMinThreadsConstraintsPending OBJECT-TYPE
      SYNTAX      INTEGER
      MAX-ACCESS  read-only
      STATUS      current
      DESCRIPTION "Number of requests that should be executed now to satisfy the min threads requirement. "
      ::= { threadPoolRuntimeEntry 70  }
   
   
   threadPoolRuntimeMinThreadsConstraintsCompleted OBJECT-TYPE
      SYNTAX      Counter64
      MAX-ACCESS  read-only
      STATUS      current
      DESCRIPTION "Number of requests with min threads constraint picked up out of order for execution immediately since their min threads requirement was not met. This does not include the case where threads are idle during schedule. "
      ::= { threadPoolRuntimeEntry 75  }
   
   
   threadPoolRuntimeSuspended OBJECT-TYPE
      SYNTAX      INTEGER
                  {
                     true(1),
                     false(2)
                  }
      
      MAX-ACCESS  read-only
      STATUS      current
      DESCRIPTION "Indicates if the RequestManager is suspended. A suspended manager will not dequeue work and dispatch threads till it is resumed. "
      ::= { threadPoolRuntimeEntry 80  }
   
   
   threadPoolRuntimeStuckThreadCount OBJECT-TYPE
      SYNTAX      INTEGER
      MAX-ACCESS  read-only
      STATUS      current
      DESCRIPTION "Number of stuck threads in the thread pool. "
      ::= { threadPoolRuntimeEntry 81  }
   
   
   threadPoolRuntimeOverloadRejectedRequestsCount OBJECT-TYPE
      SYNTAX      INTEGER
      MAX-ACCESS  read-only
      STATUS      current
      DESCRIPTION "Number of requests rejected due to configured Shared Capacity for work managers have been reached. "
      ::= { threadPoolRuntimeEntry 82  }
   
   
   threadPoolRuntimeHealthState OBJECT-TYPE
      SYNTAX      OCTET STRING
      MAX-ACCESS  read-only
      STATUS      current
      DESCRIPTION "The health state of this pool. "
      ::= { threadPoolRuntimeEntry 83  }
   
   
   workManagerRuntimeTable OBJECT-TYPE
      SYNTAX      SEQUENCE OF WorkManagerRuntimeEntry
      MAX-ACCESS  not-accessible
      STATUS      current
      DESCRIPTION "WorkManager Runtime information. "
      ::= { wls 368  }
      
   
   workManagerRuntimeEntry OBJECT-TYPE
      SYNTAX      WorkManagerRuntimeEntry
      MAX-ACCESS  not-accessible
      STATUS      current
      DESCRIPTION "Entry of workManagerRuntimeTable"
      INDEX { workManagerRuntimeIndex}
      ::= { workManagerRuntimeTable 1 }
      
   WorkManagerRuntimeEntry ::=
      SEQUENCE
      {
         workManagerRuntimeIndex DisplayString,
         workManagerRuntimeObjectName DisplayString,
         workManagerRuntimeType DisplayString,
         workManagerRuntimeName DisplayString,
         workManagerRuntimeParent DisplayString,
         workManagerRuntimeApplicationName DisplayString,
         workManagerRuntimeModuleName DisplayString,
         workManagerRuntimePendingRequests INTEGER,
         workManagerRuntimeCompletedRequests Counter64,
         workManagerRuntimeStuckThreadCount INTEGER,
         workManagerRuntimeHealthState OCTET STRING,
         workManagerRuntimeCompletedDaemonRequests Counter64,
         workManagerRuntimePartitionName OCTET STRING,
         workManagerRuntimePendingDaemonRequests INTEGER
      }
      
   
   workManagerRuntimeIndex OBJECT-TYPE
      SYNTAX      DisplayString (SIZE (1..16))
      MAX-ACCESS  read-only
      STATUS      current
      DESCRIPTION "Unique value directed from ObjectName which is used as table index"
      ::= { workManagerRuntimeEntry 1  }
   
   
   workManagerRuntimeObjectName OBJECT-TYPE
      SYNTAX      DisplayString (SIZE (1..256))
      MAX-ACCESS  read-only
      STATUS      current
      DESCRIPTION "JMX-standard MBean name"
      ::= { workManagerRuntimeEntry 5  }
   
   
   workManagerRuntimeType OBJECT-TYPE
      SYNTAX      DisplayString (SIZE (1..64))
      MAX-ACCESS  read-only
      STATUS      current
      DESCRIPTION "Returns the type of the MBean. "
      ::= { workManagerRuntimeEntry 10  }
   
   
   workManagerRuntimeName OBJECT-TYPE
      SYNTAX      DisplayString (SIZE (1..64))
      MAX-ACCESS  read-only
      STATUS      current
      DESCRIPTION "The name of this configuration. WebLogic Server uses an MBean to implement and persist the configuration. "
      ::= { workManagerRuntimeEntry 15  }
   
   
   workManagerRuntimeParent OBJECT-TYPE
      SYNTAX      DisplayString (SIZE (1..256))
      MAX-ACCESS  read-only
      STATUS      current
      DESCRIPTION "BEA-proprietary Parent object's identification, with syntax
      <type>:<name>"
      ::= { workManagerRuntimeEntry 20  }
   
   
   workManagerRuntimeApplicationName OBJECT-TYPE
      SYNTAX      DisplayString (SIZE (1..128))
      MAX-ACCESS  read-only
      STATUS      current
      DESCRIPTION "Get the name of the application this WorkManager is associated with "
      ::= { workManagerRuntimeEntry 25  }
   
   
   workManagerRuntimeModuleName OBJECT-TYPE
      SYNTAX      DisplayString (SIZE (1..128))
      MAX-ACCESS  read-only
      STATUS      current
      DESCRIPTION "Get the name of the module this WorkManager is associated with "
      ::= { workManagerRuntimeEntry 30  }
   
   
   workManagerRuntimePendingRequests OBJECT-TYPE
      SYNTAX      INTEGER
      MAX-ACCESS  read-only
      STATUS      current
      DESCRIPTION "The number of waiting requests in the queue, including daemon requests. "
      ::= { workManagerRuntimeEntry 35  }
   
   
   workManagerRuntimeCompletedRequests OBJECT-TYPE
      SYNTAX      Counter64
      MAX-ACCESS  read-only
      STATUS      current
      DESCRIPTION "The number of requests that have been processed, including daemon requests. "
      ::= { workManagerRuntimeEntry 40  }
   
   
   workManagerRuntimeStuckThreadCount OBJECT-TYPE
      SYNTAX      INTEGER
      MAX-ACCESS  read-only
      STATUS      current
      DESCRIPTION "The number of threads that are considered to be stuck on the basis of any stuck thread constraints. "
      ::= { workManagerRuntimeEntry 41  }
   
   
   workManagerRuntimeHealthState OBJECT-TYPE
      SYNTAX      OCTET STRING
      MAX-ACCESS  read-only
      STATUS      current
      DESCRIPTION "Returns the HealthState mbean for the work manager.  "
      ::= { workManagerRuntimeEntry 42  }
   
   
   workManagerRuntimeCompletedDaemonRequests OBJECT-TYPE
      SYNTAX      Counter64
      MAX-ACCESS  read-only
      STATUS      current
      DESCRIPTION "The number of daemon requests that have been processed "
      ::= { workManagerRuntimeEntry 43  }
   
   
   workManagerRuntimePartitionName OBJECT-TYPE
      SYNTAX      OCTET STRING
      MAX-ACCESS  read-only
      STATUS      current
      DESCRIPTION "Returns the name of the partition that the work manager is associated with. "
      ::= { workManagerRuntimeEntry 44  }
   
   
   workManagerRuntimePendingDaemonRequests OBJECT-TYPE
      SYNTAX      INTEGER
      MAX-ACCESS  read-only
      STATUS      current
      DESCRIPTION "The number of daemon requests in progress. "
      ::= { workManagerRuntimeEntry 45  }
   
   
   serverSecurityRuntimeTable OBJECT-TYPE
      SYNTAX      SEQUENCE OF ServerSecurityRuntimeEntry
      MAX-ACCESS  not-accessible
      STATUS      current
      DESCRIPTION "This class is used for monitoring WebLogic Security Info. "
      ::= { wls 370  }
      
   
   serverSecurityRuntimeEntry OBJECT-TYPE
      SYNTAX      ServerSecurityRuntimeEntry
      MAX-ACCESS  not-accessible
      STATUS      current
      DESCRIPTION "Entry of serverSecurityRuntimeTable"
      INDEX { serverSecurityRuntimeIndex}
      ::= { serverSecurityRuntimeTable 1 }
      
   ServerSecurityRuntimeEntry ::=
      SEQUENCE
      {
         serverSecurityRuntimeIndex DisplayString,
         serverSecurityRuntimeObjectName DisplayString,
         serverSecurityRuntimeType DisplayString,
         serverSecurityRuntimeName DisplayString,
         serverSecurityRuntimeParent DisplayString,
         serverSecurityRuntimeJACCEnabled INTEGER
      }
      
   
   serverSecurityRuntimeIndex OBJECT-TYPE
      SYNTAX      DisplayString (SIZE (1..16))
      MAX-ACCESS  read-only
      STATUS      current
      DESCRIPTION "Unique value directed from ObjectName which is used as table index"
      ::= { serverSecurityRuntimeEntry 1  }
   
   
   serverSecurityRuntimeObjectName OBJECT-TYPE
      SYNTAX      DisplayString (SIZE (1..256))
      MAX-ACCESS  read-only
      STATUS      current
      DESCRIPTION "JMX-standard MBean name"
      ::= { serverSecurityRuntimeEntry 5  }
   
   
   serverSecurityRuntimeType OBJECT-TYPE
      SYNTAX      DisplayString (SIZE (1..64))
      MAX-ACCESS  read-only
      STATUS      current
      DESCRIPTION "Returns the type of the MBean. "
      ::= { serverSecurityRuntimeEntry 10  }
   
   
   serverSecurityRuntimeName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { serverSecurityRuntimeEntry 15  }
   
   
   serverSecurityRuntimeParent OBJECT-TYPE
      SYNTAX      DisplayString (SIZE (1..256))
      MAX-ACCESS  read-only
      STATUS      current
      DESCRIPTION "BEA-proprietary Parent object's identification, with syntax
      <type>:<name>"
      ::= { serverSecurityRuntimeEntry 20  }
   
   
   serverSecurityRuntimeJACCEnabled OBJECT-TYPE
      SYNTAX      INTEGER
                  {
                     true(1),
                     false(2)
                  }
      
      MAX-ACCESS  read-only
      STATUS      current
      DESCRIPTION "Indicates whether JACC (Java Authorization Contract for Containers) was enabled on the commandline for the jvm hosting this server "
      ::= { serverSecurityRuntimeEntry 30  }
   
   
   userLockoutManagerRuntimeTable OBJECT-TYPE
      SYNTAX      SEQUENCE OF UserLockoutManagerRuntimeEntry
      MAX-ACCESS  not-accessible
      STATUS      current
      DESCRIPTION "This class is used to monitor and manage per security realm user lockout information. "
      ::= { wls 371  }
      
   
   userLockoutManagerRuntimeEntry OBJECT-TYPE
      SYNTAX      UserLockoutManagerRuntimeEntry
      MAX-ACCESS  not-accessible
      STATUS      current
      DESCRIPTION "Entry of userLockoutManagerRuntimeTable"
      INDEX { userLockoutManagerRuntimeIndex}
      ::= { userLockoutManagerRuntimeTable 1 }
      
   UserLockoutManagerRuntimeEntry ::=
      SEQUENCE
      {
         userLockoutManagerRuntimeIndex DisplayString,
         userLockoutManagerRuntimeObjectName DisplayString,
         userLockoutManagerRuntimeType DisplayString,
         userLockoutManagerRuntimeName DisplayString,
         userLockoutManagerRuntimeParent DisplayString,
         userLockoutManagerRuntimeUserLockoutTotalCount Counter64,
         userLockoutManagerRuntimeInvalidLoginAttemptsTotalCount Counter64,
         userLockoutManagerRuntimeLoginAttemptsWhileLockedTotalCount Counter64,
         userLockoutManagerRuntimeInvalidLoginUsersHighCount Counter64,
         userLockoutManagerRuntimeUnlockedUsersTotalCount Counter64,
         userLockoutManagerRuntimeLockedUsersCurrentCount Counter64
      }
      
   
   userLockoutManagerRuntimeIndex OBJECT-TYPE
      SYNTAX      DisplayString (SIZE (1..16))
      MAX-ACCESS  read-only
      STATUS      current
      DESCRIPTION "Unique value directed from ObjectName which is used as table index"
      ::= { userLockoutManagerRuntimeEntry 1  }
   
   
   userLockoutManagerRuntimeObjectName OBJECT-TYPE
      SYNTAX      DisplayString (SIZE (1..256))
      MAX-ACCESS  read-only
      STATUS      current
      DESCRIPTION "JMX-standard MBean name"
      ::= { userLockoutManagerRuntimeEntry 5  }
   
   
   userLockoutManagerRuntimeType OBJECT-TYPE
      SYNTAX      DisplayString (SIZE (1..64))
      MAX-ACCESS  read-only
      STATUS      current
      DESCRIPTION "Returns the type of the MBean. "
      ::= { userLockoutManagerRuntimeEntry 10  }
   
   
   userLockoutManagerRuntimeName OBJECT-TYPE
      SYNTAX      DisplayString (SIZE (1..64))
      MAX-ACCESS  read-only
      STATUS      current
      DESCRIPTION "The name of this configuration. WebLogic Server uses an MBean to implement and persist the configuration. "
      ::= { userLockoutManagerRuntimeEntry 15  }
   
   
   userLockoutManagerRuntimeParent OBJECT-TYPE
      SYNTAX      DisplayString (SIZE (1..256))
      MAX-ACCESS  read-only
      STATUS      current
      DESCRIPTION "BEA-proprietary Parent object's identification, with syntax
      <type>:<name>"
      ::= { userLockoutManagerRuntimeEntry 20  }
   
   
   userLockoutManagerRuntimeUserLockoutTotalCount OBJECT-TYPE
      SYNTAX      Counter64
      MAX-ACCESS  read-only
      STATUS      current
      DESCRIPTION "Returns the number of user lockouts that have occured since this server has been started.  In a cluster, this method returns the number of user lockouts that have occured since the cluster has been started because all servers share login failure information. "
      ::= { userLockoutManagerRuntimeEntry 25  }
   
   
   userLockoutManagerRuntimeInvalidLoginAttemptsTotalCount OBJECT-TYPE
      SYNTAX      Counter64
      MAX-ACCESS  read-only
      STATUS      current
      DESCRIPTION "Returns the number of invalid logins attempted since this server has been started and lockouts have been enabled.  In a cluster, this method returns the number of invalid logins attempted that have occured since the cluster has been started because all servers share login failure information. "
      ::= { userLockoutManagerRuntimeEntry 30  }
   
   
   userLockoutManagerRuntimeLoginAttemptsWhileLockedTotalCount OBJECT-TYPE
      SYNTAX      Counter64
      MAX-ACCESS  read-only
      STATUS      current
      DESCRIPTION "Returns the number of invalid logins attempted since this server has been started and lockouts have been enabled. "
      ::= { userLockoutManagerRuntimeEntry 35  }
   
   
   userLockoutManagerRuntimeInvalidLoginUsersHighCount OBJECT-TYPE
      SYNTAX      Counter64
      MAX-ACCESS  read-only
      STATUS      current
      DESCRIPTION "Returns the highest number of users with concurrent unexpired or uncleared invalid login attempts.  Invalid login attempts expire as specified by LockoutResetDuration. This count is useful in determining whether the LockoutCacheSize needs to be modified. "
      ::= { userLockoutManagerRuntimeEntry 40  }
   
   
   userLockoutManagerRuntimeUnlockedUsersTotalCount OBJECT-TYPE
      SYNTAX      Counter64
      MAX-ACCESS  read-only
      STATUS      current
      DESCRIPTION "Returns the number times users have been unlocked since this server has been started. "
      ::= { userLockoutManagerRuntimeEntry 45  }
   
   
   userLockoutManagerRuntimeLockedUsersCurrentCount OBJECT-TYPE
      SYNTAX      Counter64
      MAX-ACCESS  read-only
      STATUS      current
      DESCRIPTION "Returns the number of users that are currently locked out of this server. "
      ::= { userLockoutManagerRuntimeEntry 50  }
   
   
   servletRuntimeTable OBJECT-TYPE
      SYNTAX      SEQUENCE OF ServletRuntimeEntry
      MAX-ACCESS  not-accessible
      STATUS      current
      DESCRIPTION "Describes a servlet. "
      ::= { wls 380  }
      
   
   servletRuntimeEntry OBJECT-TYPE
      SYNTAX      ServletRuntimeEntry
      MAX-ACCESS  not-accessible
      STATUS      current
      DESCRIPTION "Entry of servletRuntimeTable"
      INDEX { servletRuntimeIndex}
      ::= { servletRuntimeTable 1 }
      
   ServletRuntimeEntry ::=
      SEQUENCE
      {
         servletRuntimeIndex  DisplayString,
         servletRuntimeObjectName DisplayString,
         servletRuntimeType   DisplayString,
         servletRuntimeName   DisplayString,
         servletRuntimeParent DisplayString,
         servletRuntimeServletName DisplayString,
         servletRuntimeReloadTotalCount INTEGER,
         servletRuntimeInvocationTotalCount INTEGER,
         servletRuntimePoolMaxCapacity INTEGER,
         servletRuntimeExecutionTimeTotal INTEGER,
         servletRuntimeExecutionTimeHigh INTEGER,
         servletRuntimeExecutionTimeLow INTEGER,
         servletRuntimeExecutionTimeAverage INTEGER,
         servletRuntimeServletPath DisplayString,
         servletRuntimeContextPath DisplayString,
         servletRuntimeURL    DisplayString,
         servletRuntimeServletClassName OCTET STRING,
         servletRuntimeURLPatterns OCTET STRING
      }
      
   
   servletRuntimeIndex OBJECT-TYPE
      SYNTAX      DisplayString (SIZE (1..16))
      MAX-ACCESS  read-only
      STATUS      current
      DESCRIPTION "Unique value directed from ObjectName which is used as table index"
      ::= { servletRuntimeEntry 1  }
   
   
   servletRuntimeObjectName OBJECT-TYPE
      SYNTAX      DisplayString (SIZE (1..256))
      MAX-ACCESS  read-only
      STATUS      current
      DESCRIPTION "JMX-standard MBean name"
      ::= { servletRuntimeEntry 5  }
   
   
   servletRuntimeType OBJECT-TYPE
      SYNTAX      DisplayString (SIZE (1..64))
      MAX-ACCESS  read-only
      STATUS      current
      DESCRIPTION "Returns the type of the MBean. "
      ::= { servletRuntimeEntry 10  }
   
   
   servletRuntimeName OBJECT-TYPE
      SYNTAX      DisplayString (SIZE (1..64))
      MAX-ACCESS  read-only
      STATUS      current
      DESCRIPTION "The name of this configuration. WebLogic Server uses an MBean to implement and persist the configuration. "
      ::= { servletRuntimeEntry 15  }
   
   
   servletRuntimeParent OBJECT-TYPE
      SYNTAX      DisplayString (SIZE (1..256))
      MAX-ACCESS  read-only
      STATUS      current
      DESCRIPTION "BEA-proprietary Parent object's identification, with syntax
      <type>:<name>"
      ::= { servletRuntimeEntry 20  }
   
   
   servletRuntimeServletName OBJECT-TYPE
      SYNTAX      DisplayString (SIZE (1..64))
      MAX-ACCESS  read-only
      STATUS      current
      DESCRIPTION "Provides the name of this instance of a servlet. "
      ::= { servletRuntimeEntry 25  }
   
   
   servletRuntimeReloadTotalCount OBJECT-TYPE
      SYNTAX      INTEGER
      MAX-ACCESS  read-only
      STATUS      current
      DESCRIPTION "Provides a total count of the number of times this servlet has been reloaded. "
      ::= { servletRuntimeEntry 30  }
   
   
   servletRuntimeInvocationTotalCount OBJECT-TYPE
      SYNTAX      INTEGER
      MAX-ACCESS  read-only
      STATUS      current
      DESCRIPTION "Provides a total count of the times this servlet has been invoked. "
      ::= { servletRuntimeEntry 35  }
   
   
   servletRuntimePoolMaxCapacity OBJECT-TYPE
      SYNTAX      INTEGER
      MAX-ACCESS  read-only
      STATUS      current
      DESCRIPTION "Provides the maximum capacity of this servlet for single thread model servlets. "
      ::= { servletRuntimeEntry 40  }
   
   
   servletRuntimeExecutionTimeTotal OBJECT-TYPE
      SYNTAX      INTEGER
      MAX-ACCESS  read-only
      STATUS      current
      DESCRIPTION "Provides the total amount of time all invocations of the servlet have executed since created. "
      ::= { servletRuntimeEntry 45  }
   
   
   servletRuntimeExecutionTimeHigh OBJECT-TYPE
      SYNTAX      INTEGER
      MAX-ACCESS  read-only
      STATUS      current
      DESCRIPTION "Provides the amount of time the single longest invocation of the servlet has executed since created. "
      ::= { servletRuntimeEntry 50  }
   
   
   servletRuntimeExecutionTimeLow OBJECT-TYPE
      SYNTAX      INTEGER
      MAX-ACCESS  read-only
      STATUS      current
      DESCRIPTION "Provides the amount of time the single shortest invocation of the servlet has executed since created. Note that for the CounterMonitor, the difference option must be used. "
      ::= { servletRuntimeEntry 55  }
   
   
   servletRuntimeExecutionTimeAverage OBJECT-TYPE
      SYNTAX      INTEGER
      MAX-ACCESS  read-only
      STATUS      current
      DESCRIPTION "Provides the average amount of time all invocations of the servlet have executed since created. "
      ::= { servletRuntimeEntry 60  }
   
   
   servletRuntimeServletPath OBJECT-TYPE
      SYNTAX      DisplayString (SIZE (1..256))
      MAX-ACCESS  read-only
      STATUS      current
      DESCRIPTION "Provides the servlet path. "
      ::= { servletRuntimeEntry 65  }
   
   
   servletRuntimeContextPath OBJECT-TYPE
      SYNTAX      DisplayString (SIZE (1..256))
      MAX-ACCESS  read-only
      STATUS      current
      DESCRIPTION "Provides the context path for this servlet. "
      ::= { servletRuntimeEntry 70  }
   
   
   servletRuntimeURL OBJECT-TYPE
      SYNTAX      DisplayString (SIZE (1..256))
      MAX-ACCESS  read-only
      STATUS      current
      DESCRIPTION "Provides the value of the URL for this servlet. "
      ::= { servletRuntimeEntry 75  }
   
   
   servletRuntimeServletClassName OBJECT-TYPE
      SYNTAX      OCTET STRING
      MAX-ACCESS  read-only
      STATUS      current
      DESCRIPTION "Provides the servlet class name "
      ::= { servletRuntimeEntry 76  }
   
   
   servletRuntimeURLPatterns OBJECT-TYPE
      SYNTAX      OCTET STRING
      MAX-ACCESS  read-only
      STATUS      current
      DESCRIPTION "Provides a description of the URL patterns for this servlet. "
      ::= { servletRuntimeEntry 77  }
   
   
   servletSessionRuntimeTable OBJECT-TYPE
      SYNTAX      SEQUENCE OF ServletSessionRuntimeEntry
      MAX-ACCESS  not-accessible
      STATUS      current
      DESCRIPTION "This table is used for monitoring a WebLogic servlet session
      within a WebLogic server."
      ::= { wls 390  }
      
   
   servletSessionRuntimeEntry OBJECT-TYPE
      SYNTAX      ServletSessionRuntimeEntry
      MAX-ACCESS  not-accessible
      STATUS      current
      DESCRIPTION "Entry of servletSessionRuntimeTable"
      INDEX { servletSessionRuntimeIndex}
      ::= { servletSessionRuntimeTable 1 }
      
   ServletSessionRuntimeEntry ::=
      SEQUENCE
      {
         servletSessionRuntimeIndex DisplayString,
         servletSessionRuntimeObjectName DisplayString,
         servletSessionRuntimeType DisplayString,
         servletSessionRuntimeName DisplayString,
         servletSessionRuntimeParent DisplayString,
         servletSessionRuntimeTimeLastAccessed Counter64,
         servletSessionRuntimeMainAttribute DisplayString,
         servletSessionRuntimeMaxInactiveInterval Counter64
      }
      
   
   servletSessionRuntimeIndex OBJECT-TYPE
      SYNTAX      DisplayString (SIZE (1..16))
      MAX-ACCESS  read-only
      STATUS      current
      DESCRIPTION "Unique value directed from ObjectName which is used as table index"
      ::= { servletSessionRuntimeEntry 1  }
   
   
   servletSessionRuntimeObjectName OBJECT-TYPE
      SYNTAX      DisplayString (SIZE (1..256))
      MAX-ACCESS  read-only
      STATUS      current
      DESCRIPTION "JMX-standard MBean name"
      ::= { servletSessionRuntimeEntry 5  }
   
   
   servletSessionRuntimeType OBJECT-TYPE
      SYNTAX      DisplayString (SIZE (1..64))
      MAX-ACCESS  read-only
      STATUS      current
      DESCRIPTION "BEA-proprietary MBean type"
      ::= { servletSessionRuntimeEntry 10  }
   
   
   servletSessionRuntimeName OBJECT-TYPE
      SYNTAX      DisplayString (SIZE (1..64))
      MAX-ACCESS  read-only
      STATUS      current
      DESCRIPTION "BEA-proprietary MBean name"
      ::= { servletSessionRuntimeEntry 15  }
   
   
   servletSessionRuntimeParent OBJECT-TYPE
      SYNTAX      DisplayString (SIZE (1..256))
      MAX-ACCESS  read-only
      STATUS      current
      DESCRIPTION "BEA-proprietary Parent object's identification, with syntax
      <type>:<name>"
      ::= { servletSessionRuntimeEntry 20  }
   
   
   servletSessionRuntimeTimeLastAccessed OBJECT-TYPE
      SYNTAX      Counter64
      MAX-ACCESS  read-only
      STATUS      current
      DESCRIPTION "Last time accessed."
      ::= { servletSessionRuntimeEntry 25  }
   
   
   servletSessionRuntimeMainAttribute OBJECT-TYPE
      SYNTAX      DisplayString (SIZE (1..64))
      MAX-ACCESS  read-only
      STATUS      current
      DESCRIPTION "Gets a Stringified copy of an attribute specified by the user (like user-name)
      associated with this session."
      ::= { servletSessionRuntimeEntry 30  }
   
   
   servletSessionRuntimeMaxInactiveInterval OBJECT-TYPE
      SYNTAX      Counter64
      MAX-ACCESS  read-only
      STATUS      current
      DESCRIPTION "Returns the timeout (seconds) for the session"
      ::= { servletSessionRuntimeEntry 31  }
   
   
   taskRuntimeTable OBJECT-TYPE
      SYNTAX      SEQUENCE OF TaskRuntimeEntry
      MAX-ACCESS  not-accessible
      STATUS      current
      DESCRIPTION "Exposes monitoring information about an ongoing and potentially long-running administrative process.  This should be taken to mean, at minimum, any OA&amp;M operation involving I/O.  Examples include starting and stopping servers, deploying and undeploying applications, or migrating services.  An MBean operation of this sort should fork a separate thread to perform the actual work and immediately return an instance of TaskRuntimeMBean to the caller.  The caller can then use this to track the task's progress as desired.  Users can also query for all instances of TaskRuntimeMBean to get a summary of both currently-running and recently-completed tasks.  Instance of TaskRuntimeMBean continue to exist in the MBeanServer after the completion of the work they describe.  They will eventually either be explicitly deregistered by the user, or removed by a scavenger process which periodically purges instances of TaskRuntimeMBean that have been completed for some time. "
      ::= { wls 391  }
      
   
   taskRuntimeEntry OBJECT-TYPE
      SYNTAX      TaskRuntimeEntry
      MAX-ACCESS  not-accessible
      STATUS      current
      DESCRIPTION "Entry of taskRuntimeTable"
      INDEX { taskRuntimeIndex}
      ::= { taskRuntimeTable 1 }
      
   TaskRuntimeEntry ::=
      SEQUENCE
      {
         taskRuntimeIndex     DisplayString,
         taskRuntimeObjectName DisplayString,
         taskRuntimeType      DisplayString,
         taskRuntimeName      DisplayString,
         taskRuntimeParent    DisplayString,
         taskRuntimeBeginTime Counter64,
         taskRuntimeDescription DisplayString,
         taskRuntimeEndTime   Counter64,
         taskRuntimeStatus    DisplayString,
         taskRuntimeRunning   INTEGER,
         taskRuntimeSystemTask INTEGER,
         taskRuntimeProgress  OCTET STRING
      }
      
   
   taskRuntimeIndex OBJECT-TYPE
      SYNTAX      DisplayString (SIZE (1..16))
      MAX-ACCESS  read-only
      STATUS      current
      DESCRIPTION "Unique value directed from ObjectName which is used as table index"
      ::= { taskRuntimeEntry 1  }
   
   
   taskRuntimeObjectName OBJECT-TYPE
      SYNTAX      DisplayString (SIZE (1..256))
      MAX-ACCESS  read-only
      STATUS      current
      DESCRIPTION "JMX-standard MBean name"
      ::= { taskRuntimeEntry 5  }
   
   
   taskRuntimeType OBJECT-TYPE
      SYNTAX      DisplayString (SIZE (1..64))
      MAX-ACCESS  read-only
      STATUS      current
      DESCRIPTION "Returns the type of the MBean. "
      ::= { taskRuntimeEntry 10  }
   
   
   taskRuntimeName OBJECT-TYPE
      SYNTAX      DisplayString (SIZE (1..64))
      MAX-ACCESS  read-only
      STATUS      current
      DESCRIPTION "The name of this configuration. WebLogic Server uses an MBean to implement and persist the configuration. "
      ::= { taskRuntimeEntry 15  }
   
   
   taskRuntimeParent OBJECT-TYPE
      SYNTAX      DisplayString (SIZE (1..256))
      MAX-ACCESS  read-only
      STATUS      current
      DESCRIPTION "BEA-proprietary Parent object's identification, with syntax
      <type>:<name>"
      ::= { taskRuntimeEntry 20  }
   
   
   taskRuntimeBeginTime OBJECT-TYPE
      SYNTAX      Counter64
      MAX-ACCESS  read-only
      STATUS      current
      DESCRIPTION "The time at which this task was started. "
      ::= { taskRuntimeEntry 25  }
   
   
   taskRuntimeDescription OBJECT-TYPE
      SYNTAX      DisplayString (SIZE (1..64))
      MAX-ACCESS  read-only
      STATUS      current
      DESCRIPTION "A description of this task. "
      ::= { taskRuntimeEntry 30  }
   
   
   taskRuntimeEndTime OBJECT-TYPE
      SYNTAX      Counter64
      MAX-ACCESS  read-only
      STATUS      current
      DESCRIPTION "The time at which this task was completed.  A value of -1 indicates that the task is currently running. "
      ::= { taskRuntimeEntry 35  }
   
   
   taskRuntimeStatus OBJECT-TYPE
      SYNTAX      DisplayString (SIZE (1..64))
      MAX-ACCESS  read-only
      STATUS      current
      DESCRIPTION "The status of this task. "
      ::= { taskRuntimeEntry 40  }
   
   
   taskRuntimeRunning OBJECT-TYPE
      SYNTAX      INTEGER
      MAX-ACCESS  read-only
      STATUS      current
      DESCRIPTION "Indicates whether the task is still running. "
      ::= { taskRuntimeEntry 45  }
   
   
   taskRuntimeSystemTask OBJECT-TYPE
      SYNTAX      INTEGER
      MAX-ACCESS  read-only
      STATUS      current
      DESCRIPTION "Indicates whether this task was initiated by the server versus a user. "
      ::= { taskRuntimeEntry 50  }
   
   
   taskRuntimeProgress OBJECT-TYPE
      SYNTAX      OCTET STRING
      MAX-ACCESS  read-only
      STATUS      current
      DESCRIPTION "The progress of this task. "
      ::= { taskRuntimeEntry 51  }
   
   
   transactionNameRuntimeTable OBJECT-TYPE
      SYNTAX      SEQUENCE OF TransactionNameRuntimeEntry
      MAX-ACCESS  not-accessible
      STATUS      current
      DESCRIPTION "This interface represents runtime statistics for a transaction name category. "
      ::= { wls 410  }
      
   
   transactionNameRuntimeEntry OBJECT-TYPE
      SYNTAX      TransactionNameRuntimeEntry
      MAX-ACCESS  not-accessible
      STATUS      current
      DESCRIPTION "Entry of transactionNameRuntimeTable"
      INDEX { transactionNameRuntimeIndex}
      ::= { transactionNameRuntimeTable 1 }
      
   TransactionNameRuntimeEntry ::=
      SEQUENCE
      {
         transactionNameRuntimeIndex DisplayString,
         transactionNameRuntimeObjectName DisplayString,
         transactionNameRuntimeType DisplayString,
         transactionNameRuntimeName DisplayString,
         transactionNameRuntimeParent DisplayString,
         transactionNameRuntimeTransactionTotalCount INTEGER,
         transactionNameRuntimeTransactionCommittedTotalCount INTEGER,
         transactionNameRuntimeTransactionRolledBackTotalCount INTEGER,
         transactionNameRuntimeTransactionHeuristicsTotalCount INTEGER,
         transactionNameRuntimeTransactionRolledBackResourceTotalCount INTEGER,
         transactionNameRuntimeTransactionRolledBackAppTotalCount INTEGER,
         transactionNameRuntimeTransactionRolledBackSystemTotalCount INTEGER,
         transactionNameRuntimeSecondsActiveTotalCount INTEGER,
         transactionNameRuntimeTransactionRolledBackTimeoutTotalCount INTEGER,
         transactionNameRuntimeTransactionName DisplayString,
         transactionNameRuntimeTransactionAbandonedTotalCount Counter64,
         txNameRuntimeTxReadOnlyOnePhaseCommittedTotalCount Counter64,
         transactionNameRuntimeTransactionTwoPhaseCommittedTotalCount Counter64,
         txNameRuntimeTxOneResourceOnePhaseCommittedTotalCount Counter64,
         transactionNameRuntimeTransactionLLRCommittedTotalCount Counter64,
         transactionNameRuntimeTransactionNoResourcesCommittedTotalCount Counter64,
         txNameRuntimeTransactionTwoPhaseCommittedNotLoggedTotalCount Counter64,
         txNameRuntimeTransactionTwoPhaseCommittedLoggedTotalCount Counter64
      }
      
   
   transactionNameRuntimeIndex OBJECT-TYPE
      SYNTAX      DisplayString (SIZE (1..16))
      MAX-ACCESS  read-only
      STATUS      current
      DESCRIPTION "Unique value directed from ObjectName which is used as table index"
      ::= { transactionNameRuntimeEntry 1  }
   
   
   transactionNameRuntimeObjectName OBJECT-TYPE
      SYNTAX      DisplayString (SIZE (1..256))
      MAX-ACCESS  read-only
      STATUS      current
      DESCRIPTION "JMX-standard MBean name"
      ::= { transactionNameRuntimeEntry 5  }
   
   
   transactionNameRuntimeType OBJECT-TYPE
      SYNTAX      DisplayString (SIZE (1..64))
      MAX-ACCESS  read-only
      STATUS      current
      DESCRIPTION "Returns the type of the MBean. "
      ::= { transactionNameRuntimeEntry 10  }
   
   
   transactionNameRuntimeName OBJECT-TYPE
      SYNTAX      DisplayString (SIZE (1..64))
      MAX-ACCESS  read-only
      STATUS      current
      DESCRIPTION "The name of this configuration. WebLogic Server uses an MBean to implement and persist the configuration. "
      ::= { transactionNameRuntimeEntry 15  }
   
   
   transactionNameRuntimeParent OBJECT-TYPE
      SYNTAX      DisplayString (SIZE (1..256))
      MAX-ACCESS  read-only
      STATUS      current
      DESCRIPTION "BEA-proprietary Parent object's identification, with syntax
      <type>:<name>"
      ::= { transactionNameRuntimeEntry 20  }
   
   
   transactionNameRuntimeTransactionTotalCount OBJECT-TYPE
      SYNTAX      INTEGER
      MAX-ACCESS  read-only
      STATUS      current
      DESCRIPTION "The total number of transactions processed. This total includes all committed, rolled back, and heuristic transaction completions since the server was started. "
      ::= { transactionNameRuntimeEntry 25  }
   
   
   transactionNameRuntimeTransactionCommittedTotalCount OBJECT-TYPE
      SYNTAX      INTEGER
      MAX-ACCESS  read-only
      STATUS      current
      DESCRIPTION "The total number of transactions committed since the server was started. "
      ::= { transactionNameRuntimeEntry 30  }
   
   
   transactionNameRuntimeTransactionRolledBackTotalCount OBJECT-TYPE
      SYNTAX      INTEGER
      MAX-ACCESS  read-only
      STATUS      current
      DESCRIPTION "The number of transactions that were rolled back since the server was started. "
      ::= { transactionNameRuntimeEntry 35  }
   
   
   transactionNameRuntimeTransactionHeuristicsTotalCount OBJECT-TYPE
      SYNTAX      INTEGER
      MAX-ACCESS  read-only
      STATUS      current
      DESCRIPTION "The number of transactions that completed with a heuristic status since the server was started. "
      ::= { transactionNameRuntimeEntry 40  }
   
   
   transactionNameRuntimeTransactionRolledBackResourceTotalCount OBJECT-TYPE
      SYNTAX      INTEGER
      MAX-ACCESS  read-only
      STATUS      current
      DESCRIPTION "The number of transactions that were rolled back due to a resource error. "
      ::= { transactionNameRuntimeEntry 45  }
   
   
   transactionNameRuntimeTransactionRolledBackAppTotalCount OBJECT-TYPE
      SYNTAX      INTEGER
      MAX-ACCESS  read-only
      STATUS      current
      DESCRIPTION "The number of transactions that were rolled back due to an application error. "
      ::= { transactionNameRuntimeEntry 50  }
   
   
   transactionNameRuntimeTransactionRolledBackSystemTotalCount OBJECT-TYPE
      SYNTAX      INTEGER
      MAX-ACCESS  read-only
      STATUS      current
      DESCRIPTION "The number of transactions that were rolled back due to an internal system error. "
      ::= { transactionNameRuntimeEntry 55  }
   
   
   transactionNameRuntimeSecondsActiveTotalCount OBJECT-TYPE
      SYNTAX      INTEGER
      MAX-ACCESS  read-only
      STATUS      current
      DESCRIPTION "The total number of seconds that transactions were active for all committed transactions. "
      ::= { transactionNameRuntimeEntry 60  }
   
   
   transactionNameRuntimeTransactionRolledBackTimeoutTotalCount OBJECT-TYPE
      SYNTAX      INTEGER
      MAX-ACCESS  read-only
      STATUS      current
      DESCRIPTION "The number of transactions that were rolled back due to a timeout expiration. "
      ::= { transactionNameRuntimeEntry 65  }
   
   
   transactionNameRuntimeTransactionName OBJECT-TYPE
      SYNTAX      DisplayString (SIZE (1..64))
      MAX-ACCESS  read-only
      STATUS      current
      DESCRIPTION "The transaction name. "
      ::= { transactionNameRuntimeEntry 70  }
   
   
   transactionNameRuntimeTransactionAbandonedTotalCount OBJECT-TYPE
      SYNTAX      Counter64
      MAX-ACCESS  read-only
      STATUS      current
      DESCRIPTION "The total number of transactions that were abandoned since the server was started. "
      ::= { transactionNameRuntimeEntry 71  }
   
   
   txNameRuntimeTxReadOnlyOnePhaseCommittedTotalCount OBJECT-TYPE
      SYNTAX      Counter64
      MAX-ACCESS  read-only
      STATUS      current
      DESCRIPTION "The total number of transactions with more than one enlisted resource that were one-phase committed due to read-only optimization since the server was started. "
      ::= { transactionNameRuntimeEntry 72  }
   
   
   transactionNameRuntimeTransactionTwoPhaseCommittedTotalCount OBJECT-TYPE
      SYNTAX      Counter64
      MAX-ACCESS  read-only
      STATUS      current
      DESCRIPTION "The total number of transactions with more than one enlisted resource that were two-phase committed since the server was started. "
      ::= { transactionNameRuntimeEntry 73  }
   
   
   txNameRuntimeTxOneResourceOnePhaseCommittedTotalCount OBJECT-TYPE
      SYNTAX      Counter64
      MAX-ACCESS  read-only
      STATUS      current
      DESCRIPTION "The total number of transactions with only one enlisted resource that were one-phase committed since the server was started. "
      ::= { transactionNameRuntimeEntry 74  }
   
   
   transactionNameRuntimeTransactionLLRCommittedTotalCount OBJECT-TYPE
      SYNTAX      Counter64
      MAX-ACCESS  read-only
      STATUS      current
      DESCRIPTION "The total number of LLR transactions that were committed since the server was started. "
      ::= { transactionNameRuntimeEntry 75  }
   
   
   transactionNameRuntimeTransactionNoResourcesCommittedTotalCount OBJECT-TYPE
      SYNTAX      Counter64
      MAX-ACCESS  read-only
      STATUS      current
      DESCRIPTION "The total number of transactions with no enlisted resources that were committed since the server was started. "
      ::= { transactionNameRuntimeEntry 76  }
   
   
   txNameRuntimeTransactionTwoPhaseCommittedNotLoggedTotalCount OBJECT-TYPE
      SYNTAX      Counter64
      MAX-ACCESS  read-only
      STATUS      current
      DESCRIPTION "The total number of two phase commited transactions that were committed without TLog since the server was started. "
      ::= { transactionNameRuntimeEntry 77  }
   
   
   txNameRuntimeTransactionTwoPhaseCommittedLoggedTotalCount OBJECT-TYPE
      SYNTAX      Counter64
      MAX-ACCESS  read-only
      STATUS      current
      DESCRIPTION "The total number of two phase commit transactions that were committed with TLog since the server was started. "
      ::= { transactionNameRuntimeEntry 78  }
   
   
   transactionResourceRuntimeTable OBJECT-TYPE
      SYNTAX      SEQUENCE OF TransactionResourceRuntimeEntry
      MAX-ACCESS  not-accessible
      STATUS      current
      DESCRIPTION "This interface represents runtime statistics for a transactional resource. "
      ::= { wls 420  }
      
   
   transactionResourceRuntimeEntry OBJECT-TYPE
      SYNTAX      TransactionResourceRuntimeEntry
      MAX-ACCESS  not-accessible
      STATUS      current
      DESCRIPTION "Entry of transactionResourceRuntimeTable"
      INDEX { transactionResourceRuntimeIndex}
      ::= { transactionResourceRuntimeTable 1 }
      
   TransactionResourceRuntimeEntry ::=
      SEQUENCE
      {
         transactionResourceRuntimeIndex DisplayString,
         transactionResourceRuntimeObjectName DisplayString,
         transactionResourceRuntimeType DisplayString,
         transactionResourceRuntimeName DisplayString,
         transactionResourceRuntimeParent DisplayString,
         transactionResourceRuntimeTransactionTotalCount Counter64,
         transactionResourceRuntimeTransactionCommittedTotalCount Counter64,
         transactionResourceRuntimeTransactionRolledBackTotalCount Counter64,
         transactionResourceRuntimeTransactionHeuristicsTotalCount Counter64,
         transactionResourceRuntimeResourceName DisplayString,
         transactionResourceRuntimeTransactionHeuristicCommitTotalCount Counter64,
         transactionResourceRuntimeTransactionHeuristicRollbackTotalCount Counter64,
         transactionResourceRuntimeTransactionHeuristicMixedTotalCount Counter64,
         transactionResourceRuntimeTransactionHeuristicHazardTotalCount Counter64,
         transactionResourceRuntimeHealthState OCTET STRING
      }
      
   
   transactionResourceRuntimeIndex OBJECT-TYPE
      SYNTAX      DisplayString (SIZE (1..16))
      MAX-ACCESS  read-only
      STATUS      current
      DESCRIPTION "Unique value directed from ObjectName which is used as table index"
      ::= { transactionResourceRuntimeEntry 1  }
   
   
   transactionResourceRuntimeObjectName OBJECT-TYPE
      SYNTAX      DisplayString (SIZE (1..256))
      MAX-ACCESS  read-only
      STATUS      current
      DESCRIPTION "JMX-standard MBean name"
      ::= { transactionResourceRuntimeEntry 5  }
   
   
   transactionResourceRuntimeType OBJECT-TYPE
      SYNTAX      DisplayString (SIZE (1..64))
      MAX-ACCESS  read-only
      STATUS      current
      DESCRIPTION "Returns the type of the MBean. "
      ::= { transactionResourceRuntimeEntry 10  }
   
   
   transactionResourceRuntimeName OBJECT-TYPE
      SYNTAX      DisplayString (SIZE (1..64))
      MAX-ACCESS  read-only
      STATUS      current
      DESCRIPTION "The name of this configuration. WebLogic Server uses an MBean to implement and persist the configuration. "
      ::= { transactionResourceRuntimeEntry 15  }
   
   
   transactionResourceRuntimeParent OBJECT-TYPE
      SYNTAX      DisplayString (SIZE (1..256))
      MAX-ACCESS  read-only
      STATUS      current
      DESCRIPTION "BEA-proprietary Parent object's identification, with syntax
      <type>:<name>"
      ::= { transactionResourceRuntimeEntry 20  }
   
   
   transactionResourceRuntimeTransactionTotalCount OBJECT-TYPE
      SYNTAX      Counter64
      MAX-ACCESS  read-only
      STATUS      current
      DESCRIPTION "The total number of transactions processed. This total includes all committed, rolled back, and heuristic transaction completions since the server was started. "
      ::= { transactionResourceRuntimeEntry 25  }
   
   
   transactionResourceRuntimeTransactionCommittedTotalCount OBJECT-TYPE
      SYNTAX      Counter64
      MAX-ACCESS  read-only
      STATUS      current
      DESCRIPTION "The total number of transactions committed since the server was started. "
      ::= { transactionResourceRuntimeEntry 30  }
   
   
   transactionResourceRuntimeTransactionRolledBackTotalCount OBJECT-TYPE
      SYNTAX      Counter64
      MAX-ACCESS  read-only
      STATUS      current
      DESCRIPTION "The number of transactions that were rolled back since the server was started. "
      ::= { transactionResourceRuntimeEntry 35  }
   
   
   transactionResourceRuntimeTransactionHeuristicsTotalCount OBJECT-TYPE
      SYNTAX      Counter64
      MAX-ACCESS  read-only
      STATUS      current
      DESCRIPTION "The number of transactions that completed with a heuristic status since the server was started. "
      ::= { transactionResourceRuntimeEntry 40  }
   
   
   transactionResourceRuntimeResourceName OBJECT-TYPE
      SYNTAX      DisplayString (SIZE (1..64))
      MAX-ACCESS  read-only
      STATUS      current
      DESCRIPTION "The resource name. "
      ::= { transactionResourceRuntimeEntry 45  }
   
   
   transactionResourceRuntimeTransactionHeuristicCommitTotalCount OBJECT-TYPE
      SYNTAX      Counter64
      MAX-ACCESS  read-only
      STATUS      current
      DESCRIPTION "The number of transactions for which this resource has returned a heuristic commit decision. "
      ::= { transactionResourceRuntimeEntry 50  }
   
   
   transactionResourceRuntimeTransactionHeuristicRollbackTotalCount OBJECT-TYPE
      SYNTAX      Counter64
      MAX-ACCESS  read-only
      STATUS      current
      DESCRIPTION "The number of transactions for which this resource has returned a heuristic rollback decision. "
      ::= { transactionResourceRuntimeEntry 55  }
   
   
   transactionResourceRuntimeTransactionHeuristicMixedTotalCount OBJECT-TYPE
      SYNTAX      Counter64
      MAX-ACCESS  read-only
      STATUS      current
      DESCRIPTION "The number of transactions for which this resource has reported a heuristic mixed decision. "
      ::= { transactionResourceRuntimeEntry 60  }
   
   
   transactionResourceRuntimeTransactionHeuristicHazardTotalCount OBJECT-TYPE
      SYNTAX      Counter64
      MAX-ACCESS  read-only
      STATUS      current
      DESCRIPTION "The number of transactions for which this resource has reported a heuristic hazard decision. "
      ::= { transactionResourceRuntimeEntry 65  }
   
   
   transactionResourceRuntimeHealthState OBJECT-TYPE
      SYNTAX      OCTET STRING
      MAX-ACCESS  read-only
      STATUS      current
      DESCRIPTION "The health state of the Resource. "
      ::= { transactionResourceRuntimeEntry 66  }
   
   
   webAppComponentRuntimeTable OBJECT-TYPE
      SYNTAX      SEQUENCE OF WebAppComponentRuntimeEntry
      MAX-ACCESS  not-accessible
      STATUS      current
      DESCRIPTION "Describes a servlet component (servlet context). "
      ::= { wls 430  }
      
   
   webAppComponentRuntimeEntry OBJECT-TYPE
      SYNTAX      WebAppComponentRuntimeEntry
      MAX-ACCESS  not-accessible
      STATUS      current
      DESCRIPTION "Entry of webAppComponentRuntimeTable"
      INDEX { webAppComponentRuntimeIndex}
      ::= { webAppComponentRuntimeTable 1 }
      
   WebAppComponentRuntimeEntry ::=
      SEQUENCE
      {
         webAppComponentRuntimeIndex DisplayString,
         webAppComponentRuntimeObjectName DisplayString,
         webAppComponentRuntimeType DisplayString,
         webAppComponentRuntimeName DisplayString,
         webAppComponentRuntimeParent DisplayString,
         webAppComponentRuntimeComponentName DisplayString,
         webAppComponentRuntimeStatus DisplayString,
         webAppComponentRuntimeSourceInfo DisplayString,
         webAppComponentRuntimeOpenSessionsCurrentCount INTEGER,
         webAppComponentRuntimeOpenSessionsHighCount INTEGER,
         webAppComponentRuntimeSessionsOpenedTotalCount INTEGER,
         webAppComponentRuntimeSingleThreadedServletPoolSize INTEGER,
         webAppComponentRuntimeJSPVerbose OCTET STRING,
         webAppComponentRuntimeIndexDirectoryEnabled OCTET STRING,
         webAppComponentRuntimeModuleId OCTET STRING,
         webAppComponentRuntimeJSPDebug OCTET STRING,
         webAppComponentRuntimeSessionCookieName OCTET STRING,
         webAppComponentRuntimeSessionCookieDomain OCTET STRING,
         webAppComponentRuntimeFilterDispatchedRequestsEnabled OCTET STRING,
         webAppComponentRuntimeLogFilename OCTET STRING,
         webAppComponentRuntimeSessionCookiePath OCTET STRING,
         webAppComponentRuntimeJSPKeepGenerated OCTET STRING,
         webAppComponentRuntimeSessionCookieComment OCTET STRING,
         webAppComponentRuntimeJSPCompileCommand OCTET STRING,
         webAppComponentRuntimeJSPPageCheckSecs Counter64,
         webAppComponentRuntimeContextRoot OCTET STRING,
         webAppComponentRuntimeModuleURI OCTET STRING,
         webAppComponentRuntimeSessionInvalidationIntervalSecs INTEGER,
         webAppComponentRuntimeServletReloadCheckSecs INTEGER,
         webAppComponentRuntimeSessionCookieMaxAgeSecs INTEGER,
         webAppComponentRuntimeSessionTimeoutSecs INTEGER,
         webAppComponentRuntimeSessionIDLength INTEGER,
         webAppComponentRuntimeDeploymentState INTEGER,
         webAppComponentRuntimeSessionMonitoringEnabled OCTET STRING,
         webAppComponentRuntimeServletSessionsMonitoringIds OCTET STRING,
         webAppComponentRuntimeApplicationIdentifier OCTET STRING,
         webAppComponentRuntimeConfiguredContextRoot OCTET STRING
      }
      
   
   webAppComponentRuntimeIndex OBJECT-TYPE
      SYNTAX      DisplayString (SIZE (1..16))
      MAX-ACCESS  read-only
      STATUS      current
      DESCRIPTION "Unique value directed from ObjectName which is used as table index"
      ::= { webAppComponentRuntimeEntry 1  }
   
   
   webAppComponentRuntimeObjectName OBJECT-TYPE
      SYNTAX      DisplayString (SIZE (1..256))
      MAX-ACCESS  read-only
      STATUS      current
      DESCRIPTION "JMX-standard MBean name"
      ::= { webAppComponentRuntimeEntry 5  }
   
   
   webAppComponentRuntimeType OBJECT-TYPE
      SYNTAX      DisplayString (SIZE (1..64))
      MAX-ACCESS  read-only
      STATUS      current
      DESCRIPTION "Returns the type of the MBean. "
      ::= { webAppComponentRuntimeEntry 10  }
   
   
   webAppComponentRuntimeName OBJECT-TYPE
      SYNTAX      DisplayString (SIZE (1..64))
      MAX-ACCESS  read-only
      STATUS      current
      DESCRIPTION "Provides the name of this MBean. "
      ::= { webAppComponentRuntimeEntry 15  }
   
   
   webAppComponentRuntimeParent OBJECT-TYPE
      SYNTAX      DisplayString (SIZE (1..256))
      MAX-ACCESS  read-only
      STATUS      current
      DESCRIPTION "BEA-proprietary Parent object's identification, with syntax
      <type>:<name>"
      ::= { webAppComponentRuntimeEntry 20  }
   
   
   webAppComponentRuntimeComponentName OBJECT-TYPE
      SYNTAX      DisplayString (SIZE (1..64))
      MAX-ACCESS  read-only
      STATUS      current
      DESCRIPTION "Provides the name of this component. "
      ::= { webAppComponentRuntimeEntry 25  }
   
   
   webAppComponentRuntimeStatus OBJECT-TYPE
      SYNTAX      DisplayString (SIZE (1..64))
      MAX-ACCESS  read-only
      STATUS      current
      DESCRIPTION "Provides the status of the component. "
      ::= { webAppComponentRuntimeEntry 30  }
   
   
   webAppComponentRuntimeSourceInfo OBJECT-TYPE
      SYNTAX      DisplayString (SIZE (1..256))
      MAX-ACCESS  read-only
      STATUS      current
      DESCRIPTION "Provides an informative string about the module's source.  Returns an informative string about the component's source. "
      ::= { webAppComponentRuntimeEntry 35  }
   
   
   webAppComponentRuntimeOpenSessionsCurrentCount OBJECT-TYPE
      SYNTAX      INTEGER
      MAX-ACCESS  read-only
      STATUS      current
      DESCRIPTION "Provides a count of the current total number of open sessions in this module.  Returns the current total number of open sessions in this component. "
      ::= { webAppComponentRuntimeEntry 50  }
   
   
   webAppComponentRuntimeOpenSessionsHighCount OBJECT-TYPE
      SYNTAX      INTEGER
      MAX-ACCESS  read-only
      STATUS      current
      DESCRIPTION "Provides the high water mark of the total number of open sessions in this server. The count starts at zero each time the server is activated. Note that this is an optimization method for a highly useful statistic that could be implemented less efficiently using change notification. "
      ::= { webAppComponentRuntimeEntry 55  }
   
   
   webAppComponentRuntimeSessionsOpenedTotalCount OBJECT-TYPE
      SYNTAX      INTEGER
      MAX-ACCESS  read-only
      STATUS      current
      DESCRIPTION "Provides a count of the total number of sessions opened. "
      ::= { webAppComponentRuntimeEntry 60  }
   
   
   webAppComponentRuntimeSingleThreadedServletPoolSize OBJECT-TYPE
      SYNTAX      INTEGER
      MAX-ACCESS  read-only
      STATUS      current
      DESCRIPTION "Provides the single threaded servlet pool size as it is configured in weblogic.xml. "
      ::= { webAppComponentRuntimeEntry 61  }
   
   
   webAppComponentRuntimeJSPVerbose OBJECT-TYPE
      SYNTAX      OCTET STRING
      MAX-ACCESS  read-only
      STATUS      current
      DESCRIPTION "Provides the JSP's verbose parameter value as it is configured in weblogic.xml. "
      ::= { webAppComponentRuntimeEntry 62  }
   
   
   webAppComponentRuntimeIndexDirectoryEnabled OBJECT-TYPE
      SYNTAX      OCTET STRING
      MAX-ACCESS  read-only
      STATUS      current
      DESCRIPTION "Provides the directory indexing indicator as it is configured in weblogic.xml. "
      ::= { webAppComponentRuntimeEntry 63  }
   
   
   webAppComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { webAppComponentRuntimeEntry 64  }
   
   
   webAppComponentRuntimeJSPDebug OBJECT-TYPE
      SYNTAX      OCTET STRING
      MAX-ACCESS  read-only
      STATUS      current
      DESCRIPTION "Provides the JSP's debug/linenumbers parameter value as it is configured in weblogic.xml. "
      ::= { webAppComponentRuntimeEntry 65  }
   
   
   webAppComponentRuntimeSessionCookieName OBJECT-TYPE
      SYNTAX      OCTET STRING
      MAX-ACCESS  read-only
      STATUS      current
      DESCRIPTION "By default, all applications on WebLogic Server specify 'JSESSIONID' as the cookie name. To provide a more specific name, edit your application's weblogic.xml deployment descriptor. "
      ::= { webAppComponentRuntimeEntry 66  }
   
   
   webAppComponentRuntimeSessionCookieDomain OBJECT-TYPE
      SYNTAX      OCTET STRING
      MAX-ACCESS  read-only
      STATUS      current
      DESCRIPTION "By default, clients can return cookies only to the server that issued the cookie. You can change this default behavior by editing your application's weblogic.xml deployment descriptor.  For more information, see the servlet specification. "
      ::= { webAppComponentRuntimeEntry 67  }
   
   
   webAppComponentRuntimeFilterDispatchedRequestsEnabled OBJECT-TYPE
      SYNTAX      OCTET STRING
      MAX-ACCESS  read-only
      STATUS      current
      DESCRIPTION "Indicates whether the dispatched requests are filtered as configured in weblogic.xml. "
      ::= { webAppComponentRuntimeEntry 68  }
   
   
   webAppComponentRuntimeLogFilename OBJECT-TYPE
      SYNTAX      OCTET STRING
      MAX-ACCESS  read-only
      STATUS      current
      DESCRIPTION "Returns the log filename as configured in the 'logging/log-filename' element in weblogic.xml. "
      ::= { webAppComponentRuntimeEntry 69  }
   
   
   webAppComponentRuntimeSessionCookiePath OBJECT-TYPE
      SYNTAX      OCTET STRING
      MAX-ACCESS  read-only
      STATUS      current
      DESCRIPTION "Provides the path name to which clients send cookies. "
      ::= { webAppComponentRuntimeEntry 70  }
   
   
   webAppComponentRuntimeJSPKeepGenerated OBJECT-TYPE
      SYNTAX      OCTET STRING
      MAX-ACCESS  read-only
      STATUS      current
      DESCRIPTION "Provides the JSP's KeepGenerated parameter value as it is configured in weblogic.xml. "
      ::= { webAppComponentRuntimeEntry 71  }
   
   
   webAppComponentRuntimeSessionCookieComment OBJECT-TYPE
      SYNTAX      OCTET STRING
      MAX-ACCESS  read-only
      STATUS      current
      DESCRIPTION "By default, all applications on WebLogic Server specify 'WebLogic Session Tracking Cookie' as the cookie comment. To provide a more specific comment, edit your application's weblogic.xml deployment descriptor. "
      ::= { webAppComponentRuntimeEntry 72  }
   
   
   webAppComponentRuntimeJSPCompileCommand OBJECT-TYPE
      SYNTAX      OCTET STRING
      MAX-ACCESS  read-only
      STATUS      current
      DESCRIPTION "Provides the JSP's compileCommand value as it is configured in weblogic.xml. "
      ::= { webAppComponentRuntimeEntry 73  }
   
   
   webAppComponentRuntimeJSPPageCheckSecs OBJECT-TYPE
      SYNTAX      Counter64
      MAX-ACCESS  read-only
      STATUS      current
      DESCRIPTION "Provides the JSP's PageCheckSecs value as it is configured in weblogic.xml. "
      ::= { webAppComponentRuntimeEntry 74  }
   
   
   webAppComponentRuntimeContextRoot OBJECT-TYPE
      SYNTAX      OCTET STRING
      MAX-ACCESS  read-only
      STATUS      current
      DESCRIPTION "Returns the context root (context path) for the web application. "
      ::= { webAppComponentRuntimeEntry 75  }
   
   
   webAppComponentRuntimeModuleURI OBJECT-TYPE
      SYNTAX      OCTET STRING
      MAX-ACCESS  read-only
      STATUS      current
      DESCRIPTION "Returns the web URI as configured in application.xml for the web application. For a standalone WAR, it will return the docroot (if exploded) or the name of the WAR file (if archived). "
      ::= { webAppComponentRuntimeEntry 76  }
   
   
   webAppComponentRuntimeSessionInvalidationIntervalSecs OBJECT-TYPE
      SYNTAX      INTEGER
      MAX-ACCESS  read-only
      STATUS      current
      DESCRIPTION "Provides the invalidation check timer interval configured for HTTP sessions. "
      ::= { webAppComponentRuntimeEntry 77  }
   
   
   webAppComponentRuntimeServletReloadCheckSecs OBJECT-TYPE
      SYNTAX      INTEGER
      MAX-ACCESS  read-only
      STATUS      current
      DESCRIPTION "Provides the servlet reload check seconds as it is configured in weblogic.xml. "
      ::= { webAppComponentRuntimeEntry 78  }
   
   
   webAppComponentRuntimeSessionCookieMaxAgeSecs OBJECT-TYPE
      SYNTAX      INTEGER
      MAX-ACCESS  read-only
      STATUS      current
      DESCRIPTION "Provides the life span of the session cookie, in seconds, after which it expires on the client. If the value is 0, the cookie expires immediately. If set to -1, the cookie expires when the user exits the browser. "
      ::= { webAppComponentRuntimeEntry 79  }
   
   
   webAppComponentRuntimeSessionTimeoutSecs OBJECT-TYPE
      SYNTAX      INTEGER
      MAX-ACCESS  read-only
      STATUS      current
      DESCRIPTION "Provides the timeout configured for HTTP sessions. "
      ::= { webAppComponentRuntimeEntry 80  }
   
   
   webAppComponentRuntimeSessionIDLength OBJECT-TYPE
      SYNTAX      INTEGER
      MAX-ACCESS  read-only
      STATUS      current
      DESCRIPTION "Provides the session ID length configured for HTTP sessions. "
      ::= { webAppComponentRuntimeEntry 81  }
   
   
   webAppComponentRuntimeDeploymentState OBJECT-TYPE
      SYNTAX      INTEGER
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { webAppComponentRuntimeEntry 82  }
   
   
   webAppComponentRuntimeSessionMonitoringEnabled OBJECT-TYPE
      SYNTAX      OCTET STRING
      MAX-ACCESS  read-only
      STATUS      current
      DESCRIPTION "Provides the session monitoring indicator as it is configured in weblogic.xml. "
      ::= { webAppComponentRuntimeEntry 83  }
   
   
   webAppComponentRuntimeServletSessionsMonitoringIds OBJECT-TYPE
      SYNTAX      OCTET STRING
      MAX-ACCESS  read-only
      STATUS      current
      DESCRIPTION " This method returns an array of monitoring IDs for HTTP sessions. By default, the monitoring ID for a given HTTP session is a random string (not the same as session ID for security reasons). If the value of the element monitoring-attribute-name in session-descriptor of weblogic.xml is set, the monitoring ID will be the toString() of the attribute value in the session, using monitoring-attribute-name as the key.  "
      ::= { webAppComponentRuntimeEntry 84  }
   
   
   webAppComponentRuntimeApplicationIdentifier OBJECT-TYPE
      SYNTAX      OCTET STRING
      MAX-ACCESS  read-only
      STATUS      current
      DESCRIPTION "Provides the identifier of the application that contains the web module. "
      ::= { webAppComponentRuntimeEntry 85  }
   
   
   webAppComponentRuntimeConfiguredContextRoot OBJECT-TYPE
      SYNTAX      OCTET STRING
      MAX-ACCESS  read-only
      STATUS      current
      DESCRIPTION " Returns the context root (context path) configured in weblogic-application.xml or web.xml file, or determined by name of the war file.    For web application deployed in partition scope, this configured context root does not include uriPrefix of the virtual target. The {@link #getContextRoot()} method returns value which includes the uriPrefix of the virtual target.    For web application deployed in domain scope, this method returns same value as {@link #getContextRoot()} method.  "
      ::= { webAppComponentRuntimeEntry 86  }
   
   
   webServerRuntimeTable OBJECT-TYPE
      SYNTAX      SEQUENCE OF WebServerRuntimeEntry
      MAX-ACCESS  not-accessible
      STATUS      current
      DESCRIPTION "Describes a Web Server (HTTP Server) "
      ::= { wls 431  }
      
   
   webServerRuntimeEntry OBJECT-TYPE
      SYNTAX      WebServerRuntimeEntry
      MAX-ACCESS  not-accessible
      STATUS      current
      DESCRIPTION "Entry of webServerRuntimeTable"
      INDEX { webServerRuntimeIndex}
      ::= { webServerRuntimeTable 1 }
      
   WebServerRuntimeEntry ::=
      SEQUENCE
      {
         webServerRuntimeIndex DisplayString,
         webServerRuntimeObjectName DisplayString,
         webServerRuntimeType DisplayString,
         webServerRuntimeName DisplayString,
         webServerRuntimeParent DisplayString,
         webServerRuntimeWebServerName DisplayString,
         webServerRuntimeDefaultWebServer OCTET STRING
      }
      
   
   webServerRuntimeIndex OBJECT-TYPE
      SYNTAX      DisplayString (SIZE (1..16))
      MAX-ACCESS  read-only
      STATUS      current
      DESCRIPTION "Unique value directed from ObjectName which is used as table index"
      ::= { webServerRuntimeEntry 1  }
   
   
   webServerRuntimeObjectName OBJECT-TYPE
      SYNTAX      DisplayString (SIZE (1..256))
      MAX-ACCESS  read-only
      STATUS      current
      DESCRIPTION "JMX-standard MBean name"
      ::= { webServerRuntimeEntry 5  }
   
   
   webServerRuntimeType OBJECT-TYPE
      SYNTAX      DisplayString (SIZE (1..64))
      MAX-ACCESS  read-only
      STATUS      current
      DESCRIPTION "Returns the type of the MBean. "
      ::= { webServerRuntimeEntry 10  }
   
   
   webServerRuntimeName OBJECT-TYPE
      SYNTAX      DisplayString (SIZE (1..64))
      MAX-ACCESS  read-only
      STATUS      current
      DESCRIPTION "The name of this configuration. WebLogic Server uses an MBean to implement and persist the configuration. "
      ::= { webServerRuntimeEntry 15  }
   
   
   webServerRuntimeParent OBJECT-TYPE
      SYNTAX      DisplayString (SIZE (1..256))
      MAX-ACCESS  read-only
      STATUS      current
      DESCRIPTION "BEA-proprietary Parent object's identification, with syntax
      <type>:<name>"
      ::= { webServerRuntimeEntry 20  }
   
   
   webServerRuntimeWebServerName OBJECT-TYPE
      SYNTAX      DisplayString (SIZE (1..64))
      MAX-ACCESS  read-only
      STATUS      current
      DESCRIPTION "Provides the name of the WebServer. "
      ::= { webServerRuntimeEntry 25  }
   
   
   webServerRuntimeDefaultWebServer OBJECT-TYPE
      SYNTAX      OCTET STRING
      MAX-ACCESS  read-only
      STATUS      current
      DESCRIPTION "Indicates whether it is the default WebServer or a VirtualHost "
      ::= { webServerRuntimeEntry 26  }
   
   
   wlecConnectionPoolRuntimeTable OBJECT-TYPE
      SYNTAX      SEQUENCE OF WlecConnectionPoolRuntimeEntry
      MAX-ACCESS  not-accessible
      STATUS      current
      DESCRIPTION "This table is used for monitoring a WebLogic WLEC Connection Pool"
      ::= { wls 440  }
      
   
   wlecConnectionPoolRuntimeEntry OBJECT-TYPE
      SYNTAX      WlecConnectionPoolRuntimeEntry
      MAX-ACCESS  not-accessible
      STATUS      current
      DESCRIPTION "Entry of wlecConnectionPoolRuntimeTable"
      INDEX { wlecConnectionPoolRuntimeIndex}
      ::= { wlecConnectionPoolRuntimeTable 1 }
      
   WlecConnectionPoolRuntimeEntry ::=
      SEQUENCE
      {
         wlecConnectionPoolRuntimeIndex DisplayString,
         wlecConnectionPoolRuntimeObjectName DisplayString,
         wlecConnectionPoolRuntimeType DisplayString,
         wlecConnectionPoolRuntimeName DisplayString,
         wlecConnectionPoolRuntimeParent DisplayString,
         wlecConnectionPoolRuntimePoolName DisplayString,
         wlecConnectionPoolRuntimeWLEDomainName DisplayString,
         wlecConnectionPoolRuntimeMaxCapacity INTEGER,
         wlecConnectionPoolRuntimePoolState DisplayString,
         wlecConnectionPoolRuntimeSecurityContextPropagation INTEGER,
         wlecConnectionPoolRuntimeCertificateBasedAuthentication INTEGER,
         wlecConnectionPoolRuntimeConnections DisplayString
      }
      
   
   wlecConnectionPoolRuntimeIndex OBJECT-TYPE
      SYNTAX      DisplayString (SIZE (1..16))
      MAX-ACCESS  read-only
      STATUS      current
      DESCRIPTION "Unique value directed from ObjectName which is used as table index"
      ::= { wlecConnectionPoolRuntimeEntry 1  }
   
   
   wlecConnectionPoolRuntimeObjectName OBJECT-TYPE
      SYNTAX      DisplayString (SIZE (1..256))
      MAX-ACCESS  read-only
      STATUS      current
      DESCRIPTION "JMX-standard MBean name"
      ::= { wlecConnectionPoolRuntimeEntry 5  }
   
   
   wlecConnectionPoolRuntimeType OBJECT-TYPE
      SYNTAX      DisplayString (SIZE (1..64))
      MAX-ACCESS  read-only
      STATUS      current
      DESCRIPTION "BEA-proprietary MBean type"
      ::= { wlecConnectionPoolRuntimeEntry 10  }
   
   
   wlecConnectionPoolRuntimeName OBJECT-TYPE
      SYNTAX      DisplayString (SIZE (1..64))
      MAX-ACCESS  read-only
      STATUS      current
      DESCRIPTION "BEA-proprietary MBean name"
      ::= { wlecConnectionPoolRuntimeEntry 15  }
   
   
   wlecConnectionPoolRuntimeParent OBJECT-TYPE
      SYNTAX      DisplayString (SIZE (1..256))
      MAX-ACCESS  read-only
      STATUS      current
      DESCRIPTION "BEA-proprietary Parent object's identification, with syntax
      <type>:<name>"
      ::= { wlecConnectionPoolRuntimeEntry 20  }
   
   
   wlecConnectionPoolRuntimePoolName OBJECT-TYPE
      SYNTAX      DisplayString (SIZE (1..64))
      MAX-ACCESS  read-only
      STATUS      current
      DESCRIPTION "The configured name of this WLEC pool."
      ::= { wlecConnectionPoolRuntimeEntry 25  }
   
   
   wlecConnectionPoolRuntimeWLEDomainName OBJECT-TYPE
      SYNTAX      DisplayString (SIZE (1..64))
      MAX-ACCESS  read-only
      STATUS      current
      DESCRIPTION "The WLE DomainName this WLEC pool is connected to."
      ::= { wlecConnectionPoolRuntimeEntry 30  }
   
   
   wlecConnectionPoolRuntimeMaxCapacity OBJECT-TYPE
      SYNTAX      INTEGER
      MAX-ACCESS  read-only
      STATUS      current
      DESCRIPTION "The maximum capacity configured for this WLEC pool."
      ::= { wlecConnectionPoolRuntimeEntry 35  }
   
   
   wlecConnectionPoolRuntimePoolState OBJECT-TYPE
      SYNTAX      DisplayString (SIZE (1..16))
      MAX-ACCESS  read-only
      STATUS      current
      DESCRIPTION "The pool state as one of 'Active' OR 'Suspended'"
      ::= { wlecConnectionPoolRuntimeEntry 40  }
   
   
   wlecConnectionPoolRuntimeSecurityContextPropagation OBJECT-TYPE
      SYNTAX      INTEGER
                  {
                     true(1),
                     false(2)
                  }
      
      MAX-ACCESS  read-only
      STATUS      current
      DESCRIPTION "A boolean value (true Or false). Is the security context propagated"
      ::= { wlecConnectionPoolRuntimeEntry 45  }
   
   
   wlecConnectionPoolRuntimeCertificateBasedAuthentication OBJECT-TYPE
      SYNTAX      INTEGER
                  {
                     true(1),
                     false(2)
                  }
      
      MAX-ACCESS  read-only
      STATUS      current
      DESCRIPTION "A boolean value (true Or false). Is certificate-based authentication enabled"
      ::= { wlecConnectionPoolRuntimeEntry 50  }
   
   
   wlecConnectionPoolRuntimeConnections OBJECT-TYPE
      SYNTAX      DisplayString (SIZE (1..2048))
      MAX-ACCESS  read-only
      STATUS      current
      DESCRIPTION "An array of WLECConnectionRuntimeMBeans that each
      represents the statistics for a WLEC Connection."
      ::= { wlecConnectionPoolRuntimeEntry 55  }
   
   
   wlecConnectionRuntimeTable OBJECT-TYPE
      SYNTAX      SEQUENCE OF WlecConnectionRuntimeEntry
      MAX-ACCESS  not-accessible
      STATUS      current
      DESCRIPTION "This table is used for monitoring individual WebLogic WLEC connections"
      ::= { wls 450  }
      
   
   wlecConnectionRuntimeEntry OBJECT-TYPE
      SYNTAX      WlecConnectionRuntimeEntry
      MAX-ACCESS  not-accessible
      STATUS      current
      DESCRIPTION "Entry of wlecConnectionRuntimeTable"
      INDEX { wlecConnectionRuntimeIndex}
      ::= { wlecConnectionRuntimeTable 1 }
      
   WlecConnectionRuntimeEntry ::=
      SEQUENCE
      {
         wlecConnectionRuntimeIndex DisplayString,
         wlecConnectionRuntimeObjectName DisplayString,
         wlecConnectionRuntimeType DisplayString,
         wlecConnectionRuntimeName DisplayString,
         wlecConnectionRuntimeParent DisplayString,
         wlecConnectionRuntimeAddress DisplayString,
         wlecConnectionRuntimeLastAccessTime DisplayString,
         wlecConnectionRuntimeAlive INTEGER,
         wlecConnectionRuntimeRequestCount INTEGER,
         wlecConnectionRuntimePendingRequestCount INTEGER,
         wlecConnectionRuntimeErrorCount INTEGER,
         wlecConnectionRuntimeInTransaction INTEGER
      }
      
   
   wlecConnectionRuntimeIndex OBJECT-TYPE
      SYNTAX      DisplayString (SIZE (1..16))
      MAX-ACCESS  read-only
      STATUS      current
      DESCRIPTION "Unique value directed from ObjectName which is used as table index"
      ::= { wlecConnectionRuntimeEntry 1  }
   
   
   wlecConnectionRuntimeObjectName OBJECT-TYPE
      SYNTAX      DisplayString (SIZE (1..256))
      MAX-ACCESS  read-only
      STATUS      current
      DESCRIPTION "JMX-standard MBean name"
      ::= { wlecConnectionRuntimeEntry 5  }
   
   
   wlecConnectionRuntimeType OBJECT-TYPE
      SYNTAX      DisplayString (SIZE (1..64))
      MAX-ACCESS  read-only
      STATUS      current
      DESCRIPTION "BEA-proprietary MBean type"
      ::= { wlecConnectionRuntimeEntry 10  }
   
   
   wlecConnectionRuntimeName OBJECT-TYPE
      SYNTAX      DisplayString (SIZE (1..64))
      MAX-ACCESS  read-only
      STATUS      current
      DESCRIPTION "BEA-proprietary MBean name"
      ::= { wlecConnectionRuntimeEntry 15  }
   
   
   wlecConnectionRuntimeParent OBJECT-TYPE
      SYNTAX      DisplayString (SIZE (1..256))
      MAX-ACCESS  read-only
      STATUS      current
      DESCRIPTION "BEA-proprietary Parent object's identification, with syntax
      <type>:<name>"
      ::= { wlecConnectionRuntimeEntry 20  }
   
   
   wlecConnectionRuntimeAddress OBJECT-TYPE
      SYNTAX      DisplayString (SIZE (1..256))
      MAX-ACCESS  read-only
      STATUS      current
      DESCRIPTION "The connection Address"
      ::= { wlecConnectionRuntimeEntry 25  }
   
   
   wlecConnectionRuntimeLastAccessTime OBJECT-TYPE
      SYNTAX      DisplayString (SIZE (1..32))
      MAX-ACCESS  read-only
      STATUS      current
      DESCRIPTION "The Last Access Date and Time"
      ::= { wlecConnectionRuntimeEntry 30  }
   
   
   wlecConnectionRuntimeAlive OBJECT-TYPE
      SYNTAX      INTEGER
                  {
                     true(1),
                     false(2)
                  }
      
      MAX-ACCESS  read-only
      STATUS      current
      DESCRIPTION "A boolean value (true Or false). Returns the connection Alive indicator"
      ::= { wlecConnectionRuntimeEntry 35  }
   
   
   wlecConnectionRuntimeRequestCount OBJECT-TYPE
      SYNTAX      INTEGER
      MAX-ACCESS  read-only
      STATUS      current
      DESCRIPTION "The Request Count"
      ::= { wlecConnectionRuntimeEntry 40  }
   
   
   wlecConnectionRuntimePendingRequestCount OBJECT-TYPE
      SYNTAX      INTEGER
      MAX-ACCESS  read-only
      STATUS      current
      DESCRIPTION "The Pending Request Count"
      ::= { wlecConnectionRuntimeEntry 45  }
   
   
   wlecConnectionRuntimeErrorCount OBJECT-TYPE
      SYNTAX      INTEGER
      MAX-ACCESS  read-only
      STATUS      current
      DESCRIPTION "The Request Error Count"
      ::= { wlecConnectionRuntimeEntry 50  }
   
   
   wlecConnectionRuntimeInTransaction OBJECT-TYPE
      SYNTAX      INTEGER
                  {
                     true(1),
                     false(2)
                  }
      
      MAX-ACCESS  read-only
      STATUS      current
      DESCRIPTION "A boolean value (true Or false). Returns the Connection in Transaction indicator"
      ::= { wlecConnectionRuntimeEntry 55  }
   
   
   wlecConnectionServiceRuntimeTable OBJECT-TYPE
      SYNTAX      SEQUENCE OF WlecConnectionServiceRuntimeEntry
      MAX-ACCESS  not-accessible
      STATUS      current
      DESCRIPTION "This table describes the web server."
      ::= { wls 451  }
      
   
   wlecConnectionServiceRuntimeEntry OBJECT-TYPE
      SYNTAX      WlecConnectionServiceRuntimeEntry
      MAX-ACCESS  not-accessible
      STATUS      current
      DESCRIPTION "Entry of wlecConnectionServiceRuntimeTable"
      INDEX { wlecConnectionServiceRuntimeIndex}
      ::= { wlecConnectionServiceRuntimeTable 1 }
      
   WlecConnectionServiceRuntimeEntry ::=
      SEQUENCE
      {
         wlecConnectionServiceRuntimeIndex DisplayString,
         wlecConnectionServiceRuntimeObjectName DisplayString,
         wlecConnectionServiceRuntimeType DisplayString,
         wlecConnectionServiceRuntimeName DisplayString,
         wlecConnectionServiceRuntimeParent DisplayString,
         wlecConnectionServiceRuntimeConnectionPoolCount INTEGER
      }
      
   
   wlecConnectionServiceRuntimeIndex OBJECT-TYPE
      SYNTAX      DisplayString (SIZE (1..16))
      MAX-ACCESS  read-only
      STATUS      current
      DESCRIPTION "Unique value directed from ObjectName which is used as table index"
      ::= { wlecConnectionServiceRuntimeEntry 1  }
   
   
   wlecConnectionServiceRuntimeObjectName OBJECT-TYPE
      SYNTAX      DisplayString (SIZE (1..256))
      MAX-ACCESS  read-only
      STATUS      current
      DESCRIPTION "JMX-standard MBean name"
      ::= { wlecConnectionServiceRuntimeEntry 5  }
   
   
   wlecConnectionServiceRuntimeType OBJECT-TYPE
      SYNTAX      DisplayString (SIZE (1..64))
      MAX-ACCESS  read-only
      STATUS      current
      DESCRIPTION "BEA-proprietary MBean type"
      ::= { wlecConnectionServiceRuntimeEntry 10  }
   
   
   wlecConnectionServiceRuntimeName OBJECT-TYPE
      SYNTAX      DisplayString (SIZE (1..64))
      MAX-ACCESS  read-only
      STATUS      current
      DESCRIPTION "BEA-proprietary MBean name"
      ::= { wlecConnectionServiceRuntimeEntry 15  }
   
   
   wlecConnectionServiceRuntimeParent OBJECT-TYPE
      SYNTAX      DisplayString (SIZE (1..256))
      MAX-ACCESS  read-only
      STATUS      current
      DESCRIPTION "BEA-proprietary Parent object's identification, with syntax
      <type>:<name>"
      ::= { wlecConnectionServiceRuntimeEntry 20  }
   
   
   wlecConnectionServiceRuntimeConnectionPoolCount OBJECT-TYPE
      SYNTAX      INTEGER
      MAX-ACCESS  read-only
      STATUS      current
      DESCRIPTION "Return the pool count."
      ::= { wlecConnectionServiceRuntimeEntry 25  }
   
   
   connectorConnectionRuntimeTable OBJECT-TYPE
      SYNTAX      SEQUENCE OF ConnectorConnectionRuntimeEntry
      MAX-ACCESS  not-accessible
      STATUS      current
      DESCRIPTION "This class is used for monitoring individual WebLogic Connector connections "
      ::= { wls 454  }
      
   
   connectorConnectionRuntimeEntry OBJECT-TYPE
      SYNTAX      ConnectorConnectionRuntimeEntry
      MAX-ACCESS  not-accessible
      STATUS      current
      DESCRIPTION "Entry of connectorConnectionRuntimeTable"
      INDEX { connectorConnectionRuntimeIndex}
      ::= { connectorConnectionRuntimeTable 1 }
      
   ConnectorConnectionRuntimeEntry ::=
      SEQUENCE
      {
         connectorConnectionRuntimeIndex DisplayString,
         connectorConnectionRuntimeObjectName DisplayString,
         connectorConnectionRuntimeType DisplayString,
         connectorConnectionRuntimeName DisplayString,
         connectorConnectionRuntimeParent DisplayString,
         connectorConnectionRuntimeActiveHandlesCurrentCount INTEGER,
         connectorConnectionRuntimeActiveHandlesHighCount INTEGER,
         connectorConnectionRuntimeHandlesCreatedTotalCount INTEGER,
         connectorConnectionRuntimeCurrentlyInUse INTEGER,
         connectorConnectionRuntimeInTransaction INTEGER,
         connectorConnectionRuntimeShared INTEGER,
         connectorConnectionRuntimeEISProductVersion OCTET STRING,
         connectorConnectionRuntimeDeletable OCTET STRING,
         connectorConnectionRuntimeReserveDurationTime Counter64,
         connectorConnectionRuntimeTransactionId OCTET STRING,
         connectorConnectionRuntimeConnectionFactoryClassName OCTET STRING,
         connectorConnectionRuntimeEISProductName OCTET STRING,
         connectorConnectionRuntimeUserName OCTET STRING,
         connectorConnectionRuntimeReserveTime Counter64,
         connectorConnectionRuntimeCreationDurationTime Counter64,
         connectorConnectionRuntimeManagedConnectionFactoryClassName OCTET STRING,
         connectorConnectionRuntimeMaxConnections OCTET STRING,
         connectorConnectionRuntimeLastUsageString OCTET STRING,
         connectorConnectionRuntimeLastUsage Counter64,
         connectorConnectionRuntimeIdle OCTET STRING,
         connectorConnectionRuntimeStackTrace OCTET STRING
      }
      
   
   connectorConnectionRuntimeIndex OBJECT-TYPE
      SYNTAX      DisplayString (SIZE (1..16))
      MAX-ACCESS  read-only
      STATUS      current
      DESCRIPTION "Unique value directed from ObjectName which is used as table index"
      ::= { connectorConnectionRuntimeEntry 1  }
   
   
   connectorConnectionRuntimeObjectName OBJECT-TYPE
      SYNTAX      DisplayString (SIZE (1..256))
      MAX-ACCESS  read-only
      STATUS      current
      DESCRIPTION "JMX-standard MBean name"
      ::= { connectorConnectionRuntimeEntry 5  }
   
   
   connectorConnectionRuntimeType OBJECT-TYPE
      SYNTAX      DisplayString (SIZE (1..64))
      MAX-ACCESS  read-only
      STATUS      current
      DESCRIPTION "Returns the type of the MBean. "
      ::= { connectorConnectionRuntimeEntry 10  }
   
   
   connectorConnectionRuntimeName OBJECT-TYPE
      SYNTAX      DisplayString (SIZE (1..64))
      MAX-ACCESS  read-only
      STATUS      current
      DESCRIPTION "The name of this configuration. WebLogic Server uses an MBean to implement and persist the configuration. "
      ::= { connectorConnectionRuntimeEntry 15  }
   
   
   connectorConnectionRuntimeParent OBJECT-TYPE
      SYNTAX      DisplayString (SIZE (1..256))
      MAX-ACCESS  read-only
      STATUS      current
      DESCRIPTION "BEA-proprietary Parent object's identification, with syntax
      <type>:<name>"
      ::= { connectorConnectionRuntimeEntry 20  }
   
   
   connectorConnectionRuntimeActiveHandlesCurrentCount OBJECT-TYPE
      SYNTAX      INTEGER
      MAX-ACCESS  read-only
      STATUS      current
      DESCRIPTION "The current total active connection handles for this connection. "
      ::= { connectorConnectionRuntimeEntry 25  }
   
   
   connectorConnectionRuntimeActiveHandlesHighCount OBJECT-TYPE
      SYNTAX      INTEGER
      MAX-ACCESS  read-only
      STATUS      current
      DESCRIPTION "The high water mark of active connection handles for this connection since the connection was created. "
      ::= { connectorConnectionRuntimeEntry 30  }
   
   
   connectorConnectionRuntimeHandlesCreatedTotalCount OBJECT-TYPE
      SYNTAX      INTEGER
      MAX-ACCESS  read-only
      STATUS      current
      DESCRIPTION "The total number of connection handles created for this connection since the connection was created. "
      ::= { connectorConnectionRuntimeEntry 35  }
   
   
   connectorConnectionRuntimeCurrentlyInUse OBJECT-TYPE
      SYNTAX      INTEGER
                  {
                     true(1),
                     false(2)
                  }
      
      MAX-ACCESS  read-only
      STATUS      current
      DESCRIPTION "Indicates whether the connection is currently in use. "
      ::= { connectorConnectionRuntimeEntry 40  }
   
   
   connectorConnectionRuntimeInTransaction OBJECT-TYPE
      SYNTAX      INTEGER
                  {
                     true(1),
                     false(2)
                  }
      
      MAX-ACCESS  read-only
      STATUS      current
      DESCRIPTION "Indicates whether the connection is currently in use in a transaction. "
      ::= { connectorConnectionRuntimeEntry 45  }
   
   
   connectorConnectionRuntimeShared OBJECT-TYPE
      SYNTAX      INTEGER
      MAX-ACCESS  read-only
      STATUS      current
      DESCRIPTION "Indicates whether the connection is currently being shared by more than one invoker. "
      ::= { connectorConnectionRuntimeEntry 50  }
   
   
   connectorConnectionRuntimeEISProductVersion OBJECT-TYPE
      SYNTAX      OCTET STRING
      MAX-ACCESS  read-only
      STATUS      current
      DESCRIPTION "Returns the EISProductVersion associated with the ManagedConnection's MetaData. "
      ::= { connectorConnectionRuntimeEntry 51  }
   
   
   connectorConnectionRuntimeDeletable OBJECT-TYPE
      SYNTAX      OCTET STRING
      MAX-ACCESS  read-only
      STATUS      current
      DESCRIPTION "Indicates whether the connection can be closed manually through the console. "
      ::= { connectorConnectionRuntimeEntry 52  }
   
   
   connectorConnectionRuntimeReserveDurationTime OBJECT-TYPE
      SYNTAX      Counter64
      MAX-ACCESS  read-only
      STATUS      current
      DESCRIPTION "Get the time taken to reserve this connection. "
      ::= { connectorConnectionRuntimeEntry 53  }
   
   
   connectorConnectionRuntimeTransactionId OBJECT-TYPE
      SYNTAX      OCTET STRING
      MAX-ACCESS  read-only
      STATUS      current
      DESCRIPTION "Get the Transaction ID of the transaction that this connection is being used with. "
      ::= { connectorConnectionRuntimeEntry 54  }
   
   
   connectorConnectionRuntimeConnectionFactoryClassName OBJECT-TYPE
      SYNTAX      OCTET STRING
      MAX-ACCESS  read-only
      STATUS      current
      DESCRIPTION "Returns the connection factory class name. "
      ::= { connectorConnectionRuntimeEntry 55  }
   
   
   connectorConnectionRuntimeEISProductName OBJECT-TYPE
      SYNTAX      OCTET STRING
      MAX-ACCESS  read-only
      STATUS      current
      DESCRIPTION "Returns the EISProductName associated with the ManagedConnection's MetaData "
      ::= { connectorConnectionRuntimeEntry 56  }
   
   
   connectorConnectionRuntimeUserName OBJECT-TYPE
      SYNTAX      OCTET STRING
      MAX-ACCESS  read-only
      STATUS      current
      DESCRIPTION "Returns the UserName associated with the ManagedConnection's MetaData "
      ::= { connectorConnectionRuntimeEntry 57  }
   
   
   connectorConnectionRuntimeReserveTime OBJECT-TYPE
      SYNTAX      Counter64
      MAX-ACCESS  read-only
      STATUS      current
      DESCRIPTION "Return the last time the connection was reserved. "
      ::= { connectorConnectionRuntimeEntry 58  }
   
   
   connectorConnectionRuntimeCreationDurationTime OBJECT-TYPE
      SYNTAX      Counter64
      MAX-ACCESS  read-only
      STATUS      current
      DESCRIPTION "Return the time taken to create the connection. "
      ::= { connectorConnectionRuntimeEntry 59  }
   
   
   connectorConnectionRuntimeManagedConnectionFactoryClassName OBJECT-TYPE
      SYNTAX      OCTET STRING
      MAX-ACCESS  read-only
      STATUS      current
      DESCRIPTION "Returns the managed connection factory class name. "
      ::= { connectorConnectionRuntimeEntry 60  }
   
   
   connectorConnectionRuntimeMaxConnections OBJECT-TYPE
      SYNTAX      OCTET STRING
      MAX-ACCESS  read-only
      STATUS      current
      DESCRIPTION "Returns the MaxConnections associated with the ManagedConnection's MetaData "
      ::= { connectorConnectionRuntimeEntry 61  }
   
   
   connectorConnectionRuntimeLastUsageString OBJECT-TYPE
      SYNTAX      OCTET STRING
      MAX-ACCESS  read-only
      STATUS      current
      DESCRIPTION "The last usage time stamp for the connection as a string. "
      ::= { connectorConnectionRuntimeEntry 62  }
   
   
   connectorConnectionRuntimeLastUsage OBJECT-TYPE
      SYNTAX      Counter64
      MAX-ACCESS  read-only
      STATUS      current
      DESCRIPTION "The last usage time stamp for the connection in milliseconds, as returned by System.currentTimeMillis(). "
      ::= { connectorConnectionRuntimeEntry 63  }
   
   
   connectorConnectionRuntimeIdle OBJECT-TYPE
      SYNTAX      OCTET STRING
      MAX-ACCESS  read-only
      STATUS      current
      DESCRIPTION "Indicates whether the connection has been idle for a period extending beyond the configured maximum. "
      ::= { connectorConnectionRuntimeEntry 64  }
   
   
   connectorConnectionRuntimeStackTrace OBJECT-TYPE
      SYNTAX      OCTET STRING
      MAX-ACCESS  read-only
      STATUS      current
      DESCRIPTION "The stack trace for the current connection, which will be blank unless connection-profiling-enabled is set to true in weblogic-ra.xml "
      ::= { connectorConnectionRuntimeEntry 65  }
   
   
   connectorConnectionPoolRuntimeTable OBJECT-TYPE
      SYNTAX      SEQUENCE OF ConnectorConnectionPoolRuntimeEntry
      MAX-ACCESS  not-accessible
      STATUS      current
      DESCRIPTION "This class is used for monitoring a WebLogic Connector Connection Pool "
      ::= { wls 455  }
      
   
   connectorConnectionPoolRuntimeEntry OBJECT-TYPE
      SYNTAX      ConnectorConnectionPoolRuntimeEntry
      MAX-ACCESS  not-accessible
      STATUS      current
      DESCRIPTION "Entry of connectorConnectionRuntimeTable"
      INDEX { connectorConnectionPoolRuntimeIndex}
      ::= { connectorConnectionPoolRuntimeTable 1 }
      
   ConnectorConnectionPoolRuntimeEntry ::=
      SEQUENCE
      {
         connectorConnectionPoolRuntimeIndex DisplayString,
         connectorConnectionPoolRuntimeObjectName DisplayString,
         connectorConnectionPoolRuntimeType DisplayString,
         connectorConnectionPoolRuntimeName DisplayString,
         connectorConnectionPoolRuntimeParent DisplayString,
         connectorConnectionPoolRuntimePoolName DisplayString,
         connectorConnectionPoolRuntimeJNDIName DisplayString,
         connectorConnectionPoolRuntimeConnectionFactoryName DisplayString,
         connectorConnectionPoolRuntimeResourceAdapterLinkRefName DisplayString,
         connectorConnectionPoolRuntimeLogFileName DisplayString,
         connectorConnectionPoolRuntimeTransactionSupport DisplayString,
         connectorConnectionPoolRuntimeLoggingEnabled INTEGER,
         connectorConnectionPoolRuntimeMaxCapacity INTEGER,
         connectorConnectionPoolRuntimeInitialCapacity INTEGER,
         connectorConnectionPoolRuntimeCapacityIncrement INTEGER,
         connectorConnectionPoolRuntimeShrinkingEnabled INTEGER,
         connectorConnectionPoolRuntimeShrinkPeriodMinutes INTEGER,
         connectorConnectionPoolRuntimeActiveConnectionsCurrentCount INTEGER,
         connectorConnectionPoolRuntimeActiveConnectionsHighCount INTEGER,
         connectorConnectionPoolRuntimeFreeConnectionsCurrentCount INTEGER,
         connectorConnectionPoolRuntimeFreeConnectionsHighCount INTEGER,
         connectorConnectionPoolRuntimeAverageActiveUsage INTEGER,
         connectorConnectionPoolRuntimeShrinkCountDownTime INTEGER,
         connectorConnectionPoolRuntimeRecycledTotal INTEGER,
         connectorConnectionPoolRuntimeConnectionsCreatedTotalCount INTEGER,
         connectorConnectionPoolRuntimeConnectionsMatchedTotalCount INTEGER,
         connectorConnectionPoolRuntimeConnectionsDestroyedTotalCount INTEGER,
         connectorConnectionPoolRuntimeConnectionsRejectedTotalCount INTEGER,
         connectorConnectionPoolRuntimeConnectionLeakProfileCount INTEGER,
         connectorConnectionPoolRuntimeNumberDetectedIdle INTEGER,
         connectorConnectionPoolRuntimeNumberDetectedLeaks INTEGER,
         connectorConnectionPoolRuntimeFreePoolSizeHighWaterMark Counter64,
         connectorConnectionPoolRuntimeKey OCTET STRING,
         connectorConnectionPoolRuntimeCurrentCapacity Counter64,
         connectorConnectionPoolRuntimeMCFClassName OCTET STRING,
         connectorConnectionPoolRuntimeTestable OCTET STRING,
         connectorConnectionPoolRuntimeNumUnavailableHighCount INTEGER,
         connectorConnectionPoolRuntimeConnectionsDestroyedByErrorTotalCt INTEGER,
         connectorConnectionPoolRuntimeNumWaiters Counter64,
         connectorConnectionPoolRuntimeConnectorEisType OCTET STRING,
         connectorConnectionPoolRuntimeNumWaitersCurrentCount INTEGER,
         connectorConnectionPoolRuntimeMaxIdleTime INTEGER,
         connectorConnectionPoolRuntimeLastShrinkTime Counter64,
         connectorConnectionPoolRuntimeState OCTET STRING,
         connectorConnectionPoolRuntimeCloseCount Counter64,
         connectorConnectionPoolRuntimeManagedConnectionFactoryClassName OCTET STRING,
         connectorConnectionPoolRuntimeHighestNumWaiters Counter64,
         connectorConnectionPoolRuntimePoolSizeHighWaterMark Counter64,
         connectorConnectionPoolRuntimeConnectionFactoryClassName OCTET STRING,
         connectorConnectionPoolRuntimeEISResourceId OCTET STRING,
         connectorConnectionPoolRuntimeFreePoolSizeLowWaterMark Counter64,
         connectorConnectionPoolRuntimePoolSizeLowWaterMark Counter64,
         connectorConnectionPoolRuntimeConsDestroyedByShrinkingTotalCount INTEGER,
         connectorConnectionPoolRuntimeNumUnavailableCurrentCount INTEGER,
         connectorConnectionPoolRuntimeProxyOn OCTET STRING,
         connectorConnectionPoolRuntimeConnectionIdleProfileCount INTEGER,
         connectorConnectionPoolRuntimeConnectionProfilingEnabled OCTET STRING,
         connectorConnectionPoolRuntimeRuntimeTransactionSupport OCTET STRING,
         connectorConnectionPoolRuntimeHealthState OCTET STRING,
         connectorConnectionPoolRuntimeLogFileStreamOpened OCTET STRING
      }
      
   
   connectorConnectionPoolRuntimeIndex OBJECT-TYPE
      SYNTAX      DisplayString (SIZE (1..16))
      MAX-ACCESS  read-only
      STATUS      current
      DESCRIPTION "Unique value directed from ObjectName which is used as table index"
      ::= { connectorConnectionPoolRuntimeEntry 1  }
   
   
   connectorConnectionPoolRuntimeObjectName OBJECT-TYPE
      SYNTAX      DisplayString (SIZE (1..256))
      MAX-ACCESS  read-only
      STATUS      current
      DESCRIPTION "JMX-standard MBean name"
      ::= { connectorConnectionPoolRuntimeEntry 5  }
   
   
   connectorConnectionPoolRuntimeType OBJECT-TYPE
      SYNTAX      DisplayString (SIZE (1..64))
      MAX-ACCESS  read-only
      STATUS      current
      DESCRIPTION "Returns the type of the MBean. "
      ::= { connectorConnectionPoolRuntimeEntry 10  }
   
   
   connectorConnectionPoolRuntimeName OBJECT-TYPE
      SYNTAX      DisplayString (SIZE (1..64))
      MAX-ACCESS  read-only
      STATUS      current
      DESCRIPTION "The name of this configuration. WebLogic Server uses an MBean to implement and persist the configuration. "
      ::= { connectorConnectionPoolRuntimeEntry 15  }
   
   
   connectorConnectionPoolRuntimeParent OBJECT-TYPE
      SYNTAX      DisplayString (SIZE (1..256))
      MAX-ACCESS  read-only
      STATUS      current
      DESCRIPTION "BEA-proprietary Parent object's identification, with syntax
      <type>:<name>"
      ::= { connectorConnectionPoolRuntimeEntry 20  }
   
   
   connectorConnectionPoolRuntimePoolName OBJECT-TYPE
      SYNTAX      DisplayString (SIZE (1..256))
      MAX-ACCESS  read-only
      STATUS      current
      DESCRIPTION "The configured Logical Name for the Connection Factory using this Connector connection pool. "
      ::= { connectorConnectionPoolRuntimeEntry 25  }
   
   
   connectorConnectionPoolRuntimeJNDIName OBJECT-TYPE
      SYNTAX      DisplayString (SIZE (1..64))
      MAX-ACCESS  read-only
      STATUS      current
      DESCRIPTION "The configured JNDI Name for the Connection Factory using this Connector connection pool. "
      ::= { connectorConnectionPoolRuntimeEntry 30  }
   
   
   connectorConnectionPoolRuntimeConnectionFactoryName OBJECT-TYPE
      SYNTAX      DisplayString (SIZE (1..256))
      MAX-ACCESS  read-only
      STATUS      current
      DESCRIPTION "For 1.0 link-ref resource adapters only, the base resource adapter's connection factory name. "
      ::= { connectorConnectionPoolRuntimeEntry 35  }
   
   
   connectorConnectionPoolRuntimeResourceAdapterLinkRefName OBJECT-TYPE
      SYNTAX      DisplayString (SIZE (1..256))
      MAX-ACCESS  read-only
      STATUS      current
      DESCRIPTION "The Resource Adapter Link Reference for cases where this Connection Factory refers to an existing Resource Adapter deployment. "
      ::= { connectorConnectionPoolRuntimeEntry 40  }
   
   
   connectorConnectionPoolRuntimeLogFileName OBJECT-TYPE
      SYNTAX      DisplayString (SIZE (1..256))
      MAX-ACCESS  read-only
      STATUS      current
      DESCRIPTION "The Log File used by the Resource Adapter for this Connector connection pool. "
      ::= { connectorConnectionPoolRuntimeEntry 45  }
   
   
   connectorConnectionPoolRuntimeTransactionSupport OBJECT-TYPE
      SYNTAX      DisplayString (SIZE (1..256))
      MAX-ACCESS  read-only
      STATUS      current
      DESCRIPTION "The static transaction support level, either configured in ra.xml or in @Conector annotation, for the Resource Adapter for this Connector connection pool. "
      ::= { connectorConnectionPoolRuntimeEntry 50  }
   
   
   connectorConnectionPoolRuntimeLoggingEnabled OBJECT-TYPE
      SYNTAX      INTEGER
                  {
                     true(1),
                     false(2)
                  }
      
      MAX-ACCESS  read-only
      STATUS      current
      DESCRIPTION "Indicates whether logging is enabled for this Connector connection pool. "
      ::= { connectorConnectionPoolRuntimeEntry 60  }
   
   
   connectorConnectionPoolRuntimeMaxCapacity OBJECT-TYPE
      SYNTAX      INTEGER
      MAX-ACCESS  read-only
      STATUS      current
      DESCRIPTION "The maximum capacity configured for this Connector connection pool. "
      ::= { connectorConnectionPoolRuntimeEntry 65  }
   
   
   connectorConnectionPoolRuntimeInitialCapacity OBJECT-TYPE
      SYNTAX      INTEGER
      MAX-ACCESS  read-only
      STATUS      current
      DESCRIPTION "The initial capacity configured for this Connector connection pool. "
      ::= { connectorConnectionPoolRuntimeEntry 70  }
   
   
   connectorConnectionPoolRuntimeCapacityIncrement OBJECT-TYPE
      SYNTAX      INTEGER
      MAX-ACCESS  read-only
      STATUS      current
      DESCRIPTION "The initial capacity configured for this Connector connection pool. "
      ::= { connectorConnectionPoolRuntimeEntry 75  }
   
   
   connectorConnectionPoolRuntimeShrinkingEnabled OBJECT-TYPE
      SYNTAX      INTEGER
                  {
                     true(1),
                     false(2)
                  }
      
      MAX-ACCESS  read-only
      STATUS      current
      DESCRIPTION "Specifies whether shrinking of this Connector connection pool is enabled. "
      ::= { connectorConnectionPoolRuntimeEntry 80  }
   
   
   connectorConnectionPoolRuntimeShrinkPeriodMinutes OBJECT-TYPE
      SYNTAX      INTEGER
      MAX-ACCESS  read-only
      STATUS      current
      DESCRIPTION "The Shrink Period (in minutes) of this Connector connection pool. "
      ::= { connectorConnectionPoolRuntimeEntry 85  }
   
   
   connectorConnectionPoolRuntimeActiveConnectionsCurrentCount OBJECT-TYPE
      SYNTAX      INTEGER
      MAX-ACCESS  read-only
      STATUS      current
      DESCRIPTION "The current total active connections. "
      ::= { connectorConnectionPoolRuntimeEntry 90  }
   
   
   connectorConnectionPoolRuntimeActiveConnectionsHighCount OBJECT-TYPE
      SYNTAX      INTEGER
      MAX-ACCESS  read-only
      STATUS      current
      DESCRIPTION "The high water mark of active connections in this Connector Pool since the pool was instantiated. "
      ::= { connectorConnectionPoolRuntimeEntry 95  }
   
   
   connectorConnectionPoolRuntimeFreeConnectionsCurrentCount OBJECT-TYPE
      SYNTAX      INTEGER
      MAX-ACCESS  read-only
      STATUS      current
      DESCRIPTION "The current total free connections. "
      ::= { connectorConnectionPoolRuntimeEntry 100  }
   
   
   connectorConnectionPoolRuntimeFreeConnectionsHighCount OBJECT-TYPE
      SYNTAX      INTEGER
      MAX-ACCESS  read-only
      STATUS      current
      DESCRIPTION "The high water mark of free connections in this Connector Pool since the pool was instantiated. "
      ::= { connectorConnectionPoolRuntimeEntry 105  }
   
   
   connectorConnectionPoolRuntimeAverageActiveUsage OBJECT-TYPE
      SYNTAX      INTEGER
      MAX-ACCESS  read-only
      STATUS      current
      DESCRIPTION "The running average usage of created connections that are active in the Connector Pool since the pool was last shrunk. "
      ::= { connectorConnectionPoolRuntimeEntry 110  }
   
   
   connectorConnectionPoolRuntimeShrinkCountDownTime OBJECT-TYPE
      SYNTAX      INTEGER
      MAX-ACCESS  read-only
      STATUS      current
      DESCRIPTION "The amount of time left (in minutes) until an attempt to shrink the pool will be made. "
      ::= { connectorConnectionPoolRuntimeEntry 115  }
   
   
   connectorConnectionPoolRuntimeRecycledTotal OBJECT-TYPE
      SYNTAX      INTEGER
      MAX-ACCESS  read-only
      STATUS      current
      DESCRIPTION "The total number of Connector connections that have been recycled in this Connector Pool since the pool is instantiated. "
      ::= { connectorConnectionPoolRuntimeEntry 120  }
   
   
   connectorConnectionPoolRuntimeConnectionsCreatedTotalCount OBJECT-TYPE
      SYNTAX      INTEGER
      MAX-ACCESS  read-only
      STATUS      current
      DESCRIPTION "The total number of Connector connections created in this Connector Pool since the pool is instantiated. "
      ::= { connectorConnectionPoolRuntimeEntry 125  }
   
   
   connectorConnectionPoolRuntimeConnectionsMatchedTotalCount OBJECT-TYPE
      SYNTAX      INTEGER
      MAX-ACCESS  read-only
      STATUS      current
      DESCRIPTION "The total number of times a request for a Connector connections was satisfied via the use of an existing created connection since the pool is instantiated. "
      ::= { connectorConnectionPoolRuntimeEntry 130  }
   
   
   connectorConnectionPoolRuntimeConnectionsDestroyedTotalCount OBJECT-TYPE
      SYNTAX      INTEGER
      MAX-ACCESS  read-only
      STATUS      current
      DESCRIPTION "The total number of Connector connections destroyed in this Connector Pool since the pool is instantiated. "
      ::= { connectorConnectionPoolRuntimeEntry 135  }
   
   
   connectorConnectionPoolRuntimeConnectionsRejectedTotalCount OBJECT-TYPE
      SYNTAX      INTEGER
      MAX-ACCESS  read-only
      STATUS      current
      DESCRIPTION "The total number of rejected requests for a Connector connections in this Connector Pool since the pool is instantiated. "
      ::= { connectorConnectionPoolRuntimeEntry 140  }
   
   
   connectorConnectionPoolRuntimeConnectionLeakProfileCount OBJECT-TYPE
      SYNTAX      INTEGER
      MAX-ACCESS  read-only
      STATUS      current
      DESCRIPTION "The number of Leak connection profiles stored for this pool. "
      ::= { connectorConnectionPoolRuntimeEntry 141  }
   
   
   connectorConnectionPoolRuntimeNumberDetectedIdle OBJECT-TYPE
      SYNTAX      INTEGER
      MAX-ACCESS  read-only
      STATUS      current
      DESCRIPTION "The total number of idle connections detected in the life time of this pool. "
      ::= { connectorConnectionPoolRuntimeEntry 143  }
   
   
   connectorConnectionPoolRuntimeNumberDetectedLeaks OBJECT-TYPE
      SYNTAX      INTEGER
      MAX-ACCESS  read-only
      STATUS      current
      DESCRIPTION "The total number of leaked connections detected in the life time of this pool. "
      ::= { connectorConnectionPoolRuntimeEntry 144  }
   
   
   connectorConnectionPoolRuntimeFreePoolSizeHighWaterMark OBJECT-TYPE
      SYNTAX      Counter64
      MAX-ACCESS  read-only
      STATUS      current
      DESCRIPTION "The FreePoolSizeHighWaterMark of this Connector connection pool. "
      ::= { connectorConnectionPoolRuntimeEntry 145  }
   
   
   connectorConnectionPoolRuntimeKey OBJECT-TYPE
      SYNTAX      OCTET STRING
      MAX-ACCESS  read-only
      STATUS      current
      DESCRIPTION "The configured Key for the Connection Factory using this Connector connection pool. "
      ::= { connectorConnectionPoolRuntimeEntry 146  }
   
   
   connectorConnectionPoolRuntimeCurrentCapacity OBJECT-TYPE
      SYNTAX      Counter64
      MAX-ACCESS  read-only
      STATUS      current
      DESCRIPTION "The PoolSize of this Connector connection pool. "
      ::= { connectorConnectionPoolRuntimeEntry 147  }
   
   
   connectorConnectionPoolRuntimeMCFClassName OBJECT-TYPE
      SYNTAX      OCTET STRING
      MAX-ACCESS  read-only
      STATUS      current
      DESCRIPTION "Get the MCF class name. "
      ::= { connectorConnectionPoolRuntimeEntry 148  }
   
   
   connectorConnectionPoolRuntimeTestable OBJECT-TYPE
      SYNTAX      OCTET STRING
      MAX-ACCESS  read-only
      STATUS      current
      DESCRIPTION "This indicates whether the connection pool is testable or not. "
      ::= { connectorConnectionPoolRuntimeEntry 149  }
   
   
   connectorConnectionPoolRuntimeNumUnavailableHighCount OBJECT-TYPE
      SYNTAX      INTEGER
      MAX-ACCESS  read-only
      STATUS      current
      DESCRIPTION "Return the highest unavailable number of connections at any given time. "
      ::= { connectorConnectionPoolRuntimeEntry 150  }
   
   
   connectorConnectionPoolRuntimeConnectionsDestroyedByErrorTotalCt OBJECT-TYPE
      SYNTAX      INTEGER
      MAX-ACCESS  read-only
      STATUS      current
      DESCRIPTION "Return the number of connections that were destroyed because an error event was received. "
      ::= { connectorConnectionPoolRuntimeEntry 151  }
   
   
   connectorConnectionPoolRuntimeNumWaiters OBJECT-TYPE
      SYNTAX      Counter64
      MAX-ACCESS  read-only
      STATUS      current
      DESCRIPTION "Gets the current number of waiters. "
      ::= { connectorConnectionPoolRuntimeEntry 152  }
   
   
   connectorConnectionPoolRuntimeConnectorEisType OBJECT-TYPE
      SYNTAX      OCTET STRING
      MAX-ACCESS  read-only
      STATUS      current
      DESCRIPTION "The EIS type of this Connector connection pool. "
      ::= { connectorConnectionPoolRuntimeEntry 153  }
   
   
   connectorConnectionPoolRuntimeNumWaitersCurrentCount OBJECT-TYPE
      SYNTAX      INTEGER
      MAX-ACCESS  read-only
      STATUS      current
      DESCRIPTION "Return the number of waiters. "
      ::= { connectorConnectionPoolRuntimeEntry 154  }
   
   
   connectorConnectionPoolRuntimeMaxIdleTime OBJECT-TYPE
      SYNTAX      INTEGER
      MAX-ACCESS  read-only
      STATUS      current
      DESCRIPTION "The configured MaxIdle time for this pool "
      ::= { connectorConnectionPoolRuntimeEntry 155  }
   
   
   connectorConnectionPoolRuntimeLastShrinkTime OBJECT-TYPE
      SYNTAX      Counter64
      MAX-ACCESS  read-only
      STATUS      current
      DESCRIPTION "Return the last time that the pool was shrunk. "
      ::= { connectorConnectionPoolRuntimeEntry 156  }
   
   
   connectorConnectionPoolRuntimeState OBJECT-TYPE
      SYNTAX      OCTET STRING
      MAX-ACCESS  read-only
      STATUS      current
      DESCRIPTION "Get the state of the pool. "
      ::= { connectorConnectionPoolRuntimeEntry 157  }
   
   
   connectorConnectionPoolRuntimeCloseCount OBJECT-TYPE
      SYNTAX      Counter64
      MAX-ACCESS  read-only
      STATUS      current
      DESCRIPTION "The number of connections that were closed for the connection pool. "
      ::= { connectorConnectionPoolRuntimeEntry 159  }
   
   
   connectorConnectionPoolRuntimeManagedConnectionFactoryClassName OBJECT-TYPE
      SYNTAX      OCTET STRING
      MAX-ACCESS  read-only
      STATUS      current
      DESCRIPTION "The ManagedConnectionFactoryName of this Connector connection pool. "
      ::= { connectorConnectionPoolRuntimeEntry 160  }
   
   
   connectorConnectionPoolRuntimeHighestNumWaiters OBJECT-TYPE
      SYNTAX      Counter64
      MAX-ACCESS  read-only
      STATUS      current
      DESCRIPTION "Gets the highest number of waiters. "
      ::= { connectorConnectionPoolRuntimeEntry 161  }
   
   
   connectorConnectionPoolRuntimePoolSizeHighWaterMark OBJECT-TYPE
      SYNTAX      Counter64
      MAX-ACCESS  read-only
      STATUS      current
      DESCRIPTION "The PoolSizeHighWaterMark of this Connector connection pool. "
      ::= { connectorConnectionPoolRuntimeEntry 162  }
   
   
   connectorConnectionPoolRuntimeConnectionFactoryClassName OBJECT-TYPE
      SYNTAX      OCTET STRING
      MAX-ACCESS  read-only
      STATUS      current
      DESCRIPTION "The ConnectionFactoryName of this Connector connection pool. "
      ::= { connectorConnectionPoolRuntimeEntry 163  }
   
   
   connectorConnectionPoolRuntimeEISResourceId OBJECT-TYPE
      SYNTAX      OCTET STRING
      MAX-ACCESS  read-only
      STATUS      current
      DESCRIPTION "The EISResourceId of this Connector connection pool. "
      ::= { connectorConnectionPoolRuntimeEntry 164  }
   
   
   connectorConnectionPoolRuntimeFreePoolSizeLowWaterMark OBJECT-TYPE
      SYNTAX      Counter64
      MAX-ACCESS  read-only
      STATUS      current
      DESCRIPTION "The FreePoolSizeLowWaterMark of this Connector connection pool. "
      ::= { connectorConnectionPoolRuntimeEntry 165  }
   
   
   connectorConnectionPoolRuntimePoolSizeLowWaterMark OBJECT-TYPE
      SYNTAX      Counter64
      MAX-ACCESS  read-only
      STATUS      current
      DESCRIPTION "The PoolSizeLowWaterMark of this Connector connection pool. "
      ::= { connectorConnectionPoolRuntimeEntry 166  }
   
   
   connectorConnectionPoolRuntimeConsDestroyedByShrinkingTotalCount OBJECT-TYPE
      SYNTAX      INTEGER
      MAX-ACCESS  read-only
      STATUS      current
      DESCRIPTION "Return the number of connections that were destroyed as a result of shrinking. "
      ::= { connectorConnectionPoolRuntimeEntry 167  }
   
   
   connectorConnectionPoolRuntimeNumUnavailableCurrentCount OBJECT-TYPE
      SYNTAX      INTEGER
      MAX-ACCESS  read-only
      STATUS      current
      DESCRIPTION "Return the number of unavailable connections. "
      ::= { connectorConnectionPoolRuntimeEntry 168  }
   
   
   connectorConnectionPoolRuntimeProxyOn OBJECT-TYPE
      SYNTAX      OCTET STRING
      MAX-ACCESS  read-only
      STATUS      current
      DESCRIPTION "Return a flag indicating if the proxy is on. Returns true if it is. "
      ::= { connectorConnectionPoolRuntimeEntry 169  }
   
   
   connectorConnectionPoolRuntimeConnectionIdleProfileCount OBJECT-TYPE
      SYNTAX      INTEGER
      MAX-ACCESS  read-only
      STATUS      current
      DESCRIPTION "The number of Idle connection profiles stored for this pool. "
      ::= { connectorConnectionPoolRuntimeEntry 170  }
   
   
   connectorConnectionPoolRuntimeConnectionProfilingEnabled OBJECT-TYPE
      SYNTAX      OCTET STRING
      MAX-ACCESS  read-only
      STATUS      current
      DESCRIPTION "Indicates whether connection profiling is enabled for this pool. "
      ::= { connectorConnectionPoolRuntimeEntry 171  }
   
   
   connectorConnectionPoolRuntimeRuntimeTransactionSupport OBJECT-TYPE
      SYNTAX      OCTET STRING
      MAX-ACCESS  read-only
      STATUS      current
      DESCRIPTION "The real transaction support level in use at runtime. "
      ::= { connectorConnectionPoolRuntimeEntry 172  }
   
   
   connectorConnectionPoolRuntimeHealthState OBJECT-TYPE
      SYNTAX      OCTET STRING
      MAX-ACCESS  read-only
      STATUS      current
      DESCRIPTION "The HealthState mbean for the application.  "
      ::= { connectorConnectionPoolRuntimeEntry 173  }
   
   
   connectorConnectionPoolRuntimeLogFileStreamOpened OBJECT-TYPE
      SYNTAX      OCTET STRING
      MAX-ACCESS  read-only
      STATUS      current
      DESCRIPTION "Gets the opened state of the log file stream represented by this instance. "
      ::= { connectorConnectionPoolRuntimeEntry 174  }
   
   
   connectorServiceRuntimeTable OBJECT-TYPE
      SYNTAX      SEQUENCE OF ConnectorServiceRuntimeEntry
      MAX-ACCESS  not-accessible
      STATUS      current
      DESCRIPTION "This interface defines the runtime information that can be accessed at a connector service level. Runtime information can be accessed at a per resource adapter level or at an overall level. "
      ::= { wls 456  }
      
   
   connectorServiceRuntimeEntry OBJECT-TYPE
      SYNTAX      ConnectorServiceRuntimeEntry
      MAX-ACCESS  not-accessible
      STATUS      current
      DESCRIPTION "Entry of connectorServiceRuntimeTable"
      INDEX { connectorServiceRuntimeIndex}
      ::= { connectorServiceRuntimeTable 1 }
      
   ConnectorServiceRuntimeEntry ::=
      SEQUENCE
      {
         connectorServiceRuntimeIndex DisplayString,
         connectorServiceRuntimeObjectName DisplayString,
         connectorServiceRuntimeType DisplayString,
         connectorServiceRuntimeName DisplayString,
         connectorServiceRuntimeParent DisplayString,
         connectorServiceRuntimeConnectionPoolCurrentCount INTEGER,
         connectorServiceRuntimeConnectionPoolsTotalCount INTEGER,
         connectorServiceRuntimeRACount INTEGER,
         connectorServiceRuntimeActiveRACount INTEGER
      }
      
   
   connectorServiceRuntimeIndex OBJECT-TYPE
      SYNTAX      DisplayString (SIZE (1..16))
      MAX-ACCESS  read-only
      STATUS      current
      DESCRIPTION "Unique value directed from ObjectName which is used as table index"
      ::= { connectorServiceRuntimeEntry 1  }
   
   
   connectorServiceRuntimeObjectName OBJECT-TYPE
      SYNTAX      DisplayString (SIZE (1..256))
      MAX-ACCESS  read-only
      STATUS      current
      DESCRIPTION "JMX-standard MBean name"
      ::= { connectorServiceRuntimeEntry 5  }
   
   
   connectorServiceRuntimeType OBJECT-TYPE
      SYNTAX      DisplayString (SIZE (1..64))
      MAX-ACCESS  read-only
      STATUS      current
      DESCRIPTION "Returns the type of the MBean. "
      ::= { connectorServiceRuntimeEntry 10  }
   
   
   connectorServiceRuntimeName OBJECT-TYPE
      SYNTAX      DisplayString (SIZE (1..64))
      MAX-ACCESS  read-only
      STATUS      current
      DESCRIPTION "The name of this configuration. WebLogic Server uses an MBean to implement and persist the configuration. "
      ::= { connectorServiceRuntimeEntry 15  }
   
   
   connectorServiceRuntimeParent OBJECT-TYPE
      SYNTAX      DisplayString (SIZE (1..256))
      MAX-ACCESS  read-only
      STATUS      current
      DESCRIPTION "BEA-proprietary Parent object's identification, with syntax
      <type>:<name>"
      ::= { connectorServiceRuntimeEntry 20  }
   
   
   connectorServiceRuntimeConnectionPoolCurrentCount OBJECT-TYPE
      SYNTAX      INTEGER
      MAX-ACCESS  read-only
      STATUS      current
      DESCRIPTION "Returns the number of connection pools in all active RAs. "
      ::= { connectorServiceRuntimeEntry 25  }
   
   
   connectorServiceRuntimeConnectionPoolsTotalCount OBJECT-TYPE
      SYNTAX      INTEGER
      MAX-ACCESS  read-only
      STATUS      current
      DESCRIPTION "Returns the number of resource adapter connection pools that have been created since server startup. This includes re-deployments.  Returns the total number of deployed connection pools instantiated since server startup. "
      ::= { connectorServiceRuntimeEntry 30  }
   
   
   connectorServiceRuntimeRACount OBJECT-TYPE
      SYNTAX      INTEGER
      MAX-ACCESS  read-only
      STATUS      current
      DESCRIPTION "Returns the number of resource adapters that have been deployed in the server. This count includes active RAs and Non-active RAs ( in the case of versioned RAs that are being replaced by a new version ) "
      ::= { connectorServiceRuntimeEntry 31  }
   
   
   connectorServiceRuntimeActiveRACount OBJECT-TYPE
      SYNTAX      INTEGER
      MAX-ACCESS  read-only
      STATUS      current
      DESCRIPTION "Returns the number of resource adapters that are active. "
      ::= { connectorServiceRuntimeEntry 32  }
   
   
   connectorComponentRuntimeTable OBJECT-TYPE
      SYNTAX      SEQUENCE OF ConnectorComponentRuntimeEntry
      MAX-ACCESS  not-accessible
      STATUS      current
      DESCRIPTION "Generates notifications about the deployment state of resource adapters. (Each resource adapter is represented by an instance of {@link weblogic.management.configuration.ConnectorComponentMBean}.)  In 2-phase deployment, if a resource adapter's state is PREPARED then it has achieved the first phase of deployment (everything is set up and all that remains is to enable a reference to the adapter). When the resource adapter is in an ACTIVATED state, it has achieved the second phase of deployment, in which applications can obtain a reference to the adapter.  A server instance creates an instance of this interface when it creates an instance of weblogic.management.configuration.ConnectorComponentMBean. "
      ::= { wls 457  }
      
   
   connectorComponentRuntimeEntry OBJECT-TYPE
      SYNTAX      ConnectorComponentRuntimeEntry
      MAX-ACCESS  not-accessible
      STATUS      current
      DESCRIPTION "Entry of connectorComponentRuntimeTable"
      INDEX { connectorComponentRuntimeIndex}
      ::= { connectorComponentRuntimeTable 1 }
      
   ConnectorComponentRuntimeEntry ::=
      SEQUENCE
      {
         connectorComponentRuntimeIndex DisplayString,
         connectorComponentRuntimeObjectName DisplayString,
         connectorComponentRuntimeType DisplayString,
         connectorComponentRuntimeName DisplayString,
         connectorComponentRuntimeParent DisplayString,
         connectorComponentRuntimeConnectionPoolCount INTEGER,
         connectorComponentRuntimeInboundConnectionsCount INTEGER,
         connectorComponentRuntimeEISResourceId DisplayString,
         connectorComponentRuntimeVersionId DisplayString,
         connectorComponentRuntimeActiveVersionId DisplayString,
         connectorComponentRuntimeVersioned INTEGER,
         connectorComponentRuntimeActiveVersion INTEGER,
         connectorComponentRuntimeJndiName DisplayString,
         connectorComponentRuntimeState DisplayString,
         connectorComponentRuntimeSuspendedState INTEGER,
         connectorComponentRuntimeDescription DisplayString,
         connectorComponentRuntimeEISType DisplayString,
         connectorComponentRuntimeSpecVersion DisplayString,
         connectorComponentRuntimeVendorName DisplayString,
         connectorComponentRuntimeVersion DisplayString,
         connectorComponentRuntimeComponentName OCTET STRING,
         connectorComponentRuntimeModuleId OCTET STRING,
         connectorComponentRuntimeConfiguration OCTET STRING,
         connectorComponentRuntimeSchema OCTET STRING,
         connectorComponentRuntimeLinkref OCTET STRING,
         connectorComponentRuntimeDeploymentState INTEGER,
         connectorComponentRuntimeConfigurationVersion OCTET STRING,
         connectorComponentRuntimeDescriptions OCTET STRING,
         connectorComponentRuntimeHealthState OCTET STRING
      }
      
   
   connectorComponentRuntimeIndex OBJECT-TYPE
      SYNTAX      DisplayString (SIZE (1..16))
      MAX-ACCESS  read-only
      STATUS      current
      DESCRIPTION "Unique value directed from ObjectName which is used as table index"
      ::= { connectorComponentRuntimeEntry 1  }
   
   
   connectorComponentRuntimeObjectName OBJECT-TYPE
      SYNTAX      DisplayString (SIZE (1..256))
      MAX-ACCESS  read-only
      STATUS      current
      DESCRIPTION "JMX-standard MBean name"
      ::= { connectorComponentRuntimeEntry 5  }
   
   
   connectorComponentRuntimeType OBJECT-TYPE
      SYNTAX      DisplayString (SIZE (1..64))
      MAX-ACCESS  read-only
      STATUS      current
      DESCRIPTION "Returns the type of the MBean. "
      ::= { connectorComponentRuntimeEntry 10  }
   
   
   connectorComponentRuntimeName OBJECT-TYPE
      SYNTAX      DisplayString (SIZE (1..64))
      MAX-ACCESS  read-only
      STATUS      current
      DESCRIPTION "The name of this configuration. WebLogic Server uses an MBean to implement and persist the configuration. "
      ::= { connectorComponentRuntimeEntry 15  }
   
   
   connectorComponentRuntimeParent OBJECT-TYPE
      SYNTAX      DisplayString (SIZE (1..256))
      MAX-ACCESS  read-only
      STATUS      current
      DESCRIPTION "BEA-proprietary Parent object's identification, with syntax
      <type>:<name>"
      ::= { connectorComponentRuntimeEntry 20  }
   
   
   connectorComponentRuntimeConnectionPoolCount OBJECT-TYPE
      SYNTAX      INTEGER
      MAX-ACCESS  read-only
      STATUS      current
      DESCRIPTION "The number of connection pools. "
      ::= { connectorComponentRuntimeEntry 25  }
   
   
   connectorComponentRuntimeInboundConnectionsCount OBJECT-TYPE
      SYNTAX      INTEGER
      MAX-ACCESS  read-only
      STATUS      current
      DESCRIPTION "The number of inbound connections for the resource adapter. "
      ::= { connectorComponentRuntimeEntry 30  }
   
   
   connectorComponentRuntimeEISResourceId OBJECT-TYPE
      SYNTAX      DisplayString (SIZE (1..64))
      MAX-ACCESS  read-only
      STATUS      current
      DESCRIPTION "Returns the EISResourceId for the component. "
      ::= { connectorComponentRuntimeEntry 35  }
   
   
   connectorComponentRuntimeVersionId OBJECT-TYPE
      SYNTAX      DisplayString (SIZE (1..64))
      MAX-ACCESS  read-only
      STATUS      current
      DESCRIPTION "Get the version Id. "
      ::= { connectorComponentRuntimeEntry 40  }
   
   
   connectorComponentRuntimeActiveVersionId OBJECT-TYPE
      SYNTAX      DisplayString (SIZE (1..64))
      MAX-ACCESS  read-only
      STATUS      current
      DESCRIPTION "Get the active version Id. "
      ::= { connectorComponentRuntimeEntry 45  }
   
   
   connectorComponentRuntimeVersioned OBJECT-TYPE
      SYNTAX      INTEGER
                  {
                     true(1),
                     false(2)
                  }
      
      MAX-ACCESS  read-only
      STATUS      current
      DESCRIPTION "Check if the resource adapter is versioned. Returns true if it is. "
      ::= { connectorComponentRuntimeEntry 50  }
   
   
   connectorComponentRuntimeActiveVersion OBJECT-TYPE
      SYNTAX      INTEGER
      MAX-ACCESS  read-only
      STATUS      current
      DESCRIPTION "Return true if this version is the active version. Returns true if this resource adapter is not versioned. "
      ::= { connectorComponentRuntimeEntry 55  }
   
   
   connectorComponentRuntimeJndiName OBJECT-TYPE
      SYNTAX      DisplayString (SIZE (1..64))
      MAX-ACCESS  read-only
      STATUS      current
      DESCRIPTION "Get the Jndi name of the resource adapter. "
      ::= { connectorComponentRuntimeEntry 60  }
   
   
   connectorComponentRuntimeState OBJECT-TYPE
      SYNTAX      DisplayString (SIZE (1..64))
      MAX-ACCESS  read-only
      STATUS      current
      DESCRIPTION "Get the state of the resource adapter. "
      ::= { connectorComponentRuntimeEntry 65  }
   
   
   connectorComponentRuntimeSuspendedState OBJECT-TYPE
      SYNTAX      INTEGER
      MAX-ACCESS  read-only
      STATUS      current
      DESCRIPTION "Gets the suspended state information of the resource adapter.  If getState() returns SUSPENDED then getSuspendedState() returns an integer describing which functions of the resource adapter are suspended: one or more of INBOUND, OUTBOUND or WORK (or ALL) or 0 for nothing suspended "
      ::= { connectorComponentRuntimeEntry 70  }
   
   
   connectorComponentRuntimeDescription OBJECT-TYPE
      SYNTAX      DisplayString (SIZE (1..64))
      MAX-ACCESS  read-only
      STATUS      current
      DESCRIPTION "Get the Description for the resource adapter. "
      ::= { connectorComponentRuntimeEntry 75  }
   
   
   connectorComponentRuntimeEISType OBJECT-TYPE
      SYNTAX      DisplayString (SIZE (1..64))
      MAX-ACCESS  read-only
      STATUS      current
      DESCRIPTION "Get the EIS type. "
      ::= { connectorComponentRuntimeEntry 80  }
   
   
   connectorComponentRuntimeSpecVersion OBJECT-TYPE
      SYNTAX      DisplayString (SIZE (1..64))
      MAX-ACCESS  read-only
      STATUS      current
      DESCRIPTION "Get the spec version. "
      ::= { connectorComponentRuntimeEntry 85  }
   
   
   connectorComponentRuntimeVendorName OBJECT-TYPE
      SYNTAX      DisplayString (SIZE (1..64))
      MAX-ACCESS  read-only
      STATUS      current
      DESCRIPTION "Get the vendor name. "
      ::= { connectorComponentRuntimeEntry 90  }
   
   
   connectorComponentRuntimeVersion OBJECT-TYPE
      SYNTAX      DisplayString (SIZE (1..32))
      MAX-ACCESS  read-only
      STATUS      current
      DESCRIPTION "Get the version. "
      ::= { connectorComponentRuntimeEntry 95  }
   
   
   connectorComponentRuntimeComponentName OBJECT-TYPE
      SYNTAX      OCTET STRING
      MAX-ACCESS  read-only
      STATUS      current
      DESCRIPTION "Get the name of the connector component. "
      ::= { connectorComponentRuntimeEntry 96  }
   
   
   connectorComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { connectorComponentRuntimeEntry 97  }
   
   
   connectorComponentRuntimeConfiguration OBJECT-TYPE
      SYNTAX      OCTET STRING
      MAX-ACCESS  read-only
      STATUS      current
      DESCRIPTION "Return the xml string representing the RA configuration. The xml corresponding to the latest schema is returned. The current supported version is '1.0' "
      ::= { connectorComponentRuntimeEntry 98  }
   
   
   connectorComponentRuntimeSchema OBJECT-TYPE
      SYNTAX      OCTET STRING
      MAX-ACCESS  read-only
      STATUS      current
      DESCRIPTION "Get the latest schema for RA configuration. "
      ::= { connectorComponentRuntimeEntry 99  }
   
   
   connectorComponentRuntimeLinkref OBJECT-TYPE
      SYNTAX      OCTET STRING
      MAX-ACCESS  read-only
      STATUS      current
      DESCRIPTION "Get the linkref. "
      ::= { connectorComponentRuntimeEntry 100  }
   
   
   connectorComponentRuntimeDeploymentState OBJECT-TYPE
      SYNTAX      INTEGER
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { connectorComponentRuntimeEntry 101  }
   
   
   connectorComponentRuntimeConfigurationVersion OBJECT-TYPE
      SYNTAX      OCTET STRING
      MAX-ACCESS  read-only
      STATUS      current
      DESCRIPTION "Return the latest configuration version. "
      ::= { connectorComponentRuntimeEntry 102  }
   
   
   connectorComponentRuntimeDescriptions OBJECT-TYPE
      SYNTAX      OCTET STRING
      MAX-ACCESS  read-only
      STATUS      current
      DESCRIPTION "Get the Descriptions for the resource adapter. "
      ::= { connectorComponentRuntimeEntry 103  }
   
   
   connectorComponentRuntimeHealthState OBJECT-TYPE
      SYNTAX      OCTET STRING
      MAX-ACCESS  read-only
      STATUS      current
      DESCRIPTION "The HealthState mbean for the application.  "
      ::= { connectorComponentRuntimeEntry 104  }
   
   
   connectorInboundRuntimeTable OBJECT-TYPE
      SYNTAX      SEQUENCE OF ConnectorInboundRuntimeEntry
      MAX-ACCESS  not-accessible
      STATUS      current
      DESCRIPTION "This class is used for monitoring inbound connections of resource adapters. "
      ::= { wls 459  }
      
   
   connectorInboundRuntimeEntry OBJECT-TYPE
      SYNTAX      ConnectorInboundRuntimeEntry
      MAX-ACCESS  not-accessible
      STATUS      current
      DESCRIPTION "Entry of connectorInboundRuntimeTable"
      INDEX { connectorInboundRuntimeIndex}
      ::= { connectorInboundRuntimeTable 1 }
      
   ConnectorInboundRuntimeEntry ::=
      SEQUENCE
      {
         connectorInboundRuntimeIndex DisplayString,
         connectorInboundRuntimeObjectName DisplayString,
         connectorInboundRuntimeType DisplayString,
         connectorInboundRuntimeName DisplayString,
         connectorInboundRuntimeParent DisplayString,
         connectorInboundRuntimeMsgListenerType DisplayString,
         connectorInboundRuntimeActivationSpecClass DisplayString,
         connectorInboundRuntimeState DisplayString
      }
      
   
   connectorInboundRuntimeIndex OBJECT-TYPE
      SYNTAX      DisplayString (SIZE (1..16))
      MAX-ACCESS  read-only
      STATUS      current
      DESCRIPTION "Unique value directed from ObjectName which is used as table index"
      ::= { connectorInboundRuntimeEntry 1  }
   
   
   connectorInboundRuntimeObjectName OBJECT-TYPE
      SYNTAX      DisplayString (SIZE (1..256))
      MAX-ACCESS  read-only
      STATUS      current
      DESCRIPTION "JMX-standard MBean name"
      ::= { connectorInboundRuntimeEntry 5  }
   
   
   connectorInboundRuntimeType OBJECT-TYPE
      SYNTAX      DisplayString (SIZE (1..64))
      MAX-ACCESS  read-only
      STATUS      current
      DESCRIPTION "Returns the type of the MBean. "
      ::= { connectorInboundRuntimeEntry 10  }
   
   
   connectorInboundRuntimeName OBJECT-TYPE
      SYNTAX      DisplayString (SIZE (1..64))
      MAX-ACCESS  read-only
      STATUS      current
      DESCRIPTION "The name of this configuration. WebLogic Server uses an MBean to implement and persist the configuration. "
      ::= { connectorInboundRuntimeEntry 15  }
   
   
   connectorInboundRuntimeParent OBJECT-TYPE
      SYNTAX      DisplayString (SIZE (1..256))
      MAX-ACCESS  read-only
      STATUS      current
      DESCRIPTION "BEA-proprietary Parent object's identification, with syntax
      <type>:<name>"
      ::= { connectorInboundRuntimeEntry 20  }
   
   
   connectorInboundRuntimeMsgListenerType OBJECT-TYPE
      SYNTAX      DisplayString (SIZE (1..64))
      MAX-ACCESS  read-only
      STATUS      current
      DESCRIPTION "The message listener type. "
      ::= { connectorInboundRuntimeEntry 25  }
   
   
   connectorInboundRuntimeActivationSpecClass OBJECT-TYPE
      SYNTAX      DisplayString (SIZE (1..64))
      MAX-ACCESS  read-only
      STATUS      current
      DESCRIPTION "The activation spec class. "
      ::= { connectorInboundRuntimeEntry 30  }
   
   
   connectorInboundRuntimeState OBJECT-TYPE
      SYNTAX      DisplayString (SIZE (1..64))
      MAX-ACCESS  read-only
      STATUS      current
      DESCRIPTION "Return the state of the Inbound connection. The values that are returned are : 'Running' and 'Suspended'. "
      ::= { connectorInboundRuntimeEntry 35  }
   
   
   jMSDurableSubscriberRuntimeTable OBJECT-TYPE
      SYNTAX      SEQUENCE OF JMSDurableSubscriberRuntimeEntry
      MAX-ACCESS  not-accessible
      STATUS      current
      DESCRIPTION "This class is used for monitoring a WebLogic JMS durable subscriber. "
      ::= { wls 460  }
      
   
   jMSDurableSubscriberRuntimeEntry OBJECT-TYPE
      SYNTAX      JMSDurableSubscriberRuntimeEntry
      MAX-ACCESS  not-accessible
      STATUS      current
      DESCRIPTION "Entry of jMSDurableSubscriberRuntimeTable"
      INDEX { jMSDurableSubscriberRuntimeIndex}
      ::= { jMSDurableSubscriberRuntimeTable 1 }
      
   JMSDurableSubscriberRuntimeEntry ::=
      SEQUENCE
      {
         jMSDurableSubscriberRuntimeIndex DisplayString,
         jMSDurableSubscriberRuntimeObjectName DisplayString,
         jMSDurableSubscriberRuntimeType DisplayString,
         jMSDurableSubscriberRuntimeName DisplayString,
         jMSDurableSubscriberRuntimeParent DisplayString,
         jMSDurableSubscriberRuntimeClientID DisplayString,
         jMSDurableSubscriberRuntimeSubscriptionName DisplayString,
         jMSDurableSubscriberRuntimeSelector DisplayString,
         jMSDurableSubscriberRuntimeNoLocal INTEGER,
         jMSDurableSubscriberRuntimeActive INTEGER,
         jMSDurableSubscriberRuntimeMessagesPendingCount Counter64,
         jMSDurableSubscriberRuntimeMessagesCurrentCount Counter64,
         jMSDurableSubscriberRuntimeBytesPendingCount Counter64,
         jMSDurableSubscriberRuntimeBytesCurrentCount Counter64,
         jMSDurableSubscriberRuntimeMessagesReceivedCount Counter64,
         jMSDurableSubscriberRuntimeMessagesHighCount Counter64,
         jMSDurableSubscriberRuntimeMessagesMovedCurrentCount Counter64,
         jMSDurableSubscriberRuntimeMessagesDeletedCurrentCount Counter64,
         jMSDurableSubscriberRuntimeSubscribersHighCount INTEGER,
         jMSDurableSubscriberRuntimeLastMessagesReceivedTime Counter64,
         jMSDurableSubscriberRuntimeClientIDPolicy OCTET STRING,
         jMSDurableSubscriberRuntimeSubscribersCurrentCount INTEGER,
         jMSDurableSubscriberRuntimeSubscribersTotalCount INTEGER,
         jMSDurableSubscriberRuntimeSubscriptionSharingPolicy OCTET STRING,
         jMSDurableSubscriberRuntimeSubscriptionLimitDeletedCount Counter64
      }
      
   
   jMSDurableSubscriberRuntimeIndex OBJECT-TYPE
      SYNTAX      DisplayString (SIZE (1..16))
      MAX-ACCESS  read-only
      STATUS      current
      DESCRIPTION "Unique value directed from ObjectName which is used as table index"
      ::= { jMSDurableSubscriberRuntimeEntry 1  }
   
   
   jMSDurableSubscriberRuntimeObjectName OBJECT-TYPE
      SYNTAX      DisplayString (SIZE (1..256))
      MAX-ACCESS  read-only
      STATUS      current
      DESCRIPTION "JMX-standard MBean name"
      ::= { jMSDurableSubscriberRuntimeEntry 5  }
   
   
   jMSDurableSubscriberRuntimeType OBJECT-TYPE
      SYNTAX      DisplayString (SIZE (1..64))
      MAX-ACCESS  read-only
      STATUS      current
      DESCRIPTION "Returns the type of the MBean. "
      ::= { jMSDurableSubscriberRuntimeEntry 10  }
   
   
   jMSDurableSubscriberRuntimeName OBJECT-TYPE
      SYNTAX      DisplayString (SIZE (1..64))
      MAX-ACCESS  read-only
      STATUS      current
      DESCRIPTION "The name of this configuration. WebLogic Server uses an MBean to implement and persist the configuration. "
      ::= { jMSDurableSubscriberRuntimeEntry 15  }
   
   
   jMSDurableSubscriberRuntimeParent OBJECT-TYPE
      SYNTAX      DisplayString (SIZE (1..256))
      MAX-ACCESS  read-only
      STATUS      current
      DESCRIPTION "BEA-proprietary Parent object's identification, with syntax
      <type>:<name>"
      ::= { jMSDurableSubscriberRuntimeEntry 20  }
   
   
   jMSDurableSubscriberRuntimeClientID OBJECT-TYPE
      SYNTAX      DisplayString (SIZE (1..256))
      MAX-ACCESS  read-only
      STATUS      current
      DESCRIPTION "A unique client identifier for this durable subscriber.  Note: The client ID is not necessarily equivalent to the WebLogic Server username; that is, a name used to authenticate a user in the WebLogic security realm. You can set the client ID to the WebLogic Server username if it is appropriate for your JMS application. "
      ::= { jMSDurableSubscriberRuntimeEntry 25  }
   
   
   jMSDurableSubscriberRuntimeSubscriptionName OBJECT-TYPE
      SYNTAX      DisplayString (SIZE (1..256))
      MAX-ACCESS  read-only
      STATUS      current
      DESCRIPTION "The subscription name for this durable subscriber. This name must be unique for each client ID.  Valid durable subscription names cannot include the following characters: comma ',', equals '=', colon ':', asterisk '*', percent '%', or question mark'?'. "
      ::= { jMSDurableSubscriberRuntimeEntry 30  }
   
   
   jMSDurableSubscriberRuntimeSelector OBJECT-TYPE
      SYNTAX      DisplayString (SIZE (1..256))
      MAX-ACCESS  read-only
      STATUS      current
      DESCRIPTION "The message selector defined for this durable subscriber. "
      ::= { jMSDurableSubscriberRuntimeEntry 35  }
   
   
   jMSDurableSubscriberRuntimeNoLocal OBJECT-TYPE
      SYNTAX      INTEGER
                  {
                     true(1),
                     false(2)
                  }
      
      MAX-ACCESS  read-only
      STATUS      current
      DESCRIPTION "Specifies whether this durable subscriber receives local messages that it has published.  To prevent this, set the noLocal parameter to true. "
      ::= { jMSDurableSubscriberRuntimeEntry 40  }
   
   
   jMSDurableSubscriberRuntimeActive OBJECT-TYPE
      SYNTAX      INTEGER
                  {
                     true(1),
                     false(2)
                  }
      
      MAX-ACCESS  read-only
      STATUS      current
      DESCRIPTION "Indicates whether this subscription is being used by a durable subscriber. "
      ::= { jMSDurableSubscriberRuntimeEntry 45  }
   
   
   jMSDurableSubscriberRuntimeMessagesPendingCount OBJECT-TYPE
      SYNTAX      Counter64
      MAX-ACCESS  read-only
      STATUS      current
      DESCRIPTION "The number of messages pending (uncommitted and unacknowledged) by this durable subscriber. "
      ::= { jMSDurableSubscriberRuntimeEntry 50  }
   
   
   jMSDurableSubscriberRuntimeMessagesCurrentCount OBJECT-TYPE
      SYNTAX      Counter64
      MAX-ACCESS  read-only
      STATUS      current
      DESCRIPTION "The number of messages still available by this durable subscriber. "
      ::= { jMSDurableSubscriberRuntimeEntry 55  }
   
   
   jMSDurableSubscriberRuntimeBytesPendingCount OBJECT-TYPE
      SYNTAX      Counter64
      MAX-ACCESS  read-only
      STATUS      current
      DESCRIPTION "The number of bytes pending by this durable subscriber. "
      ::= { jMSDurableSubscriberRuntimeEntry 60  }
   
   
   jMSDurableSubscriberRuntimeBytesCurrentCount OBJECT-TYPE
      SYNTAX      Counter64
      MAX-ACCESS  read-only
      STATUS      current
      DESCRIPTION "The number of bytes received by this durable subscriber. "
      ::= { jMSDurableSubscriberRuntimeEntry 65  }
   
   
   jMSDurableSubscriberRuntimeMessagesReceivedCount OBJECT-TYPE
      SYNTAX      Counter64
      MAX-ACCESS  read-only
      STATUS      current
      DESCRIPTION "The number of messages received by the durable subscriber since that reset. "
      ::= { jMSDurableSubscriberRuntimeEntry 66  }
   
   
   jMSDurableSubscriberRuntimeMessagesHighCount OBJECT-TYPE
      SYNTAX      Counter64
      MAX-ACCESS  read-only
      STATUS      current
      DESCRIPTION "The peak number of messages for the durable subscriber since the last reset. "
      ::= { jMSDurableSubscriberRuntimeEntry 67  }
   
   
   jMSDurableSubscriberRuntimeMessagesMovedCurrentCount OBJECT-TYPE
      SYNTAX      Counter64
      MAX-ACCESS  read-only
      STATUS      current
      DESCRIPTION "Returns the number of messages that have been moved from the destination. "
      ::= { jMSDurableSubscriberRuntimeEntry 68  }
   
   
   jMSDurableSubscriberRuntimeMessagesDeletedCurrentCount OBJECT-TYPE
      SYNTAX      Counter64
      MAX-ACCESS  read-only
      STATUS      current
      DESCRIPTION "Returns the number of messages that have been deleted from the destination. "
      ::= { jMSDurableSubscriberRuntimeEntry 69  }
   
   
   jMSDurableSubscriberRuntimeSubscribersHighCount OBJECT-TYPE
      SYNTAX      INTEGER
      MAX-ACCESS  read-only
      STATUS      current
      DESCRIPTION "The highest number of subscribers that have shared this subscription at the same time since the creation or the last reboot of the subscription, which ever is later. "
      ::= { jMSDurableSubscriberRuntimeEntry 70  }
   
   
   jMSDurableSubscriberRuntimeLastMessagesReceivedTime OBJECT-TYPE
      SYNTAX      Counter64
      MAX-ACCESS  read-only
      STATUS      current
      DESCRIPTION " The time when the last time a subscriber received a message from the subscription. The returned value is a standard java absolute time, which is measured in milliseconds since midnight, January 1, 1970 UTC   This returns the JMS durable subscription boot time if there were no messages that were successfully delivered to any subscriber on this subscription since the subscription was booted. We define the boot time of a durable subscription to be the time the subscription is originally created or recovered during a server reboot or jms migration, which ever is latest. "
      ::= { jMSDurableSubscriberRuntimeEntry 71  }
   
   
   jMSDurableSubscriberRuntimeClientIDPolicy OBJECT-TYPE
      SYNTAX      OCTET STRING
      MAX-ACCESS  read-only
      STATUS      current
      DESCRIPTION " The policy for the client identifier for this durable subscriber.  Note: The client ID policy is either Restricted or Unrestricted.  "
      ::= { jMSDurableSubscriberRuntimeEntry 72  }
   
   
   jMSDurableSubscriberRuntimeSubscribersCurrentCount OBJECT-TYPE
      SYNTAX      INTEGER
      MAX-ACCESS  read-only
      STATUS      current
      DESCRIPTION "The number of subscribers that currently share this subscription. "
      ::= { jMSDurableSubscriberRuntimeEntry 73  }
   
   
   jMSDurableSubscriberRuntimeSubscribersTotalCount OBJECT-TYPE
      SYNTAX      INTEGER
      MAX-ACCESS  read-only
      STATUS      current
      DESCRIPTION "The total number of subscribers that have accessed this subscription since the creation or the last reboot of the subscription, whichever is later. "
      ::= { jMSDurableSubscriberRuntimeEntry 74  }
   
   
   jMSDurableSubscriberRuntimeSubscriptionSharingPolicy OBJECT-TYPE
      SYNTAX      OCTET STRING
      MAX-ACCESS  read-only
      STATUS      current
      DESCRIPTION "The SubscriptionSharingPolicy on this subscriber. "
      ::= { jMSDurableSubscriberRuntimeEntry 75  }
   
   
   jMSDurableSubscriberRuntimeSubscriptionLimitDeletedCount OBJECT-TYPE
      SYNTAX      Counter64
      MAX-ACCESS  read-only
      STATUS      current
      DESCRIPTION "The number of messages deleted because of a subscription limit. "
      ::= { jMSDurableSubscriberRuntimeEntry 76  }
   
   
   safAgentRuntimeTable OBJECT-TYPE
      SYNTAX      SEQUENCE OF SafAgentRuntimeEntry
      MAX-ACCESS  not-accessible
      STATUS      current
      DESCRIPTION "This class is used for monitoring a WebLogic SAF agent. "
      ::= { wls 470  }
      
   
   safAgentRuntimeEntry OBJECT-TYPE
      SYNTAX      SafAgentRuntimeEntry
      MAX-ACCESS  not-accessible
      STATUS      current
      DESCRIPTION "Entry of SafAgentRuntimeTable"
      INDEX { safAgentRuntimeIndex}
      ::= { safAgentRuntimeTable 1 }
      
   SafAgentRuntimeEntry ::=
      SEQUENCE
      {
         safAgentRuntimeIndex DisplayString,
         safAgentRuntimeObjectName DisplayString,
         safAgentRuntimeType  DisplayString,
         safAgentRuntimeName  DisplayString,
         safAgentRuntimeParent DisplayString,
         safAgentRuntimeRemoteEndpointsCurrentCount Counter64,
         safAgentRuntimeRemoteEndpointsHighCount Counter64,
         safAgentRuntimeRemoteEndpointsTotalCount Counter64,
         safAgentRuntimePausedForIncoming INTEGER,
         safAgentRuntimePausedForForwarding INTEGER,
         safAgentRuntimeConversationsCurrentCount Counter64,
         safAgentRuntimeConversationsHighCount Counter64,
         safAgentRuntimeConversationsTotalCount Counter64,
         safAgentRuntimeMessagesCurrentCount Counter64,
         safAgentRuntimeMessagesPendingCount Counter64,
         safAgentRuntimeMessagesHighCount Counter64,
         safAgentRuntimeMessagesReceivedCount Counter64,
         safAgentRuntimeMessagesThresholdTime Counter64,
         safAgentRuntimeBytesPendingCount Counter64,
         safAgentRuntimeBytesCurrentCount Counter64,
         safAgentRuntimeBytesHighCount Counter64,
         safAgentRuntimeBytesReceivedCount Counter64,
         safAgentRuntimeBytesThresholdTime Counter64,
         safAgentRuntimeFailedMessagesTotal Counter64,
         safAgentRuntimePausedForReceiving OCTET STRING,
         safAgentRuntimeHealthState OCTET STRING
      }
      
   
   safAgentRuntimeIndex OBJECT-TYPE
      SYNTAX      DisplayString (SIZE (1..16))
      MAX-ACCESS  read-only
      STATUS      current
      DESCRIPTION "Unique value directed from ObjectName which is used as table index"
      ::= { safAgentRuntimeEntry 1  }
   
   
   safAgentRuntimeObjectName OBJECT-TYPE
      SYNTAX      DisplayString (SIZE (1..256))
      MAX-ACCESS  read-only
      STATUS      current
      DESCRIPTION "JMX-standard MBean name"
      ::= { safAgentRuntimeEntry 5  }
   
   
   safAgentRuntimeType OBJECT-TYPE
      SYNTAX      DisplayString (SIZE (1..64))
      MAX-ACCESS  read-only
      STATUS      current
      DESCRIPTION "Returns the type of the MBean. "
      ::= { safAgentRuntimeEntry 10  }
   
   
   safAgentRuntimeName OBJECT-TYPE
      SYNTAX      DisplayString (SIZE (1..64))
      MAX-ACCESS  read-only
      STATUS      current
      DESCRIPTION "The name of this configuration. WebLogic Server uses an MBean to implement and persist the configuration. "
      ::= { safAgentRuntimeEntry 15  }
   
   
   safAgentRuntimeParent OBJECT-TYPE
      SYNTAX      DisplayString (SIZE (1..256))
      MAX-ACCESS  read-only
      STATUS      current
      DESCRIPTION "BEA-proprietary Parent object's identification, with syntax
      <type>:<name>"
      ::= { safAgentRuntimeEntry 20  }
   
   
   safAgentRuntimeRemoteEndpointsCurrentCount OBJECT-TYPE
      SYNTAX      Counter64
      MAX-ACCESS  read-only
      STATUS      current
      DESCRIPTION "The current number of remote endpoints to which this SAF agent has been storing and forwarding messages. "
      ::= { safAgentRuntimeEntry 25  }
   
   
   safAgentRuntimeRemoteEndpointsHighCount OBJECT-TYPE
      SYNTAX      Counter64
      MAX-ACCESS  read-only
      STATUS      current
      DESCRIPTION "The peak number of remote endpoints to which this SAF agent has been storing and forwarding messages since last reset. "
      ::= { safAgentRuntimeEntry 30  }
   
   
   safAgentRuntimeRemoteEndpointsTotalCount OBJECT-TYPE
      SYNTAX      Counter64
      MAX-ACCESS  read-only
      STATUS      current
      DESCRIPTION "The number of remote endpoints to which this SAF agent has been storing and forwarding messages since last reset. "
      ::= { safAgentRuntimeEntry 35  }
   
   
   safAgentRuntimePausedForIncoming OBJECT-TYPE
      SYNTAX      INTEGER
                  {
                     true(1),
                     false(2)
                  }
      
      MAX-ACCESS  read-only
      STATUS      current
      DESCRIPTION "Indicates whether or not the sending agent is paused for incoming messages at the current time. "
      ::= { safAgentRuntimeEntry 40  }
   
   
   safAgentRuntimePausedForForwarding OBJECT-TYPE
      SYNTAX      INTEGER
                  {
                     true(1),
                     false(2)
                  }
      
      MAX-ACCESS  read-only
      STATUS      current
      DESCRIPTION "Indicates whether or not the sending agent is paused for forwarding at the current time. "
      ::= { safAgentRuntimeEntry 45  }
   
   
   safAgentRuntimeConversationsCurrentCount OBJECT-TYPE
      SYNTAX      Counter64
      MAX-ACCESS  read-only
      STATUS      current
      DESCRIPTION "Returns the current number of conversations "
      ::= { safAgentRuntimeEntry 55  }
   
   
   safAgentRuntimeConversationsHighCount OBJECT-TYPE
      SYNTAX      Counter64
      MAX-ACCESS  read-only
      STATUS      current
      DESCRIPTION "The peak number of conversations since the last reset. "
      ::= { safAgentRuntimeEntry 60  }
   
   
   safAgentRuntimeConversationsTotalCount OBJECT-TYPE
      SYNTAX      Counter64
      MAX-ACCESS  read-only
      STATUS      current
      DESCRIPTION "The total number of conversations since the last reset. "
      ::= { safAgentRuntimeEntry 65  }
   
   
   safAgentRuntimeMessagesCurrentCount OBJECT-TYPE
      SYNTAX      Counter64
      MAX-ACCESS  read-only
      STATUS      current
      DESCRIPTION "Returns the current number of messages. This number includes the pending messages. "
      ::= { safAgentRuntimeEntry 70  }
   
   
   safAgentRuntimeMessagesPendingCount OBJECT-TYPE
      SYNTAX      Counter64
      MAX-ACCESS  read-only
      STATUS      current
      DESCRIPTION "Returns the number of pending messages. Pending messages are over and above the current number of messages. A pending message is one that has either been sent in a transaction and not committed, or been forwarded but has not been acknowledged. "
      ::= { safAgentRuntimeEntry 75  }
   
   
   safAgentRuntimeMessagesHighCount OBJECT-TYPE
      SYNTAX      Counter64
      MAX-ACCESS  read-only
      STATUS      current
      DESCRIPTION "Returns the peak number of messages since the last reset. "
      ::= { safAgentRuntimeEntry 80  }
   
   
   safAgentRuntimeMessagesReceivedCount OBJECT-TYPE
      SYNTAX      Counter64
      MAX-ACCESS  read-only
      STATUS      current
      DESCRIPTION "The number of messages received since the last reset. "
      ::= { safAgentRuntimeEntry 85  }
   
   
   safAgentRuntimeMessagesThresholdTime OBJECT-TYPE
      SYNTAX      Counter64
      MAX-ACCESS  read-only
      STATUS      current
      DESCRIPTION "Returns the amount of time in the threshold condition since the last reset. "
      ::= { safAgentRuntimeEntry 90  }
   
   
   safAgentRuntimeBytesPendingCount OBJECT-TYPE
      SYNTAX      Counter64
      MAX-ACCESS  read-only
      STATUS      current
      DESCRIPTION "Returns the number of pending bytes. Pending bytes are over and above the current number of bytes. "
      ::= { safAgentRuntimeEntry 95  }
   
   
   safAgentRuntimeBytesCurrentCount OBJECT-TYPE
      SYNTAX      Counter64
      MAX-ACCESS  read-only
      STATUS      current
      DESCRIPTION "Returns the current number of bytes. This number does not include the pending bytes. "
      ::= { safAgentRuntimeEntry 100  }
   
   
   safAgentRuntimeBytesHighCount OBJECT-TYPE
      SYNTAX      Counter64
      MAX-ACCESS  read-only
      STATUS      current
      DESCRIPTION "Returns the peak number of bytes since the last reset. "
      ::= { safAgentRuntimeEntry 105  }
   
   
   safAgentRuntimeBytesReceivedCount OBJECT-TYPE
      SYNTAX      Counter64
      MAX-ACCESS  read-only
      STATUS      current
      DESCRIPTION "The number of bytes received since the last reset. "
      ::= { safAgentRuntimeEntry 110  }
   
   
   safAgentRuntimeBytesThresholdTime OBJECT-TYPE
      SYNTAX      Counter64
      MAX-ACCESS  read-only
      STATUS      current
      DESCRIPTION "Returns the amount of time in the threshold condition since the last reset. "
      ::= { safAgentRuntimeEntry 115  }
   
   
   safAgentRuntimeFailedMessagesTotal OBJECT-TYPE
      SYNTAX      Counter64
      MAX-ACCESS  read-only
      STATUS      current
      DESCRIPTION "Returns the total number of messages that have failed to be forwarded since the last reset. "
      ::= { safAgentRuntimeEntry 120  }
   
   
   safAgentRuntimePausedForReceiving OBJECT-TYPE
      SYNTAX      OCTET STRING
      MAX-ACCESS  read-only
      STATUS      current
      DESCRIPTION "Indicates whether or not the receiving agent is paused for receiving at the current time. "
      ::= { safAgentRuntimeEntry 121  }
   
   
   safAgentRuntimeHealthState OBJECT-TYPE
      SYNTAX      OCTET STRING
      MAX-ACCESS  read-only
      STATUS      current
      DESCRIPTION "The health state of this JMS server. "
      ::= { safAgentRuntimeEntry 122  }
   
   
   safConversationRuntimeTable OBJECT-TYPE
      SYNTAX      SEQUENCE OF SafConversationRuntimeEntry
      MAX-ACCESS  not-accessible
      STATUS      current
      DESCRIPTION "This class is used for monitoring a WebLogic SAF conversation. "
      ::= { wls 471  }
      
   
   safConversationRuntimeEntry OBJECT-TYPE
      SYNTAX      SafConversationRuntimeEntry
      MAX-ACCESS  not-accessible
      STATUS      current
      DESCRIPTION "Entry of SafConversationRuntimeTable"
      INDEX { safConversationRuntimeIndex}
      ::= { safConversationRuntimeTable 1 }
      
   SafConversationRuntimeEntry ::=
      SEQUENCE
      {
         safConversationRuntimeIndex DisplayString,
         safConversationRuntimeObjectName DisplayString,
         safConversationRuntimeType DisplayString,
         safConversationRuntimeName DisplayString,
         safConversationRuntimeParent DisplayString,
         safConversationRuntimeConversationName DisplayString,
         safConversationRuntimeDestinationURL DisplayString,
         safConversationRuntimeQOS DisplayString
      }
      
   
   safConversationRuntimeIndex OBJECT-TYPE
      SYNTAX      DisplayString (SIZE (1..16))
      MAX-ACCESS  read-only
      STATUS      current
      DESCRIPTION "Unique value directed from ObjectName which is used as table index"
      ::= { safConversationRuntimeEntry 1  }
   
   
   safConversationRuntimeObjectName OBJECT-TYPE
      SYNTAX      DisplayString (SIZE (1..256))
      MAX-ACCESS  read-only
      STATUS      current
      DESCRIPTION "JMX-standard MBean name"
      ::= { safConversationRuntimeEntry 5  }
   
   
   safConversationRuntimeType OBJECT-TYPE
      SYNTAX      DisplayString (SIZE (1..64))
      MAX-ACCESS  read-only
      STATUS      current
      DESCRIPTION "Returns the type of the MBean. "
      ::= { safConversationRuntimeEntry 10  }
   
   
   safConversationRuntimeName OBJECT-TYPE
      SYNTAX      DisplayString (SIZE (1..64))
      MAX-ACCESS  read-only
      STATUS      current
      DESCRIPTION "The name of this configuration. WebLogic Server uses an MBean to implement and persist the configuration. "
      ::= { safConversationRuntimeEntry 15  }
   
   
   safConversationRuntimeParent OBJECT-TYPE
      SYNTAX      DisplayString (SIZE (1..256))
      MAX-ACCESS  read-only
      STATUS      current
      DESCRIPTION "BEA-proprietary Parent object's identification, with syntax
      <type>:<name>"
      ::= { safConversationRuntimeEntry 20  }
   
   
   safConversationRuntimeConversationName OBJECT-TYPE
      SYNTAX      DisplayString (SIZE (1..64))
      MAX-ACCESS  read-only
      STATUS      current
      DESCRIPTION "The name of the conversation. "
      ::= { safConversationRuntimeEntry 25  }
   
   
   safConversationRuntimeDestinationURL OBJECT-TYPE
      SYNTAX      DisplayString (SIZE (1..64))
      MAX-ACCESS  read-only
      STATUS      current
      DESCRIPTION "The URL of the destination. "
      ::= { safConversationRuntimeEntry 30  }
   
   
   safConversationRuntimeQOS OBJECT-TYPE
      SYNTAX      DisplayString (SIZE (1..64))
      MAX-ACCESS  read-only
      STATUS      current
      DESCRIPTION "The quality of service (QOS) for the SAF conversation.  The quality-of-service values are:    weblogic.management.runtime.SAFConstants.QOS_EXACTLY_ONCE   weblogic.management.runtime.SAFConstants.QOS_ATLEAST_ONCE   weblogic.management.runtime.SAFConstants.QOS_ATMOST_ONCE  "
      ::= { safConversationRuntimeEntry 35  }
   
   
   safRemoteEndpointRuntimeTable OBJECT-TYPE
      SYNTAX      SEQUENCE OF SafRemoteEndpointRuntimeEntry
      MAX-ACCESS  not-accessible
      STATUS      current
      DESCRIPTION "This class is used for monitoring a WebLogic SAF remote endpoint "
      ::= { wls 472  }
      
   
   safRemoteEndpointRuntimeEntry OBJECT-TYPE
      SYNTAX      SafRemoteEndpointRuntimeEntry
      MAX-ACCESS  not-accessible
      STATUS      current
      DESCRIPTION "Entry of SafRemoteEndpointRuntimeTable"
      INDEX { safRemoteEndpointRuntimeIndex}
      ::= { safRemoteEndpointRuntimeTable 1 }
      
   SafRemoteEndpointRuntimeEntry ::=
      SEQUENCE
      {
         safRemoteEndpointRuntimeIndex DisplayString,
         safRemoteEndpointRuntimeObjectName DisplayString,
         safRemoteEndpointRuntimeType DisplayString,
         safRemoteEndpointRuntimeName DisplayString,
         safRemoteEndpointRuntimeParent DisplayString,
         safRemoteEndpointRuntimeURL DisplayString,
         safRemoteEndpointRuntimeEndpointType DisplayString,
         safRemoteEndpointRuntimePausedForIncoming INTEGER,
         safRemoteEndpointRuntimePausedForForwarding INTEGER,
         safRemoteEndpointRuntimeDowntimeHigh Counter64,
         safRemoteEndpointRuntimeDowntimeTotal Counter64,
         safRemoteEndpointRuntimeUptimeHigh Counter64,
         safRemoteEndpointRuntimeUptimeTotal Counter64,
         safRemoteEndpointRuntimeMessagesCurrentCount Counter64,
         safRemoteEndpointRuntimeMessagesPendingCount Counter64,
         safRemoteEndpointRuntimeMessagesHighCount Counter64,
         safRemoteEndpointRuntimeMessagesReceivedCount Counter64,
         safRemoteEndpointRuntimeMessagesThresholdTime Counter64,
         safRemoteEndpointRuntimeBytesPendingCount Counter64,
         safRemoteEndpointRuntimeBytesCurrentCount Counter64,
         safRemoteEndpointRuntimeBytesHighCount Counter64,
         safRemoteEndpointRuntimeBytesReceivedCount Counter64,
         safRemoteEndpointRuntimeBytesThresholdTime Counter64,
         safRemoteEndpointRuntimeFailedMessagesTotal Counter64,
         safRemoteEndpointRuntimeLastTimeFailedToConnect OCTET STRING,
         safRemoteEndpointRuntimeOperationState OCTET STRING,
         safRemoteEndpointRuntimeLastTimeConnected OCTET STRING
      }
      
   
   safRemoteEndpointRuntimeIndex OBJECT-TYPE
      SYNTAX      DisplayString (SIZE (1..16))
      MAX-ACCESS  read-only
      STATUS      current
      DESCRIPTION "Unique value directed from ObjectName which is used as table index"
      ::= { safRemoteEndpointRuntimeEntry 1  }
   
   
   safRemoteEndpointRuntimeObjectName OBJECT-TYPE
      SYNTAX      DisplayString (SIZE (1..256))
      MAX-ACCESS  read-only
      STATUS      current
      DESCRIPTION "JMX-standard MBean name"
      ::= { safRemoteEndpointRuntimeEntry 5  }
   
   
   safRemoteEndpointRuntimeType OBJECT-TYPE
      SYNTAX      DisplayString (SIZE (1..64))
      MAX-ACCESS  read-only
      STATUS      current
      DESCRIPTION "Returns the type of the MBean. "
      ::= { safRemoteEndpointRuntimeEntry 10  }
   
   
   safRemoteEndpointRuntimeName OBJECT-TYPE
      SYNTAX      DisplayString (SIZE (1..64))
      MAX-ACCESS  read-only
      STATUS      current
      DESCRIPTION "The name of this configuration. WebLogic Server uses an MBean to implement and persist the configuration. "
      ::= { safRemoteEndpointRuntimeEntry 15  }
   
   
   safRemoteEndpointRuntimeParent OBJECT-TYPE
      SYNTAX      DisplayString (SIZE (1..256))
      MAX-ACCESS  read-only
      STATUS      current
      DESCRIPTION "BEA-proprietary Parent object's identification, with syntax
      <type>:<name>"
      ::= { safRemoteEndpointRuntimeEntry 20  }
   
   
   safRemoteEndpointRuntimeURL OBJECT-TYPE
      SYNTAX      DisplayString (SIZE (1..128))
      MAX-ACCESS  read-only
      STATUS      current
      DESCRIPTION "The URL of the remote endpoint. "
      ::= { safRemoteEndpointRuntimeEntry 25  }
   
   
   safRemoteEndpointRuntimeEndpointType OBJECT-TYPE
      SYNTAX      DisplayString (SIZE (1..256))
      MAX-ACCESS  read-only
      STATUS      current
      DESCRIPTION "Specifies if the remote endpoint is a JMS or Web Services (WSRM) destination. The possible values are: weblogic.management.runtime.SAFConstants.JMS_ENDPOINT or weblogic.management.runtime.SAFConstants.WS_ENDPOINT. "
      ::= { safRemoteEndpointRuntimeEntry 30  }
   
   
   safRemoteEndpointRuntimePausedForIncoming OBJECT-TYPE
      SYNTAX      INTEGER
                  {
                     true(1),
                     false(2)
                  }
      
      MAX-ACCESS  read-only
      STATUS      current
      DESCRIPTION "Indicates if a remote endpoint is currently not accepting new messages. "
      ::= { safRemoteEndpointRuntimeEntry 35  }
   
   
   safRemoteEndpointRuntimePausedForForwarding OBJECT-TYPE
      SYNTAX      INTEGER
                  {
                     true(1),
                     false(2)
                  }
      
      MAX-ACCESS  read-only
      STATUS      current
      DESCRIPTION "Indicates if the remote endpoint is currently not forwarding messages. "
      ::= { safRemoteEndpointRuntimeEntry 40  }
   
   
   safRemoteEndpointRuntimeDowntimeHigh OBJECT-TYPE
      SYNTAX      Counter64
      MAX-ACCESS  read-only
      STATUS      current
      DESCRIPTION "Specifies the longest time, in seconds, that the remote endpoint has not been available since the last reset. "
      ::= { safRemoteEndpointRuntimeEntry 50  }
   
   
   safRemoteEndpointRuntimeDowntimeTotal OBJECT-TYPE
      SYNTAX      Counter64
      MAX-ACCESS  read-only
      STATUS      current
      DESCRIPTION "Specifies the total time, in seconds, that the remote endpoint has not been available since the last reset. "
      ::= { safRemoteEndpointRuntimeEntry 55  }
   
   
   safRemoteEndpointRuntimeUptimeHigh OBJECT-TYPE
      SYNTAX      Counter64
      MAX-ACCESS  read-only
      STATUS      current
      DESCRIPTION "Specifies the longest time, in seconds, that the remote endpoint has been available since the last reset. "
      ::= { safRemoteEndpointRuntimeEntry 60  }
   
   
   safRemoteEndpointRuntimeUptimeTotal OBJECT-TYPE
      SYNTAX      Counter64
      MAX-ACCESS  read-only
      STATUS      current
      DESCRIPTION "Specifies the total time, in seconds, that the remote endpoint has been available since the last reset. "
      ::= { safRemoteEndpointRuntimeEntry 65  }
   
   
   safRemoteEndpointRuntimeMessagesCurrentCount OBJECT-TYPE
      SYNTAX      Counter64
      MAX-ACCESS  read-only
      STATUS      current
      DESCRIPTION "Returns the current number of messages. This number includes the pending messages. "
      ::= { safRemoteEndpointRuntimeEntry 85  }
   
   
   safRemoteEndpointRuntimeMessagesPendingCount OBJECT-TYPE
      SYNTAX      Counter64
      MAX-ACCESS  read-only
      STATUS      current
      DESCRIPTION "Returns the number of pending messages. Pending messages are over and above the current number of messages. A pending message is one that has either been sent in a transaction and not committed, or been forwarded but has not been acknowledged. "
      ::= { safRemoteEndpointRuntimeEntry 90  }
   
   
   safRemoteEndpointRuntimeMessagesHighCount OBJECT-TYPE
      SYNTAX      Counter64
      MAX-ACCESS  read-only
      STATUS      current
      DESCRIPTION "Returns the peak number of messages since the last reset. "
      ::= { safRemoteEndpointRuntimeEntry 95  }
   
   
   safRemoteEndpointRuntimeMessagesReceivedCount OBJECT-TYPE
      SYNTAX      Counter64
      MAX-ACCESS  read-only
      STATUS      current
      DESCRIPTION "The number of messages received since the last reset. "
      ::= { safRemoteEndpointRuntimeEntry 100  }
   
   
   safRemoteEndpointRuntimeMessagesThresholdTime OBJECT-TYPE
      SYNTAX      Counter64
      MAX-ACCESS  read-only
      STATUS      current
      DESCRIPTION "Returns the amount of time in the threshold condition since the last reset. "
      ::= { safRemoteEndpointRuntimeEntry 105  }
   
   
   safRemoteEndpointRuntimeBytesPendingCount OBJECT-TYPE
      SYNTAX      Counter64
      MAX-ACCESS  read-only
      STATUS      current
      DESCRIPTION "Returns the number of pending bytes. Pending bytes are over and above the current number of bytes. "
      ::= { safRemoteEndpointRuntimeEntry 110  }
   
   
   safRemoteEndpointRuntimeBytesCurrentCount OBJECT-TYPE
      SYNTAX      Counter64
      MAX-ACCESS  read-only
      STATUS      current
      DESCRIPTION "Returns the current number of bytes. This number does not include the pending bytes. "
      ::= { safRemoteEndpointRuntimeEntry 115  }
   
   
   safRemoteEndpointRuntimeBytesHighCount OBJECT-TYPE
      SYNTAX      Counter64
      MAX-ACCESS  read-only
      STATUS      current
      DESCRIPTION "Returns the peak number of bytes since the last reset. "
      ::= { safRemoteEndpointRuntimeEntry 120  }
   
   
   safRemoteEndpointRuntimeBytesReceivedCount OBJECT-TYPE
      SYNTAX      Counter64
      MAX-ACCESS  read-only
      STATUS      current
      DESCRIPTION "The number of bytes received since the last reset. "
      ::= { safRemoteEndpointRuntimeEntry 125  }
   
   
   safRemoteEndpointRuntimeBytesThresholdTime OBJECT-TYPE
      SYNTAX      Counter64
      MAX-ACCESS  read-only
      STATUS      current
      DESCRIPTION "Returns the amount of time in the threshold condition since the last reset. "
      ::= { safRemoteEndpointRuntimeEntry 130  }
   
   
   safRemoteEndpointRuntimeFailedMessagesTotal OBJECT-TYPE
      SYNTAX      Counter64
      MAX-ACCESS  read-only
      STATUS      current
      DESCRIPTION "Returns the total number of messages that have failed to be forwarded since the last reset. "
      ::= { safRemoteEndpointRuntimeEntry 135  }
   
   
   safRemoteEndpointRuntimeLastTimeFailedToConnect OBJECT-TYPE
      SYNTAX      OCTET STRING
      MAX-ACCESS  read-only
      STATUS      current
      DESCRIPTION "Specifies the last time that the remote endpoint failed to be connected. "
      ::= { safRemoteEndpointRuntimeEntry 136  }
   
   
   safRemoteEndpointRuntimeOperationState OBJECT-TYPE
      SYNTAX      OCTET STRING
      MAX-ACCESS  read-only
      STATUS      current
      DESCRIPTION "Specifies the state of the most recent ExireAll operation. "
      ::= { safRemoteEndpointRuntimeEntry 137  }
   
   
   safRemoteEndpointRuntimeLastTimeConnected OBJECT-TYPE
      SYNTAX      OCTET STRING
      MAX-ACCESS  read-only
      STATUS      current
      DESCRIPTION "Specifies the last time that the remote endpoint was connected. "
      ::= { safRemoteEndpointRuntimeEntry 138  }
   
   
   wldfDbstoreArchiveRuntimeTable OBJECT-TYPE
      SYNTAX      SEQUENCE OF WldfDbstoreArchiveRuntimeEntry
      MAX-ACCESS  not-accessible
      STATUS      current
      DESCRIPTION "Use this interface to retrieve statistical information associated with the WLDF archives that use databases for storage. "
      ::= { wls 480  }
      
   
   wldfDbstoreArchiveRuntimeEntry OBJECT-TYPE
      SYNTAX      WldfDbstoreArchiveRuntimeEntry
      MAX-ACCESS  not-accessible
      STATUS      current
      DESCRIPTION "Entry of WLDFDbStoreArchiveRuntimeTable"
      INDEX { wldfDbstoreArchiveRuntimeIndex}
      ::= { wldfDbstoreArchiveRuntimeTable 1 }
      
   WldfDbstoreArchiveRuntimeEntry ::=
      SEQUENCE
      {
         wldfDbstoreArchiveRuntimeIndex DisplayString,
         wldfDbstoreArchiveRuntimeObjectName DisplayString,
         wldfDbstoreArchiveRuntimeType DisplayString,
         wldfDbstoreArchiveRuntimeName DisplayString,
         wldfDbstoreArchiveRuntimeParent DisplayString,
         wldfDbstoreArchiveRuntimeRecordSeekCount Counter64,
         wldfDbstoreArchiveRuntimeRecordSeekTime Counter64,
         wldfDbstoreArchiveRuntimeRetrievedRecordCount Counter64,
         wldfDbstoreArchiveRuntimeRecordRetrievalTime Counter64,
         wldfDbstoreArchiveRuntimeInsertionCount Counter64,
         wldfDbstoreArchiveRuntimeInsertionTime Counter64,
         wldfDbstoreArchiveRuntimeDeletionCount Counter64,
         wldfDbstoreArchiveRuntimeDeletionTime Counter64,
         wldfDbstoreArchiveRuntimeLastDataRetirementStartTime Counter64,
         wldfDbstoreArchiveRuntimeDataRetirementCycles INTEGER,
         wldfDbstoreArchiveRuntimeDataRetirementTotalTime Counter64,
         wldfDbstoreArchiveRuntimeRetiredRecordCount Counter64,
         wldfDbstoreArchiveRuntimeLastDataRetirementTime Counter64
      }
      
   
   wldfDbstoreArchiveRuntimeIndex OBJECT-TYPE
      SYNTAX      DisplayString (SIZE (1..16))
      MAX-ACCESS  read-only
      STATUS      current
      DESCRIPTION "Unique value directed from ObjectName which is used as table index"
      ::= { wldfDbstoreArchiveRuntimeEntry 1  }
   
   
   wldfDbstoreArchiveRuntimeObjectName OBJECT-TYPE
      SYNTAX      DisplayString (SIZE (1..256))
      MAX-ACCESS  read-only
      STATUS      current
      DESCRIPTION "JMX-standard MBean name"
      ::= { wldfDbstoreArchiveRuntimeEntry 5  }
   
   
   wldfDbstoreArchiveRuntimeType OBJECT-TYPE
      SYNTAX      DisplayString (SIZE (1..64))
      MAX-ACCESS  read-only
      STATUS      current
      DESCRIPTION "Returns the type of the MBean. "
      ::= { wldfDbstoreArchiveRuntimeEntry 10  }
   
   
   wldfDbstoreArchiveRuntimeName OBJECT-TYPE
      SYNTAX      DisplayString (SIZE (1..64))
      MAX-ACCESS  read-only
      STATUS      current
      DESCRIPTION "The name of this configuration. WebLogic Server uses an MBean to implement and persist the configuration. "
      ::= { wldfDbstoreArchiveRuntimeEntry 15  }
   
   
   wldfDbstoreArchiveRuntimeParent OBJECT-TYPE
      SYNTAX      DisplayString (SIZE (1..256))
      MAX-ACCESS  read-only
      STATUS      current
      DESCRIPTION "BEA-proprietary Parent object's identification, with syntax
      <type>:<name>"
      ::= { wldfDbstoreArchiveRuntimeEntry 20  }
   
   
   wldfDbstoreArchiveRuntimeRecordSeekCount OBJECT-TYPE
      SYNTAX      Counter64
      MAX-ACCESS  read-only
      STATUS      current
      DESCRIPTION " "
      ::= { wldfDbstoreArchiveRuntimeEntry 25  }
   
   
   wldfDbstoreArchiveRuntimeRecordSeekTime OBJECT-TYPE
      SYNTAX      Counter64
      MAX-ACCESS  read-only
      STATUS      current
      DESCRIPTION " "
      ::= { wldfDbstoreArchiveRuntimeEntry 30  }
   
   
   wldfDbstoreArchiveRuntimeRetrievedRecordCount OBJECT-TYPE
      SYNTAX      Counter64
      MAX-ACCESS  read-only
      STATUS      current
      DESCRIPTION " "
      ::= { wldfDbstoreArchiveRuntimeEntry 35  }
   
   
   wldfDbstoreArchiveRuntimeRecordRetrievalTime OBJECT-TYPE
      SYNTAX      Counter64
      MAX-ACCESS  read-only
      STATUS      current
      DESCRIPTION " "
      ::= { wldfDbstoreArchiveRuntimeEntry 40  }
   
   
   wldfDbstoreArchiveRuntimeInsertionCount OBJECT-TYPE
      SYNTAX      Counter64
      MAX-ACCESS  read-only
      STATUS      current
      DESCRIPTION " "
      ::= { wldfDbstoreArchiveRuntimeEntry 45  }
   
   
   wldfDbstoreArchiveRuntimeInsertionTime OBJECT-TYPE
      SYNTAX      Counter64
      MAX-ACCESS  read-only
      STATUS      current
      DESCRIPTION " "
      ::= { wldfDbstoreArchiveRuntimeEntry 50  }
   
   
   wldfDbstoreArchiveRuntimeDeletionCount OBJECT-TYPE
      SYNTAX      Counter64
      MAX-ACCESS  read-only
      STATUS      current
      DESCRIPTION " "
      ::= { wldfDbstoreArchiveRuntimeEntry 55  }
   
   
   wldfDbstoreArchiveRuntimeDeletionTime OBJECT-TYPE
      SYNTAX      Counter64
      MAX-ACCESS  read-only
      STATUS      current
      DESCRIPTION " "
      ::= { wldfDbstoreArchiveRuntimeEntry 60  }
   
   
   wldfDbstoreArchiveRuntimeLastDataRetirementStartTime OBJECT-TYPE
      SYNTAX      Counter64
      MAX-ACCESS  read-only
      STATUS      current
      DESCRIPTION " "
      ::= { wldfDbstoreArchiveRuntimeEntry 61  }
   
   
   wldfDbstoreArchiveRuntimeDataRetirementCycles OBJECT-TYPE
      SYNTAX      INTEGER
      MAX-ACCESS  read-only
      STATUS      current
      DESCRIPTION " "
      ::= { wldfDbstoreArchiveRuntimeEntry 62  }
   
   
   wldfDbstoreArchiveRuntimeDataRetirementTotalTime OBJECT-TYPE
      SYNTAX      Counter64
      MAX-ACCESS  read-only
      STATUS      current
      DESCRIPTION " "
      ::= { wldfDbstoreArchiveRuntimeEntry 63  }
   
   
   wldfDbstoreArchiveRuntimeRetiredRecordCount OBJECT-TYPE
      SYNTAX      Counter64
      MAX-ACCESS  read-only
      STATUS      current
      DESCRIPTION " "
      ::= { wldfDbstoreArchiveRuntimeEntry 64  }
   
   
   wldfDbstoreArchiveRuntimeLastDataRetirementTime OBJECT-TYPE
      SYNTAX      Counter64
      MAX-ACCESS  read-only
      STATUS      current
      DESCRIPTION " "
      ::= { wldfDbstoreArchiveRuntimeEntry 65  }
   
   
   wldfFileArchiveRuntimeTable OBJECT-TYPE
      SYNTAX      SEQUENCE OF WldfFileArchiveRuntimeEntry
      MAX-ACCESS  not-accessible
      STATUS      current
      DESCRIPTION "Use this interface to collect statistical information about file-based WLDF archives. "
      ::= { wls 481  }
      
   
   wldfFileArchiveRuntimeEntry OBJECT-TYPE
      SYNTAX      WldfFileArchiveRuntimeEntry
      MAX-ACCESS  not-accessible
      STATUS      current
      DESCRIPTION "Entry of WLDFFileArchiveRuntimeTable"
      INDEX { wldfFileArchiveRuntimeIndex}
      ::= { wldfFileArchiveRuntimeTable 1 }
      
   WldfFileArchiveRuntimeEntry ::=
      SEQUENCE
      {
         wldfFileArchiveRuntimeIndex DisplayString,
         wldfFileArchiveRuntimeObjectName DisplayString,
         wldfFileArchiveRuntimeType DisplayString,
         wldfFileArchiveRuntimeName DisplayString,
         wldfFileArchiveRuntimeParent DisplayString,
         wldfFileArchiveRuntimeRecordSeekCount Counter64,
         wldfFileArchiveRuntimeRecordSeekTime Counter64,
         wldfFileArchiveRuntimeRetrievedRecordCount Counter64,
         wldfFileArchiveRuntimeRecordRetrievalTime Counter64,
         wldfFileArchiveRuntimeRotatedFilesCount INTEGER,
         wldfFileArchiveRuntimeIndexCycleCount INTEGER,
         wldfFileArchiveRuntimeIndexTime Counter64,
         wldfFileArchiveRuntimeIncrementalIndexCycleCount INTEGER,
         wldfFileArchiveRuntimeIncrementalIndexTime Counter64
      }
      
   
   wldfFileArchiveRuntimeIndex OBJECT-TYPE
      SYNTAX      DisplayString (SIZE (1..16))
      MAX-ACCESS  read-only
      STATUS      current
      DESCRIPTION "Unique value directed from ObjectName which is used as table index"
      ::= { wldfFileArchiveRuntimeEntry 1  }
   
   
   wldfFileArchiveRuntimeObjectName OBJECT-TYPE
      SYNTAX      DisplayString (SIZE (1..256))
      MAX-ACCESS  read-only
      STATUS      current
      DESCRIPTION "JMX-standard MBean name"
      ::= { wldfFileArchiveRuntimeEntry 5  }
   
   
   wldfFileArchiveRuntimeType OBJECT-TYPE
      SYNTAX      DisplayString (SIZE (1..64))
      MAX-ACCESS  read-only
      STATUS      current
      DESCRIPTION "Returns the type of the MBean. "
      ::= { wldfFileArchiveRuntimeEntry 10  }
   
   
   wldfFileArchiveRuntimeName OBJECT-TYPE
      SYNTAX      DisplayString (SIZE (1..64))
      MAX-ACCESS  read-only
      STATUS      current
      DESCRIPTION "The name of this configuration. WebLogic Server uses an MBean to implement and persist the configuration. "
      ::= { wldfFileArchiveRuntimeEntry 15  }
   
   
   wldfFileArchiveRuntimeParent OBJECT-TYPE
      SYNTAX      DisplayString (SIZE (1..256))
      MAX-ACCESS  read-only
      STATUS      current
      DESCRIPTION "BEA-proprietary Parent object's identification, with syntax
      <type>:<name>"
      ::= { wldfFileArchiveRuntimeEntry 20  }
   
   
   wldfFileArchiveRuntimeRecordSeekCount OBJECT-TYPE
      SYNTAX      Counter64
      MAX-ACCESS  read-only
      STATUS      current
      DESCRIPTION " "
      ::= { wldfFileArchiveRuntimeEntry 25  }
   
   
   wldfFileArchiveRuntimeRecordSeekTime OBJECT-TYPE
      SYNTAX      Counter64
      MAX-ACCESS  read-only
      STATUS      current
      DESCRIPTION " "
      ::= { wldfFileArchiveRuntimeEntry 30  }
   
   
   wldfFileArchiveRuntimeRetrievedRecordCount OBJECT-TYPE
      SYNTAX      Counter64
      MAX-ACCESS  read-only
      STATUS      current
      DESCRIPTION " "
      ::= { wldfFileArchiveRuntimeEntry 35  }
   
   
   wldfFileArchiveRuntimeRecordRetrievalTime OBJECT-TYPE
      SYNTAX      Counter64
      MAX-ACCESS  read-only
      STATUS      current
      DESCRIPTION " "
      ::= { wldfFileArchiveRuntimeEntry 40  }
   
   
   wldfFileArchiveRuntimeRotatedFilesCount OBJECT-TYPE
      SYNTAX      INTEGER
      MAX-ACCESS  read-only
      STATUS      current
      DESCRIPTION " "
      ::= { wldfFileArchiveRuntimeEntry 45  }
   
   
   wldfFileArchiveRuntimeIndexCycleCount OBJECT-TYPE
      SYNTAX      INTEGER
      MAX-ACCESS  read-only
      STATUS      current
      DESCRIPTION " "
      ::= { wldfFileArchiveRuntimeEntry 50  }
   
   
   wldfFileArchiveRuntimeIndexTime OBJECT-TYPE
      SYNTAX      Counter64
      MAX-ACCESS  read-only
      STATUS      current
      DESCRIPTION " "
      ::= { wldfFileArchiveRuntimeEntry 55  }
   
   
   wldfFileArchiveRuntimeIncrementalIndexCycleCount OBJECT-TYPE
      SYNTAX      INTEGER
      MAX-ACCESS  read-only
      STATUS      current
      DESCRIPTION " "
      ::= { wldfFileArchiveRuntimeEntry 60  }
   
   
   wldfFileArchiveRuntimeIncrementalIndexTime OBJECT-TYPE
      SYNTAX      Counter64
      MAX-ACCESS  read-only
      STATUS      current
      DESCRIPTION " "
      ::= { wldfFileArchiveRuntimeEntry 65  }
   
   
   wldfWlstoreArchiveRuntimeTable OBJECT-TYPE
      SYNTAX      SEQUENCE OF WldfWlstoreArchiveRuntimeEntry
      MAX-ACCESS  not-accessible
      STATUS      current
      DESCRIPTION "Use this interface to retrieve statistical information associated with WLDF archives that use WebLogic Store for data storage. "
      ::= { wls 482  }
      
   
   wldfWlstoreArchiveRuntimeEntry OBJECT-TYPE
      SYNTAX      WldfWlstoreArchiveRuntimeEntry
      MAX-ACCESS  not-accessible
      STATUS      current
      DESCRIPTION "Entry of WLDFWlstoreArchiveRuntimeTable"
      INDEX { wldfWlstoreArchiveRuntimeIndex}
      ::= { wldfWlstoreArchiveRuntimeTable 1 }
      
   WldfWlstoreArchiveRuntimeEntry ::=
      SEQUENCE
      {
         wldfWlstoreArchiveRuntimeIndex DisplayString,
         wldfWlstoreArchiveRuntimeObjectName DisplayString,
         wldfWlstoreArchiveRuntimeType DisplayString,
         wldfWlstoreArchiveRuntimeName DisplayString,
         wldfWlstoreArchiveRuntimeParent DisplayString,
         wldfWlstoreArchiveRuntimeRecordSeekCount Counter64,
         wldfWlstoreArchiveRuntimeRecordSeekTime Counter64,
         wldfWlstoreArchiveRuntimeRetrievedRecordCount Counter64,
         wldfWlstoreArchiveRuntimeRecordRetrievalTime Counter64,
         wldfWlstoreArchiveRuntimeIndexPageCount INTEGER,
         wldfWlstoreArchiveRuntimeInsertionCount Counter64,
         wldfWlstoreArchiveRuntimeInsertionTime Counter64,
         wldfWlstoreArchiveRuntimeDeletionCount Counter64,
         wldfWlstoreArchiveRuntimeDeletionTime Counter64,
         wldfWlstoreArchiveRuntimeLastDataRetirementStartTime Counter64,
         wldfWlstoreArchiveRuntimeRecordCount Counter64,
         wldfWlstoreArchiveRuntimeDataRetirementCycles INTEGER,
         wldfWlstoreArchiveRuntimeDataRetirementTotalTime Counter64,
         wldfWlstoreArchiveRuntimeRetiredRecordCount Counter64,
         wldfWlstoreArchiveRuntimeLastDataRetirementTime Counter64
      }
      
   
   wldfWlstoreArchiveRuntimeIndex OBJECT-TYPE
      SYNTAX      DisplayString (SIZE (1..16))
      MAX-ACCESS  read-only
      STATUS      current
      DESCRIPTION "Unique value directed from ObjectName which is used as table index"
      ::= { wldfWlstoreArchiveRuntimeEntry 1  }
   
   
   wldfWlstoreArchiveRuntimeObjectName OBJECT-TYPE
      SYNTAX      DisplayString (SIZE (1..256))
      MAX-ACCESS  read-only
      STATUS      current
      DESCRIPTION "JMX-standard MBean name"
      ::= { wldfWlstoreArchiveRuntimeEntry 5  }
   
   
   wldfWlstoreArchiveRuntimeType OBJECT-TYPE
      SYNTAX      DisplayString (SIZE (1..64))
      MAX-ACCESS  read-only
      STATUS      current
      DESCRIPTION "Returns the type of the MBean. "
      ::= { wldfWlstoreArchiveRuntimeEntry 10  }
   
   
   wldfWlstoreArchiveRuntimeName OBJECT-TYPE
      SYNTAX      DisplayString (SIZE (1..64))
      MAX-ACCESS  read-only
      STATUS      current
      DESCRIPTION "The name of this configuration. WebLogic Server uses an MBean to implement and persist the configuration. "
      ::= { wldfWlstoreArchiveRuntimeEntry 15  }
   
   
   wldfWlstoreArchiveRuntimeParent OBJECT-TYPE
      SYNTAX      DisplayString (SIZE (1..256))
      MAX-ACCESS  read-only
      STATUS      current
      DESCRIPTION "BEA-proprietary Parent object's identification, with syntax
      <type>:<name>"
      ::= { wldfWlstoreArchiveRuntimeEntry 20  }
   
   
   wldfWlstoreArchiveRuntimeRecordSeekCount OBJECT-TYPE
      SYNTAX      Counter64
      MAX-ACCESS  read-only
      STATUS      current
      DESCRIPTION " "
      ::= { wldfWlstoreArchiveRuntimeEntry 25  }
   
   
   wldfWlstoreArchiveRuntimeRecordSeekTime OBJECT-TYPE
      SYNTAX      Counter64
      MAX-ACCESS  read-only
      STATUS      current
      DESCRIPTION " "
      ::= { wldfWlstoreArchiveRuntimeEntry 30  }
   
   
   wldfWlstoreArchiveRuntimeRetrievedRecordCount OBJECT-TYPE
      SYNTAX      Counter64
      MAX-ACCESS  read-only
      STATUS      current
      DESCRIPTION " "
      ::= { wldfWlstoreArchiveRuntimeEntry 35  }
   
   
   wldfWlstoreArchiveRuntimeRecordRetrievalTime OBJECT-TYPE
      SYNTAX      Counter64
      MAX-ACCESS  read-only
      STATUS      current
      DESCRIPTION " "
      ::= { wldfWlstoreArchiveRuntimeEntry 40  }
   
   
   wldfWlstoreArchiveRuntimeIndexPageCount OBJECT-TYPE
      SYNTAX      INTEGER
      MAX-ACCESS  read-only
      STATUS      current
      DESCRIPTION " "
      ::= { wldfWlstoreArchiveRuntimeEntry 45  }
   
   
   wldfWlstoreArchiveRuntimeInsertionCount OBJECT-TYPE
      SYNTAX      Counter64
      MAX-ACCESS  read-only
      STATUS      current
      DESCRIPTION " "
      ::= { wldfWlstoreArchiveRuntimeEntry 50  }
   
   
   wldfWlstoreArchiveRuntimeInsertionTime OBJECT-TYPE
      SYNTAX      Counter64
      MAX-ACCESS  read-only
      STATUS      current
      DESCRIPTION " "
      ::= { wldfWlstoreArchiveRuntimeEntry 55  }
   
   
   wldfWlstoreArchiveRuntimeDeletionCount OBJECT-TYPE
      SYNTAX      Counter64
      MAX-ACCESS  read-only
      STATUS      current
      DESCRIPTION " "
      ::= { wldfWlstoreArchiveRuntimeEntry 60  }
   
   
   wldfWlstoreArchiveRuntimeDeletionTime OBJECT-TYPE
      SYNTAX      Counter64
      MAX-ACCESS  read-only
      STATUS      current
      DESCRIPTION " "
      ::= { wldfWlstoreArchiveRuntimeEntry 65  }
   
   
   wldfWlstoreArchiveRuntimeLastDataRetirementStartTime OBJECT-TYPE
      SYNTAX      Counter64
      MAX-ACCESS  read-only
      STATUS      current
      DESCRIPTION " "
      ::= { wldfWlstoreArchiveRuntimeEntry 66  }
   
   
   wldfWlstoreArchiveRuntimeRecordCount OBJECT-TYPE
      SYNTAX      Counter64
      MAX-ACCESS  read-only
      STATUS      current
      DESCRIPTION " "
      ::= { wldfWlstoreArchiveRuntimeEntry 67  }
   
   
   wldfWlstoreArchiveRuntimeDataRetirementCycles OBJECT-TYPE
      SYNTAX      INTEGER
      MAX-ACCESS  read-only
      STATUS      current
      DESCRIPTION " "
      ::= { wldfWlstoreArchiveRuntimeEntry 68  }
   
   
   wldfWlstoreArchiveRuntimeDataRetirementTotalTime OBJECT-TYPE
      SYNTAX      Counter64
      MAX-ACCESS  read-only
      STATUS      current
      DESCRIPTION " "
      ::= { wldfWlstoreArchiveRuntimeEntry 69  }
   
   
   wldfWlstoreArchiveRuntimeRetiredRecordCount OBJECT-TYPE
      SYNTAX      Counter64
      MAX-ACCESS  read-only
      STATUS      current
      DESCRIPTION " "
      ::= { wldfWlstoreArchiveRuntimeEntry 70  }
   
   
   wldfWlstoreArchiveRuntimeLastDataRetirementTime OBJECT-TYPE
      SYNTAX      Counter64
      MAX-ACCESS  read-only
      STATUS      current
      DESCRIPTION " "
      ::= { wldfWlstoreArchiveRuntimeEntry 71  }
   
   
   wldfHarvesterRuntimeTable OBJECT-TYPE
      SYNTAX      SEQUENCE OF WldfHarvesterRuntimeEntry
      MAX-ACCESS  not-accessible
      STATUS      current
      DESCRIPTION "Provides aggregated information about all active Harvester configurations, as well as metadata about harvestable and harvested attributes, types, and instances. Harvestable means potentially available for harvesting; harvested means explicitly designated for harvesting. These terms apply to types, instances, and the attributes within those types. In addition, the interface provides access to sampling and snapshot statistics. All statistics are base on data collected during the current server session. "
      ::= { wls 483  }
      
   
   wldfHarvesterRuntimeEntry OBJECT-TYPE
      SYNTAX      WldfHarvesterRuntimeEntry
      MAX-ACCESS  not-accessible
      STATUS      current
      DESCRIPTION "Entry of WLDFHarvesterRuntimeTable"
      INDEX { wldfHarvesterRuntimeIndex}
      ::= { wldfHarvesterRuntimeTable 1 }
      
   WldfHarvesterRuntimeEntry ::=
      SEQUENCE
      {
         wldfHarvesterRuntimeIndex DisplayString,
         wldfHarvesterRuntimeObjectName DisplayString,
         wldfHarvesterRuntimeType DisplayString,
         wldfHarvesterRuntimeName DisplayString,
         wldfHarvesterRuntimeParent DisplayString,
         wldfHarvesterRuntimeSamplePeriod Counter64,
         wldfHarvesterRuntimeTotalSamplingCycles Counter64,
         wldfHarvesterRuntimeMinimumSamplingTime Counter64,
         wldfHarvesterRuntimeMaximumSamplingTime Counter64,
         wldfHarvesterRuntimeTotalSamplingTime Counter64,
         wldfHarvesterRuntimeAverageSamplingTime Counter64,
         wldfHarvesterRuntimeCurrentDataSampleCount Counter64,
         wldfHarvesterRuntimeCurrentSnapshotStartTime Counter64,
         wldfHarvesterRuntimeCurrentSnapshotElapsedTime Counter64,
         wldfHarvesterRuntimeTotalSamplingTimeOutlierCount Counter64,
         wldfHarvesterRuntimeOutlierDetectionFactor OCTET STRING,
         wldfHarvesterRuntimeTotalDataSampleCount Counter64,
         wldfHarvesterRuntimeCurrentSampleTimeAnOutlier OCTET STRING,
         wldfHarvesterRuntimeKnownHarvestableTypes OCTET STRING
      }
      
   
   wldfHarvesterRuntimeIndex OBJECT-TYPE
      SYNTAX      DisplayString (SIZE (1..16))
      MAX-ACCESS  read-only
      STATUS      current
      DESCRIPTION "Unique value directed from ObjectName which is used as table index"
      ::= { wldfHarvesterRuntimeEntry 1  }
   
   
   wldfHarvesterRuntimeObjectName OBJECT-TYPE
      SYNTAX      DisplayString (SIZE (1..256))
      MAX-ACCESS  read-only
      STATUS      current
      DESCRIPTION "JMX-standard MBean name"
      ::= { wldfHarvesterRuntimeEntry 5  }
   
   
   wldfHarvesterRuntimeType OBJECT-TYPE
      SYNTAX      DisplayString (SIZE (1..64))
      MAX-ACCESS  read-only
      STATUS      current
      DESCRIPTION "Returns the type of the MBean. "
      ::= { wldfHarvesterRuntimeEntry 10  }
   
   
   wldfHarvesterRuntimeName OBJECT-TYPE
      SYNTAX      DisplayString (SIZE (1..64))
      MAX-ACCESS  read-only
      STATUS      current
      DESCRIPTION "The name of this configuration. WebLogic Server uses an MBean to implement and persist the configuration. "
      ::= { wldfHarvesterRuntimeEntry 15  }
   
   
   wldfHarvesterRuntimeParent OBJECT-TYPE
      SYNTAX      DisplayString (SIZE (1..256))
      MAX-ACCESS  read-only
      STATUS      current
      DESCRIPTION "BEA-proprietary Parent object's identification, with syntax <type>:<name>"
      ::= { wldfHarvesterRuntimeEntry 20  }
   
   
   wldfHarvesterRuntimeSamplePeriod OBJECT-TYPE
      SYNTAX      Counter64
      MAX-ACCESS  read-only
      STATUS      current
      DESCRIPTION "The current global sample period, in nanoseconds. "
      ::= { wldfHarvesterRuntimeEntry 25  }
   
   
   wldfHarvesterRuntimeTotalSamplingCycles OBJECT-TYPE
      SYNTAX      Counter64
      MAX-ACCESS  read-only
      STATUS      current
      DESCRIPTION " The total number of sampling cycles taken thus far.  "
      ::= { wldfHarvesterRuntimeEntry 30  }
   
   
   wldfHarvesterRuntimeMinimumSamplingTime OBJECT-TYPE
      SYNTAX      Counter64
      MAX-ACCESS  read-only
      STATUS      current
      DESCRIPTION " The minimum sampling time, in nanoseconds.  "
      ::= { wldfHarvesterRuntimeEntry 35  }
   
   
   wldfHarvesterRuntimeMaximumSamplingTime OBJECT-TYPE
      SYNTAX      Counter64
      MAX-ACCESS  read-only
      STATUS      current
      DESCRIPTION " The maximum sampling time, in nanoseconds.  "
      ::= { wldfHarvesterRuntimeEntry 40  }
   
   
   wldfHarvesterRuntimeTotalSamplingTime OBJECT-TYPE
      SYNTAX      Counter64
      MAX-ACCESS  read-only
      STATUS      current
      DESCRIPTION " The total amount of time, in nanoseconds, spent in sampling cycles.  "
      ::= { wldfHarvesterRuntimeEntry 45  }
   
   
   wldfHarvesterRuntimeAverageSamplingTime OBJECT-TYPE
      SYNTAX      Counter64
      MAX-ACCESS  read-only
      STATUS      current
      DESCRIPTION " The average amount of time, in nanoseconds, spent in sampling cycles.  "
      ::= { wldfHarvesterRuntimeEntry 50  }
   
   
   wldfHarvesterRuntimeCurrentDataSampleCount OBJECT-TYPE
      SYNTAX      Counter64
      MAX-ACCESS  read-only
      STATUS      current
      DESCRIPTION " The number of collected data samples in the current snapshot.  "
      ::= { wldfHarvesterRuntimeEntry 55  }
   
   
   wldfHarvesterRuntimeCurrentSnapshotStartTime OBJECT-TYPE
      SYNTAX      Counter64
      MAX-ACCESS  read-only
      STATUS      current
      DESCRIPTION " The start time, in nanoseconds, of a snapshot.  "
      ::= { wldfHarvesterRuntimeEntry 60  }
   
   
   wldfHarvesterRuntimeCurrentSnapshotElapsedTime OBJECT-TYPE
      SYNTAX      Counter64
      MAX-ACCESS  read-only
      STATUS      current
      DESCRIPTION " The elapsed time, in nanoseconds, of a snapshot.  "
      ::= { wldfHarvesterRuntimeEntry 65  }
   
   
   wldfHarvesterRuntimeTotalSamplingTimeOutlierCount OBJECT-TYPE
      SYNTAX      Counter64
      MAX-ACCESS  read-only
      STATUS      current
      DESCRIPTION "The number of times within this server session that the sampling time differed significantly enough from the average to be considered a statistical outlier.  The Harvester removes these values form the ongoing averages. "
      ::= { wldfHarvesterRuntimeEntry 66  }
   
   
   wldfHarvesterRuntimeOutlierDetectionFactor OBJECT-TYPE
      SYNTAX      OCTET STRING
      MAX-ACCESS  read-only
      STATUS      current
      DESCRIPTION "The multiplicative factor used to determine a statistical outlier. If the actual sampling time exceeds this the session average multiplied by the outlier detection factor, then the sampling time is considered to be a statistical outlier. "
      ::= { wldfHarvesterRuntimeEntry 67  }
   
   
   wldfHarvesterRuntimeTotalDataSampleCount OBJECT-TYPE
      SYNTAX      Counter64
      MAX-ACCESS  read-only
      STATUS      current
      DESCRIPTION "The number of configured data samples that have been collected so far in this server session. "
      ::= { wldfHarvesterRuntimeEntry 68  }
   
   
   wldfHarvesterRuntimeCurrentSampleTimeAnOutlier OBJECT-TYPE
      SYNTAX      OCTET STRING
      MAX-ACCESS  read-only
      STATUS      current
      DESCRIPTION "Whether or not the sampling time for the most recent data sample differed significantly enough from the average to be considered a statistical outlier. "
      ::= { wldfHarvesterRuntimeEntry 69  }
   
   
   wldfHarvesterRuntimeKnownHarvestableTypes OBJECT-TYPE
      SYNTAX      OCTET STRING
      MAX-ACCESS  read-only
      STATUS      current
      DESCRIPTION "The set of all known types, regardless of whether the types are currently configured for harvesting. The set includes the WebLogic Server MBeans, which are always present, plus any other types that can be discovered. MBeans that are not WebLogic Server MBeans will require instances to exist in order to discover the type. "
      ::= { wldfHarvesterRuntimeEntry 70  }
   
   
   wldfInstrumentationRuntimeTable OBJECT-TYPE
      SYNTAX      SEQUENCE OF WldfInstrumentationRuntimeEntry
      MAX-ACCESS  not-accessible
      STATUS      current
      DESCRIPTION "This interface defines various methods for accessing runtime information about the diagnostic instrumentation system. "
      ::= { wls 484  }
      
   
   wldfInstrumentationRuntimeEntry OBJECT-TYPE
      SYNTAX      WldfInstrumentationRuntimeEntry
      MAX-ACCESS  not-accessible
      STATUS      current
      DESCRIPTION "Entry of WLDFInstrumentationRuntimeTable"
      INDEX { wldfInstrumentationRuntimeIndex}
      ::= { wldfInstrumentationRuntimeTable 1 }
      
   WldfInstrumentationRuntimeEntry ::=
      SEQUENCE
      {
         wldfInstrumentationRuntimeIndex DisplayString,
         wldfInstrumentationRuntimeObjectName DisplayString,
         wldfInstrumentationRuntimeType DisplayString,
         wldfInstrumentationRuntimeName DisplayString,
         wldfInstrumentationRuntimeParent DisplayString,
         wldfInstrumentationRuntimeInspectedClassesCount INTEGER,
         wldfInstrumentationRuntimeModifiedClassesCount INTEGER,
         wldfInstrumentationRuntimeMinWeavingTime Counter64,
         wldfInstrumentationRuntimeMaxWeavingTime Counter64,
         wldfInstrumentationRuntimeTotalWeavingTime Counter64,
         wldfInstrumentationRuntimeExecutionJoinpointCount INTEGER,
         wldfInstrumentationRuntimeCallJoinpointCount INTEGER,
         wldfInstrumentationRuntimeClassweaveAbortCount INTEGER
      }
      
   
   wldfInstrumentationRuntimeIndex OBJECT-TYPE
      SYNTAX      DisplayString (SIZE (1..16))
      MAX-ACCESS  read-only
      STATUS      current
      DESCRIPTION "Unique value directed from ObjectName which is used as table index"
      ::= { wldfInstrumentationRuntimeEntry 1  }
   
   
   wldfInstrumentationRuntimeObjectName OBJECT-TYPE
      SYNTAX      DisplayString (SIZE (1..256))
      MAX-ACCESS  read-only
      STATUS      current
      DESCRIPTION "JMX-standard MBean name"
      ::= { wldfInstrumentationRuntimeEntry 5  }
   
   
   wldfInstrumentationRuntimeType OBJECT-TYPE
      SYNTAX      DisplayString (SIZE (1..64))
      MAX-ACCESS  read-only
      STATUS      current
      DESCRIPTION "Returns the type of the MBean. "
      ::= { wldfInstrumentationRuntimeEntry 10  }
   
   
   wldfInstrumentationRuntimeName OBJECT-TYPE
      SYNTAX      DisplayString (SIZE (1..64))
      MAX-ACCESS  read-only
      STATUS      current
      DESCRIPTION "The name of this configuration. WebLogic Server uses an MBean to implement and persist the configuration. "
      ::= { wldfInstrumentationRuntimeEntry 15  }
   
   
   wldfInstrumentationRuntimeParent OBJECT-TYPE
      SYNTAX      DisplayString (SIZE (1..256))
      MAX-ACCESS  read-only
      STATUS      current
      DESCRIPTION "BEA-proprietary Parent object's identification, with syntax <type>:<name>"
      ::= { wldfInstrumentationRuntimeEntry 20  }
   
   
   wldfInstrumentationRuntimeInspectedClassesCount OBJECT-TYPE
      SYNTAX      INTEGER
      MAX-ACCESS  read-only
      STATUS      current
      DESCRIPTION "The number of classes inspected for weaving (weaving is the insertion of diagnostic code). "
      ::= { wldfInstrumentationRuntimeEntry 25  }
   
   
   wldfInstrumentationRuntimeModifiedClassesCount OBJECT-TYPE
      SYNTAX      INTEGER
      MAX-ACCESS  read-only
      STATUS      current
      DESCRIPTION "The number of modified classes (classes where diagnostic code has been inserted). "
      ::= { wldfInstrumentationRuntimeEntry 30  }
   
   
   wldfInstrumentationRuntimeMinWeavingTime OBJECT-TYPE
      SYNTAX      Counter64
      MAX-ACCESS  read-only
      STATUS      current
      DESCRIPTION "For all classes, the weaving time in nanoseconds for the class that required the least time to process (includes the time spent both for inspection and for modification). "
      ::= { wldfInstrumentationRuntimeEntry 35  }
   
   
   wldfInstrumentationRuntimeMaxWeavingTime OBJECT-TYPE
      SYNTAX      Counter64
      MAX-ACCESS  read-only
      STATUS      current
      DESCRIPTION "For all classes, the weaving time in nanoseconds for the class that required the most time to process (includes the time spent both for inspection and for modification). "
      ::= { wldfInstrumentationRuntimeEntry 40  }
   
   
   wldfInstrumentationRuntimeTotalWeavingTime OBJECT-TYPE
      SYNTAX      Counter64
      MAX-ACCESS  read-only
      STATUS      current
      DESCRIPTION "For all classes, the total weaving time in nanoseconds for processing (includes the time spent both for inspection and for modification). "
      ::= { wldfInstrumentationRuntimeEntry 45  }
   
   
   wldfInstrumentationRuntimeExecutionJoinpointCount OBJECT-TYPE
      SYNTAX      INTEGER
      MAX-ACCESS  read-only
      STATUS      current
      DESCRIPTION "The number of affected EXECUTION joinpoints for all classes that were inspected. (EXECUTION joinpoints are on the callee side.) "
      ::= { wldfInstrumentationRuntimeEntry 50  }
   
   
   wldfInstrumentationRuntimeCallJoinpointCount OBJECT-TYPE
      SYNTAX      INTEGER
      MAX-ACCESS  read-only
      STATUS      current
      DESCRIPTION "The number of affected CALL joinpoints for all classes that were inspected. (CALL joinpoints are on the caller side.) "
      ::= { wldfInstrumentationRuntimeEntry 55  }
   
   
   wldfInstrumentationRuntimeClassweaveAbortCount OBJECT-TYPE
      SYNTAX      INTEGER
      MAX-ACCESS  read-only
      STATUS      current
      DESCRIPTION "Number of classes for which the class weaving aborted with some exceptional situation. "
      ::= { wldfInstrumentationRuntimeEntry 56  }
   
   
   wldfWatchNotificationRuntimeTable OBJECT-TYPE
      SYNTAX      SEQUENCE OF WldfWatchNotificationRuntimeEntry
      MAX-ACCESS  not-accessible
      STATUS      current
      DESCRIPTION "Provides access to policy and action statistical data for the current instance of this server. Note: As of WebLogic Server 12.2.1, the terms watch and notification are replaced by policy and action, respectively. However, the definition of these terms has not changed. "
      ::= { wls 485  }
      
   
   wldfWatchNotificationRuntimeEntry OBJECT-TYPE
      SYNTAX      WldfWatchNotificationRuntimeEntry
      MAX-ACCESS  not-accessible
      STATUS      current
      DESCRIPTION "Entry of WLDFWatchNotificationRuntimeTable"
      INDEX { wldfWatchNotificationRuntimeIndex}
      ::= { wldfWatchNotificationRuntimeTable 1 }
      
   WldfWatchNotificationRuntimeEntry ::=
      SEQUENCE
      {
         wldfWatchNotificationRuntimeIndex DisplayString,
         wldfWatchNotificationRuntimeObjectName DisplayString,
         wldfWatchNotificationRuntimeType DisplayString,
         wldfWatchNotificationRuntimeName DisplayString,
         wldfWatchNotificationRuntimeParent DisplayString,
         wldfWatchNotificationRuntimeTotalHarvesterEvaluationCycles Counter64,
         wldfWatchNotificationRuntimeTotalHarvesterWatchEvaluations Counter64,
         wldfWatchNotificationRuntimeTotalHarvesterWatchesTriggered Counter64,
         wldfWatchNotificationRuntimeAverageHarvesterWatchEvaluationTime Counter64,
         wldfWatchNotificationRuntimeTotalLogEvaluationCycles Counter64,
         wldfWatchNotificationRuntimeTotalLogWatchEvaluations Counter64,
         wldfWatchNotificationRuntimeTotalLogWatchesTriggered Counter64,
         wldfWatchNotificationRuntimeAverageLogWatchEvaluationTime Counter64,
         wldfWatchNotificationRuntimeTotalEventDataEvaluationCycles Counter64,
         wldfWatchNotificationRuntimeTotalEventDataWatchEvaluations Counter64,
         wldfWatchNotificationRuntimeTotalEventDataWatchesTriggered Counter64,
         wldfWatchNotificationRuntimeAverageEventDataWatchEvaluationTime Counter64,
         wldfWatchNotificationRuntimeCurrentActiveAlarmsCount INTEGER,
         wldfWatchNotificationRuntimeMaximumActiveAlarmsCount INTEGER,
         wldfWatchNotificationRuntimeTotalActiveManualResetAlarms Counter64,
         wldfWatchNotificationRuntimeTotalActiveAutomaticResetAlarms Counter64,
         wldfWatchNotificationRuntimeTotalNotificationsPerformed Counter64,
         wldfWatchNotificationRuntimeTotalDIMGNotificationsPerformed Counter64,
         wldfWatchNotificationRuntimeTotalSNMPNotificationsPerformed Counter64,
         wldfWatchNotificationRuntimeMinimumEventDataWatchEvaluationTime Counter64,
         wldfWatchNotificationRuntimeMinimumHarvesterWatchEvaluationTime Counter64,
         wldfWatchNotificationRuntimeTotalFailedJMXNotifications Counter64,
         wldfWatchNotificationRuntimeTotalJMXNotificationsPerformed Counter64,
         wldfWatchNotificationRuntimeTotalSMTPNotificationsPerformed Counter64,
         wldfWatchNotificationRuntimeTotalJMSNotificationsPerformed Counter64,
         wldfWatchNotificationRuntimeMaximumLogWatchEvaluationTime Counter64,
         wldfWatchNotificationRuntimeTotalFailedJMSNotifications Counter64,
         wldfWatchNotificationRuntimeMinimumLogWatchEvaluationTime Counter64,
         wldfWatchNotificationRuntimeMaximumHarvesterWatchEvaluationTime Counter64,
         wldfWatchNotificationRuntimeTotalFailedDIMGNotifications Counter64,
         wldfWatchNotificationRuntimeMaximumEventDataWatchEvaluationTime Counter64,
         wldfWatchNotificationRuntimeTotalFailedNotifications Counter64,
         wldfWatchNotificationRuntimeTotalFailedSMTPNotifications Counter64,
         wldfWatchNotificationRuntimeTotalFailedSNMPNotifications Counter64,
         wldfWatchNotificationRuntimeActiveAlarmWatches OCTET STRING
      }
      
   
   wldfWatchNotificationRuntimeIndex OBJECT-TYPE
      SYNTAX      DisplayString (SIZE (1..16))
      MAX-ACCESS  read-only
      STATUS      current
      DESCRIPTION "Unique value directed from ObjectName which is used as table index"
      ::= { wldfWatchNotificationRuntimeEntry 1  }
   
   
   wldfWatchNotificationRuntimeObjectName OBJECT-TYPE
      SYNTAX      DisplayString (SIZE (1..256))
      MAX-ACCESS  read-only
      STATUS      current
      DESCRIPTION "JMX-standard MBean name"
      ::= { wldfWatchNotificationRuntimeEntry 5  }
   
   
   wldfWatchNotificationRuntimeType OBJECT-TYPE
      SYNTAX      DisplayString (SIZE (1..64))
      MAX-ACCESS  read-only
      STATUS      current
      DESCRIPTION "Returns the type of the MBean. "
      ::= { wldfWatchNotificationRuntimeEntry 10  }
   
   
   wldfWatchNotificationRuntimeName OBJECT-TYPE
      SYNTAX      DisplayString (SIZE (1..64))
      MAX-ACCESS  read-only
      STATUS      current
      DESCRIPTION "The name of this configuration. WebLogic Server uses an MBean to implement and persist the configuration. "
      ::= { wldfWatchNotificationRuntimeEntry 15  }
   
   
   wldfWatchNotificationRuntimeParent OBJECT-TYPE
      SYNTAX      DisplayString (SIZE (1..256))
      MAX-ACCESS  read-only
      STATUS      current
      DESCRIPTION "BEA-proprietary Parent object's identification, with syntax <type>:<name>"
      ::= { wldfWatchNotificationRuntimeEntry 20  }
   
   
   wldfWatchNotificationRuntimeTotalHarvesterEvaluationCycles OBJECT-TYPE
      SYNTAX      Counter64
      MAX-ACCESS  read-only
      STATUS      current
      DESCRIPTION "The total number of times the Harvester has invoked the Policy and Action component to evaluate Harvester policies. (This number corresponds to the number of sampling cycles.) "
      ::= { wldfWatchNotificationRuntimeEntry 25  }
   
   
   wldfWatchNotificationRuntimeTotalHarvesterWatchEvaluations OBJECT-TYPE
      SYNTAX      Counter64
      MAX-ACCESS  read-only
      STATUS      current
      DESCRIPTION "The total number of Harvester policies that have been evaluated. For each cycle, the Policy and Action component evaluates all of the enabled Harvester policies. "
      ::= { wldfWatchNotificationRuntimeEntry 30  }
   
   
   wldfWatchNotificationRuntimeTotalHarvesterWatchesTriggered OBJECT-TYPE
      SYNTAX      Counter64
      MAX-ACCESS  read-only
      STATUS      current
      DESCRIPTION "The total number of Harvester policies that have evaluated to true and triggered actions.  "
      ::= { wldfWatchNotificationRuntimeEntry 35  }
   
   
   wldfWatchNotificationRuntimeAverageHarvesterWatchEvaluationTime OBJECT-TYPE
      SYNTAX      Counter64
      MAX-ACCESS  read-only
      STATUS      current
      DESCRIPTION "The average Harvester evaluation cycle time, in milliseconds. "
      ::= { wldfWatchNotificationRuntimeEntry 40  }
   
   
   wldfWatchNotificationRuntimeTotalLogEvaluationCycles OBJECT-TYPE
      SYNTAX      Counter64
      MAX-ACCESS  read-only
      STATUS      current
      DESCRIPTION "The total number of times Log policies have been evaluated. "
      ::= { wldfWatchNotificationRuntimeEntry 45  }
   
   
   wldfWatchNotificationRuntimeTotalLogWatchEvaluations OBJECT-TYPE
      SYNTAX      Counter64
      MAX-ACCESS  read-only
      STATUS      current
      DESCRIPTION "The total number of Log policies that have been evaluated. For each cycle, the Policy and Action component evaluates all of the enabled Log policies. "
      ::= { wldfWatchNotificationRuntimeEntry 50  }
   
   
   wldfWatchNotificationRuntimeTotalLogWatchesTriggered OBJECT-TYPE
      SYNTAX      Counter64
      MAX-ACCESS  read-only
      STATUS      current
      DESCRIPTION "The total number of Log policies that have evaluated to true and triggered actions.  "
      ::= { wldfWatchNotificationRuntimeEntry 55  }
   
   
   wldfWatchNotificationRuntimeAverageLogWatchEvaluationTime OBJECT-TYPE
      SYNTAX      Counter64
      MAX-ACCESS  read-only
      STATUS      current
      DESCRIPTION "The average Log evaluation cycle time, in milliseconds. "
      ::= { wldfWatchNotificationRuntimeEntry 60  }
   
   
   wldfWatchNotificationRuntimeTotalEventDataEvaluationCycles OBJECT-TYPE
      SYNTAX      Counter64
      MAX-ACCESS  read-only
      STATUS      current
      DESCRIPTION "The total number of times Instrumentation event data policies have been evaluated. "
      ::= { wldfWatchNotificationRuntimeEntry 65  }
   
   
   wldfWatchNotificationRuntimeTotalEventDataWatchEvaluations OBJECT-TYPE
      SYNTAX      Counter64
      MAX-ACCESS  read-only
      STATUS      current
      DESCRIPTION "The total number of Instrumentation event data policies that have been evaluated. For each cycle, the Policy and Action component evaluates all of the enabled Instrumentation event data policies. "
      ::= { wldfWatchNotificationRuntimeEntry 70  }
   
   
   wldfWatchNotificationRuntimeTotalEventDataWatchesTriggered OBJECT-TYPE
      SYNTAX      Counter64
      MAX-ACCESS  read-only
      STATUS      current
      DESCRIPTION "The total number of Instrumentation event data policies that have evaluated to true and triggered actions. "
      ::= { wldfWatchNotificationRuntimeEntry 75  }
   
   
   wldfWatchNotificationRuntimeAverageEventDataWatchEvaluationTime OBJECT-TYPE
      SYNTAX      Counter64
      MAX-ACCESS  read-only
      STATUS      current
      DESCRIPTION "The average Instrumentation event data evaluation cycle time, in milliseconds. "
      ::= { wldfWatchNotificationRuntimeEntry 80  }
   
   
   wldfWatchNotificationRuntimeCurrentActiveAlarmsCount OBJECT-TYPE
      SYNTAX      INTEGER
      MAX-ACCESS  read-only
      STATUS      current
      DESCRIPTION "The number of active alarms of any type. "
      ::= { wldfWatchNotificationRuntimeEntry 85  }
   
   
   wldfWatchNotificationRuntimeMaximumActiveAlarmsCount OBJECT-TYPE
      SYNTAX      INTEGER
      MAX-ACCESS  read-only
      STATUS      current
      DESCRIPTION "The maximum number of active alarms at any one time. "
      ::= { wldfWatchNotificationRuntimeEntry 90  }
   
   
   wldfWatchNotificationRuntimeTotalActiveManualResetAlarms OBJECT-TYPE
      SYNTAX      Counter64
      MAX-ACCESS  read-only
      STATUS      current
      DESCRIPTION "The total number of active manually reset alarms. "
      ::= { wldfWatchNotificationRuntimeEntry 95  }
   
   
   wldfWatchNotificationRuntimeTotalActiveAutomaticResetAlarms OBJECT-TYPE
      SYNTAX      Counter64
      MAX-ACCESS  read-only
      STATUS      current
      DESCRIPTION "The total number of active automatically reset alarms. "
      ::= { wldfWatchNotificationRuntimeEntry 100  }
   
   
   wldfWatchNotificationRuntimeTotalNotificationsPerformed OBJECT-TYPE
      SYNTAX      Counter64
      MAX-ACCESS  read-only
      STATUS      current
      DESCRIPTION "The total number of actions performed. "
      ::= { wldfWatchNotificationRuntimeEntry 105  }
   
   
   wldfWatchNotificationRuntimeTotalDIMGNotificationsPerformed OBJECT-TYPE
      SYNTAX      Counter64
      MAX-ACCESS  read-only
      STATUS      current
      DESCRIPTION "The total number of Diagnostic Image actions fired.  Diagnostic Image files are not true actions, but this records the number of image captures requested by the policy component. "
      ::= { wldfWatchNotificationRuntimeEntry 106  }
   
   
   wldfWatchNotificationRuntimeTotalSNMPNotificationsPerformed OBJECT-TYPE
      SYNTAX      Counter64
      MAX-ACCESS  read-only
      STATUS      current
      DESCRIPTION "The total number of SNMP actions successfully fired. "
      ::= { wldfWatchNotificationRuntimeEntry 107  }
   
   
   wldfWatchNotificationRuntimeMinimumEventDataWatchEvaluationTime OBJECT-TYPE
      SYNTAX      Counter64
      MAX-ACCESS  read-only
      STATUS      current
      DESCRIPTION "The minimum time spent evaluating Log policies. "
      ::= { wldfWatchNotificationRuntimeEntry 108  }
   
   
   wldfWatchNotificationRuntimeMinimumHarvesterWatchEvaluationTime OBJECT-TYPE
      SYNTAX      Counter64
      MAX-ACCESS  read-only
      STATUS      current
      DESCRIPTION "The minimum time spent evaluating Harvester policies. "
      ::= { wldfWatchNotificationRuntimeEntry 109  }
   
   
   wldfWatchNotificationRuntimeTotalFailedJMXNotifications OBJECT-TYPE
      SYNTAX      Counter64
      MAX-ACCESS  read-only
      STATUS      current
      DESCRIPTION "The total number of failed JMX action attempts. "
      ::= { wldfWatchNotificationRuntimeEntry 110  }
   
   
   wldfWatchNotificationRuntimeTotalJMXNotificationsPerformed OBJECT-TYPE
      SYNTAX      Counter64
      MAX-ACCESS  read-only
      STATUS      current
      DESCRIPTION "The total number of JMX actions successfully fired. "
      ::= { wldfWatchNotificationRuntimeEntry 111  }
   
   
   wldfWatchNotificationRuntimeTotalSMTPNotificationsPerformed OBJECT-TYPE
      SYNTAX      Counter64
      MAX-ACCESS  read-only
      STATUS      current
      DESCRIPTION "The total number of SMTP actions successfully fired. "
      ::= { wldfWatchNotificationRuntimeEntry 112  }
   
   
   wldfWatchNotificationRuntimeTotalJMSNotificationsPerformed OBJECT-TYPE
      SYNTAX      Counter64
      MAX-ACCESS  read-only
      STATUS      current
      DESCRIPTION "The total number of JMS actions successfully fired. "
      ::= { wldfWatchNotificationRuntimeEntry 113  }
   
   
   wldfWatchNotificationRuntimeMaximumLogWatchEvaluationTime OBJECT-TYPE
      SYNTAX      Counter64
      MAX-ACCESS  read-only
      STATUS      current
      DESCRIPTION "The maximum time spent evaluating Log policies. "
      ::= { wldfWatchNotificationRuntimeEntry 114  }
   
   
   wldfWatchNotificationRuntimeTotalFailedJMSNotifications OBJECT-TYPE
      SYNTAX      Counter64
      MAX-ACCESS  read-only
      STATUS      current
      DESCRIPTION "The total number of failed JMS action attempts. "
      ::= { wldfWatchNotificationRuntimeEntry 115  }
   
   
   wldfWatchNotificationRuntimeMinimumLogWatchEvaluationTime OBJECT-TYPE
      SYNTAX      Counter64
      MAX-ACCESS  read-only
      STATUS      current
      DESCRIPTION "The minimum time spent evaluating Log policies. "
      ::= { wldfWatchNotificationRuntimeEntry 116  }
   
   
   wldfWatchNotificationRuntimeMaximumHarvesterWatchEvaluationTime OBJECT-TYPE
      SYNTAX      Counter64
      MAX-ACCESS  read-only
      STATUS      current
      DESCRIPTION "The maximum time spent evaluating Harvester policies. "
      ::= { wldfWatchNotificationRuntimeEntry 117  }
   
   
   wldfWatchNotificationRuntimeTotalFailedDIMGNotifications OBJECT-TYPE
      SYNTAX      Counter64
      MAX-ACCESS  read-only
      STATUS      current
      DESCRIPTION "The total number of failed Diagnostic Image action requests. "
      ::= { wldfWatchNotificationRuntimeEntry 118  }
   
   
   wldfWatchNotificationRuntimeMaximumEventDataWatchEvaluationTime OBJECT-TYPE
      SYNTAX      Counter64
      MAX-ACCESS  read-only
      STATUS      current
      DESCRIPTION "The maximum time spent evaluating EventData policies. "
      ::= { wldfWatchNotificationRuntimeEntry 119  }
   
   
   wldfWatchNotificationRuntimeTotalFailedNotifications OBJECT-TYPE
      SYNTAX      Counter64
      MAX-ACCESS  read-only
      STATUS      current
      DESCRIPTION "The total number of failed action requests. "
      ::= { wldfWatchNotificationRuntimeEntry 120  }
   
   
   wldfWatchNotificationRuntimeTotalFailedSMTPNotifications OBJECT-TYPE
      SYNTAX      Counter64
      MAX-ACCESS  read-only
      STATUS      current
      DESCRIPTION "The total number of failed SMTP action attempts. "
      ::= { wldfWatchNotificationRuntimeEntry 121  }
   
   
   wldfWatchNotificationRuntimeTotalFailedSNMPNotifications OBJECT-TYPE
      SYNTAX      Counter64
      MAX-ACCESS  read-only
      STATUS      current
      DESCRIPTION "The total number of failed SNMP action attempts. "
      ::= { wldfWatchNotificationRuntimeEntry 122  }
   
   
   wldfWatchNotificationRuntimeActiveAlarmWatches OBJECT-TYPE
      SYNTAX      OCTET STRING
      MAX-ACCESS  read-only
      STATUS      current
      DESCRIPTION "The names of active alarm policies. "
      ::= { wldfWatchNotificationRuntimeEntry 123  }
   
   
   bridgeDestinationCommonTable OBJECT-TYPE
      SYNTAX      SEQUENCE OF BridgeDestinationCommonEntry
      MAX-ACCESS  not-accessible
      STATUS      current
      DESCRIPTION "This MBean represents a bridge destination for a messaging bridge instance. Each messaging bridge instance consists of the following destination types:    Source: The message producing destination. A bridge instance consumes messages from the source destination.    Target: The destination where a bridge instance forwards messages produced by the source destination.   "
      ::= { wls 505  }
      
   
   bridgeDestinationCommonEntry OBJECT-TYPE
      SYNTAX      BridgeDestinationCommonEntry
      MAX-ACCESS  not-accessible
      STATUS      current
      DESCRIPTION "Entry of bridgeDestinationCommonTable"
      INDEX { bridgeDestinationCommonIndex}
      ::= { bridgeDestinationCommonTable 1 }
      
   BridgeDestinationCommonEntry ::=
      SEQUENCE
      {
         bridgeDestinationCommonIndex DisplayString,
         bridgeDestinationCommonObjectName DisplayString,
         bridgeDestinationCommonType DisplayString,
         bridgeDestinationCommonName DisplayString,
         bridgeDestinationCommonParent DisplayString,
         bridgeDestinationCommonAdapterJNDIName DisplayString,
         bridgeDestinationCommonClasspath DisplayString,
         bridgeDestinationCommonUserName DisplayString,
         bridgeDestinationCommonTags OCTET STRING
      }
      
   
   bridgeDestinationCommonIndex OBJECT-TYPE
      SYNTAX      DisplayString (SIZE (1..16))
      MAX-ACCESS  read-only
      STATUS      current
      DESCRIPTION "Unique value directed from ObjectName which is used as table index"
      ::= { bridgeDestinationCommonEntry 1  }
   
   
   bridgeDestinationCommonObjectName OBJECT-TYPE
      SYNTAX      DisplayString (SIZE (1..256))
      MAX-ACCESS  read-only
      STATUS      current
      DESCRIPTION "JMX-standard MBean name"
      ::= { bridgeDestinationCommonEntry 5  }
   
   
   bridgeDestinationCommonType OBJECT-TYPE
      SYNTAX      DisplayString (SIZE (1..64))
      MAX-ACCESS  read-only
      STATUS      current
      DESCRIPTION "Returns the type of the MBean. "
      ::= { bridgeDestinationCommonEntry 10  }
   
   
   bridgeDestinationCommonName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { bridgeDestinationCommonEntry 15  }
   
   
   bridgeDestinationCommonParent OBJECT-TYPE
      SYNTAX      DisplayString (SIZE (1..256))
      MAX-ACCESS  read-only
      STATUS      current
      DESCRIPTION "BEA-proprietary Parent object's identification, with syntax
      <type>:<name>"
      ::= { bridgeDestinationCommonEntry 20  }
   
   
   bridgeDestinationCommonAdapterJNDIName OBJECT-TYPE
      SYNTAX      DisplayString
      MAX-ACCESS  read-only
      STATUS      current
      DESCRIPTION "The JNDI name of the adapter used to communicate with the specified destination.  This name is specified in the adapter's deployment descriptor file and is used by the WebLogic Server Connector container to bind the adapter in WebLogic Server JNDI. "
      ::= { bridgeDestinationCommonEntry 21  }
   
   
   bridgeDestinationCommonClasspath OBJECT-TYPE
      SYNTAX      DisplayString
      MAX-ACCESS  read-only
      STATUS      current
      DESCRIPTION "The CLASSPATH of the bridge destination.    Used mainly to connect to WebLogic Server 6.0 or earlier.    When connecting to a destination that is running on WebLogic Server 6.0 or earlier, the bridge destination must supply a CLASSPATH that indicates the locations of the classes for the earlier WebLogic Server implementation.    "
      ::= { bridgeDestinationCommonEntry 22  }
   
   
   bridgeDestinationCommonUserName OBJECT-TYPE
      SYNTAX      DisplayString
      MAX-ACCESS  read-only
      STATUS      current
      DESCRIPTION "The optional user name the adapter uses to access the bridge destination.  All operations on the specified destination are done using this user name and the corresponding password. Therefore, the User Name/Password for the source and target destinations must have permission to the access the underlying destinations in order for the messaging bridge to work. "
      ::= { bridgeDestinationCommonEntry 23  }
   
   
   bridgeDestinationCommonTags OBJECT-TYPE
      SYNTAX      OCTET STRING
      MAX-ACCESS  read-only
      STATUS      current
      DESCRIPTION "Return all tags on this Configuration MBean "
      ::= { bridgeDestinationCommonEntry 24  }
   
   
   clusterTable OBJECT-TYPE
      SYNTAX      SEQUENCE OF ClusterEntry
      MAX-ACCESS  not-accessible
      STATUS      current
      DESCRIPTION "This bean represents a cluster in the domain. Servers join a cluster by calling ServerMBean.setCluster with the logical name of the cluster. A configuration may define zero or more clusters. They may be looked up by logical name.  The name of a cluster denotes its logical cluster name. "
      ::= { wls 510  }
      
   
   clusterEntry OBJECT-TYPE
      SYNTAX      ClusterEntry
      MAX-ACCESS  not-accessible
      STATUS      current
      DESCRIPTION "Entry of clusterTable"
      INDEX { clusterIndex}
      ::= { clusterTable 1 }
      
   ClusterEntry ::=
      SEQUENCE
      {
         clusterIndex         DisplayString,
         clusterObjectName    DisplayString,
         clusterType          DisplayString,
         clusterName          DisplayString,
         clusterParent        DisplayString,
         clusterClusterAddress DisplayString,
         clusterMulticastAddress DisplayString,
         clusterMulticastTTL  INTEGER,
         clusterMulticastSendDelay INTEGER,
         clusterDefaultLoadAlgorithm DisplayString,
         clusterServiceAgeThresholdSeconds INTEGER,
         clusterMulticastBufferSize INTEGER,
         clusterMulticastPort INTEGER,
         clusterClientCertProxyEnabled INTEGER,
         clusterWeblogicPluginEnabled INTEGER,
         clusterHealthCheckIntervalMillis INTEGER,
         clusterHealthCheckPeriodsUntilFencing INTEGER,
         clusterSessionFlushInterval INTEGER,
         clusterAdditionalAutoMigrationAttempts INTEGER,
         clusterRemoteClusterAddress OCTET STRING,
         clusterFrontendHTTPPort INTEGER,
         clusterMulticastDataEncryption OCTET STRING,
         clusterSecureReplicationEnabled OCTET STRING,
         clusterJobSchedulerTableName OCTET STRING,
         clusterReplicationTimeoutEnabled OCTET STRING,
         clusterAsyncSessionQueueTimeout INTEGER,
         clusterInterClusterCommLinkHealthCheckInterval INTEGER,
         clusterSessionFlushThreshold INTEGER,
         clusterClusterType   OCTET STRING,
         clusterGreedySessionFlushInterval INTEGER,
         clusterPersistSessionsOnShutdown OCTET STRING,
         clusterMigrationBasis OCTET STRING,
         clusterHttpTraceSupportEnabled OCTET STRING,
         clusterReplicationChannel OCTET STRING,
         clusterFencingGracePeriodMillis INTEGER,
         clusterFrontendHost  OCTET STRING,
         clusterMemberWarmupTimeoutSeconds INTEGER,
         clusterFrontendHTTPSPort INTEGER,
         clusterClusterBroadcastChannel OCTET STRING,
         clusterIdlePeriodsUntilTimeout INTEGER,
         clusterNumberOfServersInClusterAddress INTEGER,
         clusterClusterMessagingMode OCTET STRING,
         clusterMillisToSleepBetweenAutoMigrationAttempts Counter64,
         clusterAutoMigrationTableName OCTET STRING,
         clusterWANSessionPersistenceTableName OCTET STRING,
         clusterOneWayRmiForReplicationEnabled OCTET STRING,
         clusterMessageOrderingEnabled OCTET STRING,
         clusterSessionLazyDeserializationEnabled OCTET STRING,
         clusterMemberDeathDetectorEnabled OCTET STRING,
         clusterTxnAffinityEnabled OCTET STRING,
         clusterDatabaseLeasingBasisConnectionRetryDelay Counter64,
         clusterDatabaseLeasingBasisConnectionRetryCount INTEGER,
         clusterServiceActivationRequestResponseTimeout INTEGER,
         clusterTags          OCTET STRING,
         clusterSessionStateQueryProtocolEnabled OCTET STRING,
         clusterSessionStateQueryRequestTimeout INTEGER,
         clusterSiteName      OCTET STRING,
         clusterSingletonServiceRequestTimeout INTEGER,
         clusterConcurrentSingletonActivationEnabled OCTET STRING,
         clusterUnicastReadTimeout INTEGER
      }
      
   
   clusterIndex OBJECT-TYPE
      SYNTAX      DisplayString (SIZE (1..16))
      MAX-ACCESS  read-only
      STATUS      current
      DESCRIPTION "Unique value directed from ObjectName which is used as table index"
      ::= { clusterEntry 1  }
   
   
   clusterObjectName OBJECT-TYPE
      SYNTAX      DisplayString (SIZE (1..256))
      MAX-ACCESS  read-only
      STATUS      current
      DESCRIPTION "JMX-standard MBean name"
      ::= { clusterEntry 5  }
   
   
   clusterType OBJECT-TYPE
      SYNTAX      DisplayString (SIZE (1..64))
      MAX-ACCESS  read-only
      STATUS      current
      DESCRIPTION "Returns the type of the MBean. "
      ::= { clusterEntry 10  }
   
   
   clusterName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { clusterEntry 15  }
   
   
   clusterParent OBJECT-TYPE
      SYNTAX      DisplayString (SIZE (1..256))
      MAX-ACCESS  read-only
      STATUS      current
      DESCRIPTION "BEA-proprietary Parent object's identification, with syntax
      <type>:<name>"
      ::= { clusterEntry 20  }
   
   
   clusterClusterAddress OBJECT-TYPE
      SYNTAX      DisplayString (SIZE (1..256))
      MAX-ACCESS  read-only
      STATUS      current
      DESCRIPTION "The address that forms a portion of the URL a client uses to connect to this cluster, and that is used for generating EJB handles and entity EJB failover addresses. (This address may be either a DNS host name that maps to multiple IP addresses or a comma-separated list of single address host names or IP addresses.)  Defines the address to be used by clients to connect to this cluster. This address may be either a DNS host name that maps to multiple IP addresses or a comma separated list of single address host names or IP addresses. If network channels are configured, it is possible to set the cluster address on a per channel basis. "
      ::= { clusterEntry 30  }
   
   
   clusterMulticastAddress OBJECT-TYPE
      SYNTAX      DisplayString (SIZE (1..256))
      MAX-ACCESS  read-only
      STATUS      current
      DESCRIPTION "The multicast address used by cluster members to communicate with each other.  The valid range is from from 224.0.0.0 to 239.255.255.255. The default value used by WebLogic Server is 239.192.0.0.  You should avoid using multicast addresses in the range x.0.0.1  This address should be unique to this cluster and should not be shared by other applications. "
      ::= { clusterEntry 35  }
   
   
   clusterMulticastTTL OBJECT-TYPE
      SYNTAX      INTEGER
      MAX-ACCESS  read-only
      STATUS      current
      DESCRIPTION "The number of network hops (between 1 and 255) that a cluster multicast message is allowed to travel.  Defines the number of network hops that a cluster multicast message is allowed to travel. 1 restricts the cluster to one subnet. "
      ::= { clusterEntry 40  }
   
   
   clusterMulticastSendDelay OBJECT-TYPE
      SYNTAX      INTEGER
      MAX-ACCESS  read-only
      STATUS      current
      DESCRIPTION "The amount of time (between 0 and 250 milliseconds) to delay sending message fragments over multicast in order to avoid OS-level buffer overflow.  Defines the number of milliseconds to delay sending message fragments over multicast in order to avoid OS-level buffer overflow. "
      ::= { clusterEntry 45  }
   
   
   clusterDefaultLoadAlgorithm OBJECT-TYPE
      SYNTAX      DisplayString (SIZE (1..32))
      MAX-ACCESS  read-only
      STATUS      current
      DESCRIPTION "Defines the algorithm to be used for load-balancing between replicated services if none is specified for a particular service. The round-robin algorithm cycles through a list of WebLogic Server instances in order. Weight-based load balancing improves on the round-robin algorithm by taking into account a pre-assigned weight for each server. In random load balancing, requests are routed to servers at random. "
      ::= { clusterEntry 50  }
   
   
   clusterServiceAgeThresholdSeconds OBJECT-TYPE
      SYNTAX      INTEGER
      MAX-ACCESS  read-only
      STATUS      current
      DESCRIPTION "The number of seconds (between 0 and 65534) by which the age of two conflicting services must differ before one is considered older than the other.  Defines the number of seconds by which the age of two conflicting services must differ before one is considered older than the other. "
      ::= { clusterEntry 55  }
   
   
   clusterMulticastBufferSize OBJECT-TYPE
      SYNTAX      INTEGER
      MAX-ACCESS  read-only
      STATUS      current
      DESCRIPTION "The multicast socket send/receive buffer size (at least 64 kilobytes).  Returns the multicast socket send/receive buffer size. "
      ::= { clusterEntry 56  }
   
   
   clusterMulticastPort OBJECT-TYPE
      SYNTAX      INTEGER
      MAX-ACCESS  read-only
      STATUS      current
      DESCRIPTION "The multicast port (between 1 and 65535) used by cluster members to communicate with each other.  Defines the multicast port used by cluster members to communicate with each other. "
      ::= { clusterEntry 57  }
   
   
   clusterClientCertProxyEnabled OBJECT-TYPE
      SYNTAX      INTEGER
      MAX-ACCESS  read-only
      STATUS      current
      DESCRIPTION "Specifies whether to honor the WL-Proxy-Client-Cert header coming with the request or not.  "
      ::= { clusterEntry 58  }
   
   
   clusterWeblogicPluginEnabled OBJECT-TYPE
      SYNTAX      INTEGER
      MAX-ACCESS  read-only
      STATUS      current
      DESCRIPTION "Specifies if this cluster will receive requests from a proxy plug-in or HttpClusterServlet.  Set this attribute to true if the cluster will receive requests from a proxy plug-in or HttpClusterServlet. A call to getRemoteAddr will return the address of the browser client from the proprietary WL-Proxy-Client-IP header instead of the Web server.  Set this attribute to false to disable the weblogic-plugin-enabled parameter, weblogic-plugin-enabled=false, in the config.xmlfile.  Note: If you are using Oracle HTTP Server, the WebLogic Proxy Plug-In, or Oracle Traffic Director to distribute client requests to a Managed Server or a cluster, Oracle recommends setting this attribute to true. "
      ::= { clusterEntry 59  }
   
   
   clusterHealthCheckIntervalMillis OBJECT-TYPE
      SYNTAX      INTEGER
      MAX-ACCESS  read-only
      STATUS      current
      DESCRIPTION "Interval in milliseconds at which Migratable Servers and Cluster Masters prove their liveness via the database. "
      ::= { clusterEntry 60  }
   
   
   clusterHealthCheckPeriodsUntilFencing OBJECT-TYPE
      SYNTAX      INTEGER
      MAX-ACCESS  read-only
      STATUS      current
      DESCRIPTION "Maximum number of periods that a cluster member will wait before timing out a Cluster Master and also the maximum number of periods the Cluster Master will wait before timing out a Migratable Server. "
      ::= { clusterEntry 61  }
   
   
   clusterSessionFlushInterval OBJECT-TYPE
      SYNTAX      INTEGER
      MAX-ACCESS  read-only
      STATUS      current
      DESCRIPTION "Interval in seconds until HTTP Sessions are periodically flushed to the backup cluster to dump session state on disk. "
      ::= { clusterEntry 62  }
   
   
   clusterAdditionalAutoMigrationAttempts OBJECT-TYPE
      SYNTAX      INTEGER
      MAX-ACCESS  read-only
      STATUS      current
      DESCRIPTION "A migratable server could fail to come up on every possible configured machine. This attribute controls how many further attempts, after the first one, should be tried.  Note that each attempt specified here indicates another full circuit of migrations amongst all the configured machines. So for a 3-server cluster, and the default value of 3, a total of 9 migrations will be attempted.  If it is set to -1, migrations will go on forever until the server starts. "
      ::= { clusterEntry 63  }
   
   
   clusterRemoteClusterAddress OBJECT-TYPE
      SYNTAX      OCTET STRING
      MAX-ACCESS  read-only
      STATUS      current
      DESCRIPTION "Set the foreign cluster. Cluster infrastructure uses this address to connect to foreign cluster for HTTP Session WAN/MAN failover. "
      ::= { clusterEntry 64  }
   
   
   clusterFrontendHTTPPort OBJECT-TYPE
      SYNTAX      INTEGER
      MAX-ACCESS  read-only
      STATUS      current
      DESCRIPTION "The name of the HTTP port to which all redirected URLs will be sent.  Sets the FrontendHTTPPort for the default webserver (not virtual hosts) for all the servers in the cluster. Provides a method to ensure that the webapp will always have the correct PORT information, even when the request is coming through a firewall or a proxy. If this parameter is configured, the HOST header will be ignored and the information in this parameter will be used in its place, when constructing the absolute urls for redirects. "
      ::= { clusterEntry 65  }
   
   
   clusterMulticastDataEncryption OBJECT-TYPE
      SYNTAX      OCTET STRING
      MAX-ACCESS  read-only
      STATUS      current
      DESCRIPTION "Enables multicast data to be encrypted. Only the multicast data is encrypted. Multicast header information is not encrypted. "
      ::= { clusterEntry 66  }
   
   
   clusterSecureReplicationEnabled OBJECT-TYPE
      SYNTAX      OCTET STRING
      MAX-ACCESS  read-only
      STATUS      current
      DESCRIPTION "Servers in a cluster replicate session data. If a replication channel is defined then the session data will be sent using the replication channel protocol and secured replication settings will be ignored. If no replication channel is defined and secured replication is enabled then session data for in-memory replication will be sent over SSL using the default secured channel. However, this added security for replication traffic comes with a significant cluster performance degradation. It should only be enabled if security is of greater concern than performance degradation. "
      ::= { clusterEntry 67  }
   
   
   clusterJobSchedulerTableName OBJECT-TYPE
      SYNTAX      OCTET STRING
      MAX-ACCESS  read-only
      STATUS      current
      DESCRIPTION "The table name to use for storing timers active with the job scheduler "
      ::= { clusterEntry 68  }
   
   
   clusterReplicationTimeoutEnabled OBJECT-TYPE
      SYNTAX      OCTET STRING
      MAX-ACCESS  read-only
      STATUS      current
      DESCRIPTION "Indicates if timeout should be applied to session replication calls. "
      ::= { clusterEntry 69  }
   
   
   clusterAsyncSessionQueueTimeout OBJECT-TYPE
      SYNTAX      INTEGER
      MAX-ACCESS  read-only
      STATUS      current
      DESCRIPTION "Interval in seconds until the producer thread will wait for the AsyncSessionQueue to become unblocked.  Should be similar to the RequestTimeOut as that will determine the longest that the queue should remain full. "
      ::= { clusterEntry 70  }
   
   
   clusterInterClusterCommLinkHealthCheckInterval OBJECT-TYPE
      SYNTAX      INTEGER
      MAX-ACCESS  read-only
      STATUS      current
      DESCRIPTION "If the cluster link between two clusters goes down, a trigger will run periodically to see if the link is restored. The duration is specified in milliseconds. "
      ::= { clusterEntry 71  }
   
   
   clusterSessionFlushThreshold OBJECT-TYPE
      SYNTAX      INTEGER
      MAX-ACCESS  read-only
      STATUS      current
      DESCRIPTION "When number of sessions to be flushed reaches this threshold limit, sessions will be flushed to the backup cluster before the flush interval. This helps the server to flush sessions faster under load. "
      ::= { clusterEntry 72  }
   
   
   clusterClusterType OBJECT-TYPE
      SYNTAX      OCTET STRING
      MAX-ACCESS  read-only
      STATUS      current
      DESCRIPTION "Optimizes cross-cluster replication for the type of network that servers in the clusters use for administrative communication.  To enhance the reliability of HTTP sessions, you can configure servers in one cluster to replicate the session data to servers in a different cluster. In such an environment, configure the clusters to be one of the following types:   man If the clustered servers can send their data through a metro area network (man) in which latency is negligible. With this ClusterType value, servers replicate session state synchronously and in memory only. For example, when serverA in cluster1 starts an HTTP session, its backup server, serverB in cluster2, immediately replicates this session in memory to Server B.   wan If the clusters are far apart or send their data through a wide area network (wan) that experiences significant network latency. With this ClusterType value, a server replicates session state synchronously to the backup server in the same cluster and asynchronously to a server in the remote cluster. For example, when serverA in cluster1 starts an HTTP session, it sends the data to serverB in cluster1 and then asynchronously sends data to serverX in cluster 2. ServerX will persist the session state in the database.  If you persist session data in a replicating database, and if you prefer to use the database to replicate the data instead of WebLogic Server, choose a cluster type of wan and leave the remote cluster address undefined. WebLogic Server saves the session data to the local database and assumes that the database replicates data as needed.   "
      ::= { clusterEntry 73  }
   
   
   clusterGreedySessionFlushInterval OBJECT-TYPE
      SYNTAX      INTEGER
      MAX-ACCESS  read-only
      STATUS      current
      DESCRIPTION "Interval in seconds until HTTP Sessions are periodically flushed to secondary server. "
      ::= { clusterEntry 74  }
   
   
   clusterPersistSessionsOnShutdown OBJECT-TYPE
      SYNTAX      OCTET STRING
      MAX-ACCESS  read-only
      STATUS      current
      DESCRIPTION "When shutting down servers, sessions are not updated. If the primary and secondary servers of a session are shut down with no session updates, the session will be lost. Turning on PersistSessionsOnShutdown will save any active sessions to the database specified in {@link ClusterMBean#getDataSourceForSessionPersistence()} when a server is shutdown. The sessions will not be written at any other time. (For example, they are not saved via this mechanism if there is a server crash.)  This attribute is applicable both to session persistence on server shutdown or session persistence across a WAN.  Rolling upgrade can potentially have a bad interaction with traditional in-memory session replication.  As managed servers are shutdown and upgraded, in-memory servlet sessions will be lost if both primary and secondary are rebooted before a new request arrives for the session. "
      ::= { clusterEntry 75  }
   
   
   clusterMigrationBasis OBJECT-TYPE
      SYNTAX      OCTET STRING
      MAX-ACCESS  read-only
      STATUS      current
      DESCRIPTION "Controls the mechanism used for server and service migration.   Database -- Requires the availability of a high-availability database, such as Oracle RAC, to store leasing information.  Consensus -- Stores the leasing information in-memory within a cluster member. This option requires Node Manager to be configured and running.   Note: Within a WebLogic Server installation, you can only use one type of leasing. Although it is possible to implement multiple features that use leasing within your environment, each must use the same kind of leasing. "
      ::= { clusterEntry 76  }
   
   
   clusterHttpTraceSupportEnabled OBJECT-TYPE
      SYNTAX      OCTET STRING
      MAX-ACCESS  read-only
      STATUS      current
      DESCRIPTION "Returns the value of HttpTraceSupportEnabled.  "
      ::= { clusterEntry 77  }
   
   
   clusterReplicationChannel OBJECT-TYPE
      SYNTAX      OCTET STRING
      MAX-ACCESS  read-only
      STATUS      current
      DESCRIPTION "The channel name to be used for replication traffic. Cluster infrastructure uses this channel to send updates for HTTP sessions and stateful session beans. If none is set then the default channel will be used.  In order for this feature to work, the named channel must exist on all members of the cluster and must be configured to use the same protocol. It is valid for the selected channel to be configured to use a secure protocol. "
      ::= { clusterEntry 78  }
   
   
   clusterFencingGracePeriodMillis OBJECT-TYPE
      SYNTAX      INTEGER
      MAX-ACCESS  read-only
      STATUS      current
      DESCRIPTION "During automatic migration, if the Cluster Master determines a server to be dead, it waits for this period of time (in milliseconds) before the Cluster Master migrates the service to another server in the cluster. "
      ::= { clusterEntry 79  }
   
   
   clusterFrontendHost OBJECT-TYPE
      SYNTAX      OCTET STRING
      MAX-ACCESS  read-only
      STATUS      current
      DESCRIPTION "The name of the host to which all redirected URLs will be sent.  Sets the HTTP FrontendHost for the default webserver (not virtual hosts) for all the servers in the cluster. Provides a method to ensure that the webapp will always have the correct HOST information, even when the request is coming through a firewall or a proxy. If this parameter is configured, the HOST header will be ignored and the information in this parameter will be used in its place, when constructing the absolute urls for redirects. "
      ::= { clusterEntry 80  }
   
   
   clusterMemberWarmupTimeoutSeconds OBJECT-TYPE
      SYNTAX      INTEGER
      MAX-ACCESS  read-only
      STATUS      current
      DESCRIPTION "Maximum number of seconds that a cluster member will wait to discover and synchronize with other servers in the cluster. Normally, the member will be able to sync in 30 seconds. If the value of this attribute is higher, that does not necessarily mean that it will take longer for the member to warmup. Instead it defines an upper bound on the time that a server will wait to sync with the servers that it has discovered. If the value is set 0, servers will not attempt to discover other running server in the cluster during server initialization "
      ::= { clusterEntry 81  }
   
   
   clusterFrontendHTTPSPort OBJECT-TYPE
      SYNTAX      INTEGER
      MAX-ACCESS  read-only
      STATUS      current
      DESCRIPTION "The name of the secure HTTP port to which all redirected URLs will be sent.  Sets the FrontendHTTPSPort for the default webserver (not virtual hosts) for all the servers in the cluster. Provides a method to ensure that the webapp will always have the correct PORT information, even when the request is coming through a firewall or a proxy. If this parameter is configured, the HOST header will be ignored and the information in this parameter will be used in its place, when constructing the absolute urls for redirects. "
      ::= { clusterEntry 82  }
   
   
   clusterClusterBroadcastChannel OBJECT-TYPE
      SYNTAX      OCTET STRING
      MAX-ACCESS  read-only
      STATUS      current
      DESCRIPTION "Specifies the channel used to handle communications within a cluster. If no channel is specified the default channel is used. ClusterBroadcastChannel is only are supported if the unicast messaging type is used. "
      ::= { clusterEntry 83  }
   
   
   clusterIdlePeriodsUntilTimeout OBJECT-TYPE
      SYNTAX      INTEGER
      MAX-ACCESS  read-only
      STATUS      current
      DESCRIPTION "Maximum number of periods that a cluster member will wait before timing out a member of a cluster.  Maximum number of periods that a cluster member will wait before timing out a member of a cluster. "
      ::= { clusterEntry 84  }
   
   
   clusterNumberOfServersInClusterAddress OBJECT-TYPE
      SYNTAX      INTEGER
      MAX-ACCESS  read-only
      STATUS      current
      DESCRIPTION "Number of servers to be listed from this cluster when generating a cluster address automatically. This setting has no effect if Cluster Address is explicitly set. "
      ::= { clusterEntry 85  }
   
   
   clusterClusterMessagingMode OBJECT-TYPE
      SYNTAX      OCTET STRING
      MAX-ACCESS  read-only
      STATUS      current
      DESCRIPTION "Specifies the messaging type used in the cluster. Multicast messaging is provided for backwards compatibility. "
      ::= { clusterEntry 86  }
   
   
   clusterMillisToSleepBetweenAutoMigrationAttempts OBJECT-TYPE
      SYNTAX      Counter64
      MAX-ACCESS  read-only
      STATUS      current
      DESCRIPTION "Controls how long of a pause there should be between the migration attempts described in getAdditionalAutoMigrationAttempts(). Note that this delay only happens when the server has failed to come up on every machine. "
      ::= { clusterEntry 87  }
   
   
   clusterAutoMigrationTableName OBJECT-TYPE
      SYNTAX      OCTET STRING
      MAX-ACCESS  read-only
      STATUS      current
      DESCRIPTION "Return the name of the table to be used for server migration. "
      ::= { clusterEntry 88  }
   
   
   clusterWANSessionPersistenceTableName OBJECT-TYPE
      SYNTAX      OCTET STRING
      MAX-ACCESS  read-only
      STATUS      current
      DESCRIPTION "Return the name of the table to be used for WAN session persistence. "
      ::= { clusterEntry 89  }
   
   
   clusterOneWayRmiForReplicationEnabled OBJECT-TYPE
      SYNTAX      OCTET STRING
      MAX-ACCESS  read-only
      STATUS      current
      DESCRIPTION "Indicates if one-way RMI is being used for replication. One-way RMI also requires configuring replication ports on each server in the cluster. "
      ::= { clusterEntry 90  }
   
   
   clusterMessageOrderingEnabled OBJECT-TYPE
      SYNTAX      OCTET STRING
      MAX-ACCESS  read-only
      STATUS      current
      DESCRIPTION "Forces unicast messages to be processed in order. There are scenarios where JMS may update JNDI very frequently. It will result in a lot of messages over unicast. Due to the close proximity of messages the probability of out of order handling of messages increases which would trigger frequent state dumps. Frequent JNDI tree refresh may result in NameNotFoundException. Use this property to prevent out of order handling of messages. "
      ::= { clusterEntry 91  }
   
   
   clusterSessionLazyDeserializationEnabled OBJECT-TYPE
      SYNTAX      OCTET STRING
      MAX-ACCESS  read-only
      STATUS      current
      DESCRIPTION "Enables increased efficiency with session replication. Enabling this attribute should be used only when configuring a WebLogic domain for Oracle Exalogic. "
      ::= { clusterEntry 92  }
   
   
   clusterMemberDeathDetectorEnabled OBJECT-TYPE
      SYNTAX      OCTET STRING
      MAX-ACCESS  read-only
      STATUS      current
      DESCRIPTION "Enables faster Automatic Service Migration times with Database Leasing Basis. "
      ::= { clusterEntry 93  }
   
   
   clusterTxnAffinityEnabled OBJECT-TYPE
      SYNTAX      OCTET STRING
      MAX-ACCESS  read-only
      STATUS      current
      DESCRIPTION "If enabled, a server's transaction requests go to servers in the cluster that are already participating in the global transaction. "
      ::= { clusterEntry 94  }
   
   
   clusterDatabaseLeasingBasisConnectionRetryDelay OBJECT-TYPE
      SYNTAX      Counter64
      MAX-ACCESS  read-only
      STATUS      current
      DESCRIPTION "The length of time, in milliseconds,Database Leasing will wait before attempting to obtain a new connection from the Data Source when a connection has failed. "
      ::= { clusterEntry 95  }
   
   
   clusterDatabaseLeasingBasisConnectionRetryCount OBJECT-TYPE
      SYNTAX      INTEGER
      MAX-ACCESS  read-only
      STATUS      current
      DESCRIPTION "The maximum number of times Database Leasing will try to obtain a valid connection from the Data Source. "
      ::= { clusterEntry 96  }
   
   
   clusterServiceActivationRequestResponseTimeout OBJECT-TYPE
      SYNTAX      INTEGER
      MAX-ACCESS  read-only
      STATUS      current
      DESCRIPTION "The maximum time, in milliseconds seconds, for services to wait for response from cluster members. "
      ::= { clusterEntry 97  }
   
   
   clusterTags OBJECT-TYPE
      SYNTAX      OCTET STRING
      MAX-ACCESS  read-only
      STATUS      current
      DESCRIPTION "Return all tags on this Configuration MBean "
      ::= { clusterEntry 98  }
   
   
   clusterSessionStateQueryProtocolEnabled OBJECT-TYPE
      SYNTAX      OCTET STRING
      MAX-ACCESS  read-only
      STATUS      current
      DESCRIPTION "Indicates if session state query protocol is enabled.  The Session State Query protocol will query the local cluster for the location of a session state instance if a request arrives at a server that is neither the primary or secondary server. "
      ::= { clusterEntry 99  }
   
   
   clusterSessionStateQueryRequestTimeout OBJECT-TYPE
      SYNTAX      INTEGER
      MAX-ACCESS  read-only
      STATUS      current
      DESCRIPTION "The maximum time, in seconds, for session state query request to wait for response from cluster members. "
      ::= { clusterEntry 100  }
   
   
   clusterSiteName OBJECT-TYPE
      SYNTAX      OCTET STRING
      MAX-ACCESS  read-only
      STATUS      current
      DESCRIPTION "The name of the site this cluster is associated with. "
      ::= { clusterEntry 101  }
   
   
   clusterSingletonServiceRequestTimeout OBJECT-TYPE
      SYNTAX      INTEGER
      MAX-ACCESS  read-only
      STATUS      current
      DESCRIPTION "The maximum time, in milliseconds, for service activation requests will wait for response from cluster members.  A value of 0 means that the request will wait indefinitely to complete. "
      ::= { clusterEntry 102  }
   
   
   clusterConcurrentSingletonActivationEnabled OBJECT-TYPE
      SYNTAX      OCTET STRING
      MAX-ACCESS  read-only
      STATUS      current
      DESCRIPTION "Specifies whether to allow the concurrent activation, deactivation, or restart of two or more singleton services. "
      ::= { clusterEntry 103  }
   
   
   clusterUnicastReadTimeout OBJECT-TYPE
      SYNTAX      INTEGER
      MAX-ACCESS  read-only
      STATUS      current
      DESCRIPTION "The specified read timeout, in milliseconds, on a unicast connection.  A timeout of zero is interpreted as an infinite timeout, that is blocking read forever. "
      ::= { clusterEntry 104  }
   
   
   comTable OBJECT-TYPE
      SYNTAX      SEQUENCE OF ComEntry
      MAX-ACCESS  not-accessible
      STATUS      current
      DESCRIPTION "This bean represents the server-wide configuration of COM "
      ::= { wls 512  }
      
   
   comEntry OBJECT-TYPE
      SYNTAX      ComEntry
      MAX-ACCESS  not-accessible
      STATUS      current
      DESCRIPTION "Entry of comTable"
      INDEX { comIndex}
      ::= { comTable 1 }
      
   ComEntry ::=
      SEQUENCE
      {
         comIndex             DisplayString,
         comObjectName        DisplayString,
         comType              DisplayString,
         comName              DisplayString,
         comParent            DisplayString,
         comNTAuthHost        DisplayString,
         comApartmentThreaded INTEGER,
         comMemoryLoggingEnabled INTEGER,
         comNativeModeEnabled INTEGER,
         comPrefetchEnums     INTEGER,
         comVerboseLoggingEnabled INTEGER,
         comTags              OCTET STRING
      }
      
   
   comIndex OBJECT-TYPE
      SYNTAX      DisplayString (SIZE (1..16))
      MAX-ACCESS  read-only
      STATUS      current
      DESCRIPTION "Unique value directed from ObjectName which is used as table index"
      ::= { comEntry 1  }
   
   
   comObjectName OBJECT-TYPE
      SYNTAX      DisplayString (SIZE (1..256))
      MAX-ACCESS  read-only
      STATUS      current
      DESCRIPTION "JMX-standard MBean name"
      ::= { comEntry 5  }
   
   
   comType OBJECT-TYPE
      SYNTAX      DisplayString (SIZE (1..64))
      MAX-ACCESS  read-only
      STATUS      current
      DESCRIPTION "Returns the type of the MBean. "
      ::= { comEntry 10  }
   
   
   comName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { comEntry 15  }
   
   
   comParent OBJECT-TYPE
      SYNTAX      DisplayString (SIZE (1..256))
      MAX-ACCESS  read-only
      STATUS      current
      DESCRIPTION "BEA-proprietary Parent object's identification, with syntax
      <type>:<name>"
      ::= { comEntry 20  }
   
   
   comNTAuthHost OBJECT-TYPE
      SYNTAX      DisplayString (SIZE (1..256))
      MAX-ACCESS  read-only
      STATUS      current
      DESCRIPTION "The address of the primary domain controller this server uses for authenticating clients. (If not specified, COM clients will not be authenticated.) "
      ::= { comEntry 25  }
   
   
   comApartmentThreaded OBJECT-TYPE
      SYNTAX      INTEGER
      MAX-ACCESS  read-only
      STATUS      current
      DESCRIPTION "Controls the flag that is used to initialize COM in native mode.  By default, when jCOM initializes COM in native mode, it starts COM with the COINIT_MULTITHREADED. This causes COM to use Multi-Threaded Apartment (MTA) thread model. In the MTA model, calls to an object are not synchronized by COM. Multiple clients can concurrently call an object that supports this model on different threads, and the object must provide synchronization in its interface/method implementations using synchronization objects such as events, mutexes, semaphores, etc. MTA objects can receive concurrent calls from multiple out-of-process clients through a pool of COM-created threads belonging to the object's process.  If the server logs a Class Not Registered Message when starting COM in native mode, try setting this property. This will cause jCOM to start COM in native mode, using COINIT_APARTMENTTHREADED option instead of the COINIT_MULTITHREADED option. In a component that is marked as Apartment Threaded, each method of that component will execute on a thread that is associated with that component. This separates the methods into their own 'Apartments', with each instance of a component corresponding to one apartment. While there is only one thread inside of a component, each instance of that component will have its own thread apartment. "
      ::= { comEntry 30  }
   
   
   comMemoryLoggingEnabled OBJECT-TYPE
      SYNTAX      INTEGER
      MAX-ACCESS  read-only
      STATUS      current
      DESCRIPTION "Specifies whether this server should log memory usage. "
      ::= { comEntry 35  }
   
   
   comNativeModeEnabled OBJECT-TYPE
      SYNTAX      INTEGER
      MAX-ACCESS  read-only
      STATUS      current
      DESCRIPTION "Specifies whether this server should use native DLLs to allow Java objects to interact with COM objects. (Supported on Windows only.) "
      ::= { comEntry 45  }
   
   
   comPrefetchEnums OBJECT-TYPE
      SYNTAX      INTEGER
      MAX-ACCESS  read-only
      STATUS      current
      DESCRIPTION "Specifies whether this server should prefetch the next element in a java.lang.Enumeration (that had been improperly converted from a COM VariantEnumeration type) so the correct value is returned when the hasMoreElements() method is called.  Some COM methods return a COM VariantEnumeration type. The java2com tool automatically converts the returned type into a java.lang.Enumeration. This is not a perfect match since COM enumerations have no equivalent to the hasMoreElements() call. The client must continue to call nextElement until a NoSuchElementException occurs. Setting this property will cause jCOM to prefetch the next element in behind the scenes and return the correct value when hasMoreElements is called. "
      ::= { comEntry 50  }
   
   
   comVerboseLoggingEnabled OBJECT-TYPE
      SYNTAX      INTEGER
      MAX-ACCESS  read-only
      STATUS      current
      DESCRIPTION "Specifies whether verbose logging is enabled. "
      ::= { comEntry 55  }
   
   
   comTags OBJECT-TYPE
      SYNTAX      OCTET STRING
      MAX-ACCESS  read-only
      STATUS      current
      DESCRIPTION "Return all tags on this Configuration MBean "
      ::= { comEntry 56  }
   
   
   domainTable OBJECT-TYPE
      SYNTAX      SEQUENCE OF DomainEntry
      MAX-ACCESS  not-accessible
      STATUS      current
      DESCRIPTION "A WebLogic Domain is a group of servers and/or clusters which are administered as a group. "
      ::= { wls 530  }
      
   
   domainEntry OBJECT-TYPE
      SYNTAX      DomainEntry
      MAX-ACCESS  not-accessible
      STATUS      current
      DESCRIPTION "Entry of domainTable"
      INDEX { domainIndex}
      ::= { domainTable 1 }
      
   DomainEntry ::=
      SEQUENCE
      {
         domainIndex          DisplayString,
         domainObjectName     DisplayString,
         domainType           DisplayString,
         domainName           DisplayString,
         domainParent         DisplayString,
         domainLastModificationTime Counter64,
         domainRootDirectory  DisplayString,
         domainAdministrationPort INTEGER,
         domainArchiveConfigurationCount INTEGER,
         domainConfigurationVersion DisplayString,
         domainConsoleContextPath DisplayString,
         domainAdministrationPortEnabled INTEGER,
         domainClusterConstraintsEnabled INTEGER,
         domainConsoleEnabled INTEGER,
         domainInternalAppsDeployOnDemandEnabled OCTET STRING,
         domainDomainVersion  OCTET STRING,
         domainConfigBackupEnabled OCTET STRING,
         domainConsoleExtensionDirectory OCTET STRING,
         domainConfigurationAuditType OCTET STRING,
         domainAdminServerName OCTET STRING,
         domainAdministrationProtocol OCTET STRING,
         domainProductionModeEnabled OCTET STRING,
         domainAdministrationMBeanAuditingEnabled OCTET STRING,
         domainServiceMigrationHistorySize INTEGER,
         domainExalogicOptimizationsEnabled OCTET STRING,
         domainJavaServiceConsoleEnabled OCTET STRING,
         domainJavaServiceEnabled OCTET STRING,
         domainServerMigrationHistorySize INTEGER,
         domainTags           OCTET STRING,
         domainLogFormatCompatibilityEnabled OCTET STRING,
         domainParallelDeployApplicationModules OCTET STRING,
         domainMaxConcurrentNewThreads INTEGER,
         domainDiagnosticContextCompatibilityModeEnabled OCTET STRING,
         domainBatchJobsDataSourceJndiName OCTET STRING,
         domainEnableEECompliantClassloadingForEmbeddedAdapters OCTET STRING,
         domainParallelDeployApplications OCTET STRING,
         domainBatchJobsExecutorServiceName OCTET STRING,
         domainSiteName       OCTET STRING,
         domainMaxConcurrentLongRunningRequests INTEGER,
         domainPartitionUriSpace OCTET STRING,
         domainDBPassiveMode  OCTET STRING,
         domainDBPassiveModeGracePeriodSeconds INTEGER
      }
      
   
   domainIndex OBJECT-TYPE
      SYNTAX      DisplayString (SIZE (1..16))
      MAX-ACCESS  read-only
      STATUS      current
      DESCRIPTION "Unique value directed from ObjectName which is used as table index"
      ::= { domainEntry 1  }
   
   
   domainObjectName OBJECT-TYPE
      SYNTAX      DisplayString (SIZE (1..256))
      MAX-ACCESS  read-only
      STATUS      current
      DESCRIPTION "JMX-standard MBean name"
      ::= { domainEntry 5  }
   
   
   domainType OBJECT-TYPE
      SYNTAX      DisplayString (SIZE (1..64))
      MAX-ACCESS  read-only
      STATUS      current
      DESCRIPTION "Returns the type of the MBean. "
      ::= { domainEntry 10  }
   
   
   domainName OBJECT-TYPE
      SYNTAX      DisplayString (SIZE (1..64))
      MAX-ACCESS  read-only
      STATUS      current
      DESCRIPTION "An alphanumeric name for this domain.  For more information on domain naming conventions, see Domain and Server Name Restrictions in Understanding Domain Configuration for Oracle WebLogic Server.  This name is included as one of the key properties in the MBean's javax.management.ObjectName:  Name=user-specified-name "
      ::= { domainEntry 15  }
   
   
   domainParent OBJECT-TYPE
      SYNTAX      DisplayString (SIZE (1..256))
      MAX-ACCESS  read-only
      STATUS      current
      DESCRIPTION "BEA-proprietary Parent object's identification, with syntax
      <type>:<name>"
      ::= { domainEntry 20  }
   
   
   domainLastModificationTime OBJECT-TYPE
      SYNTAX      Counter64
      MAX-ACCESS  read-only
      STATUS      current
      DESCRIPTION "Return the last time this domain was updated. This is guaranteed to be unique for a given transactional modification. "
      ::= { domainEntry 25  }
   
   
   domainRootDirectory OBJECT-TYPE
      SYNTAX      DisplayString (SIZE (1..256))
      MAX-ACCESS  read-only
      STATUS      current
      DESCRIPTION "Return the root directory for the domain. In other words for a server process [ServerMBean.getRootDirectory] or [ServerMBean.getDomainDirectory] "
      ::= { domainEntry 35  }
   
   
   domainAdministrationPort OBJECT-TYPE
      SYNTAX      INTEGER
      MAX-ACCESS  read-only
      STATUS      current
      DESCRIPTION "The common secure administration port for this WebLogic Server domain. (Requires you to enable the administration port.) "
      ::= { domainEntry 51  }
   
   
   domainArchiveConfigurationCount OBJECT-TYPE
      SYNTAX      INTEGER
      MAX-ACCESS  read-only
      STATUS      current
      DESCRIPTION "The number of archival versions of config.xml saved by the Administration Server each time the domain configuration is modified. "
      ::= { domainEntry 52  }
   
   
   domainConfigurationVersion OBJECT-TYPE
      SYNTAX      DisplayString
      MAX-ACCESS  read-only
      STATUS      current
      DESCRIPTION "The release identifier for the configuration. This identifier will be used to indicate the version of the configuration. All server generated configurations will be established with the release identifier of the running server. The form of the version is major.minor.servicepack.rollingpatch. Not all parts of the version are required. i.e. '7' is acceptable. "
      ::= { domainEntry 53  }
   
   
   domainConsoleContextPath OBJECT-TYPE
      SYNTAX      DisplayString
      MAX-ACCESS  read-only
      STATUS      current
      DESCRIPTION "The context path that you want to use in URLs that specify the Administration Console. (Requires you to enable the Administration Console for the current domain.)  To access the Administration Console, you use the following URL: http://listen-addess:listen-port/context-path. For example, if you set the context path to myconsole, then you use the following URL to access the Administration Console: http://localhost:7001/myconsole.  To specify the listen address and listen port that you use to access the Administration Console, configure the listen address and listen port of the Administration Server. "
      ::= { domainEntry 54  }
   
   
   domainAdministrationPortEnabled OBJECT-TYPE
      SYNTAX      INTEGER
      MAX-ACCESS  read-only
      STATUS      current
      DESCRIPTION "Specifies whether the domain-wide administration port should be enabled for this WebLogic Server domain. Because the administration port uses SSL, enabling the administration port requires that SSL must be configured for all servers in the domain.  The domain-wide administration port enables you to start a WebLogic Server instance in STANDBY state. It also allows you to separate administration traffic from application traffic in your domain. Because all servers in the domain must enable or disable the administration port at once, you configure the default administration port settings at the domain level.  If you enable the administration port:    The administration port accepts only connections that specify administrator credentials.    Connections that specify administrator credentials can use only the administration port.    The command that starts managed servers must specify a secure protocol and the administration port: -Dweblogic.management.server=https://admin_server:administration_port   "
      ::= { domainEntry 55  }
   
   
   domainClusterConstraintsEnabled OBJECT-TYPE
      SYNTAX      INTEGER
      MAX-ACCESS  read-only
      STATUS      current
      DESCRIPTION "Specifies that deployments targeted to a cluster succeed only if all servers in the cluster are running.  By default, cluster constraints are disabled and deployment is attempted only on the servers that are reachable at the time of deployment from the Administration Server. Any servers that have been shut down or are temporarily partitioned from the Administration Server will retrieve the deployment during server startup or shortly after the network partition is resolved. "
      ::= { domainEntry 56  }
   
   
   domainConsoleEnabled OBJECT-TYPE
      SYNTAX      INTEGER
      MAX-ACCESS  read-only
      STATUS      current
      DESCRIPTION "Specifies whether the Administration Server automatically deploys the Administration Console in the current domain.  If the Administration Console is not deployed, you can still use the WebLogic Scripting Tool or the management APIs to configure and monitor the domain. "
      ::= { domainEntry 57  }
   
   
   domainInternalAppsDeployOnDemandEnabled OBJECT-TYPE
      SYNTAX      OCTET STRING
      MAX-ACCESS  read-only
      STATUS      current
      DESCRIPTION "Specifies whether internal applications such as the console, uddi, wlstestclient, and uddiexplorer are deployed on demand (first access) instead of during server startup.  "
      ::= { domainEntry 58  }
   
   
   domainDomainVersion OBJECT-TYPE
      SYNTAX      OCTET STRING
      MAX-ACCESS  read-only
      STATUS      current
      DESCRIPTION "Defines the common version of all servers in a domain. In a domain containing servers that are not all at the same release version, this attribute is used to determine the feature level that servers will assume.  The value must be less than or equal to the version of any managed server in the domain.  If this value is not equal to the version of the release version of the admin server, then the admin server will not be allowed to make modifications to the configuration. "
      ::= { domainEntry 59  }
   
   
   domainConfigBackupEnabled OBJECT-TYPE
      SYNTAX      OCTET STRING
      MAX-ACCESS  read-only
      STATUS      current
      DESCRIPTION "If true, then backups of the configuration will be made during server boot. "
      ::= { domainEntry 60  }
   
   
   domainConsoleExtensionDirectory OBJECT-TYPE
      SYNTAX      OCTET STRING
      MAX-ACCESS  read-only
      STATUS      current
      DESCRIPTION "Returns the directory path that console extensions are loaded from. "
      ::= { domainEntry 61  }
   
   
   domainConfigurationAuditType OBJECT-TYPE
      SYNTAX      OCTET STRING
      MAX-ACCESS  read-only
      STATUS      current
      DESCRIPTION "Returns the criteria used for auditing configuration events  (configuration changes and other operations):  CONFIG_CHANGE_NONE Configuration events will neither be written to the server log or directed to the Security Audit Framework. CONFIG_CHANGE_LOG Configuration events will be written to the server log. CONFIG_CHANGE_AUDITConfiguration events will be directed to the Security Audit Framework. CONFIG_CHANGE_LOG_AND_AUDIT Configuration events will be written to the server log and directed to the Security Audit Framework.  "
      ::= { domainEntry 62  }
   
   
   domainAdminServerName OBJECT-TYPE
      SYNTAX      OCTET STRING
      MAX-ACCESS  read-only
      STATUS      current
      DESCRIPTION " "
      ::= { domainEntry 63  }
   
   
   domainAdministrationProtocol OBJECT-TYPE
      SYNTAX      OCTET STRING
      MAX-ACCESS  read-only
      STATUS      current
      DESCRIPTION "The default protocol for communicating through the administration port or administration channels. (Requires you to enable the administration port or to create an administration channel.)  If requests through the administration port or an administration channel do not specify a protocol, WebLogic Server uses the protocol specified here.  Valid admin protocols are:   t3s  https  iiops  "
      ::= { domainEntry 64  }
   
   
   domainProductionModeEnabled OBJECT-TYPE
      SYNTAX      OCTET STRING
      MAX-ACCESS  read-only
      STATUS      current
      DESCRIPTION "Specifies whether all servers in this domain run in production mode. You can configure servers in your domain to start in one of two modes, development or production. You use development mode while you are developing your applications. Development mode uses a relaxed security configuration and enables you to auto-deploy applications. You use production mode when your application is running in its final form. A production domain uses full security and may use clusters or other advanced features.  The runtime mode is a domain-wide setting. As each Managed Server starts, it refers to the mode of the Administration Server to determine its runtime mode. If you configure the domain to run in production mode, the Administration Server saves this setting to the domain's configuration document. "
      ::= { domainEntry 65  }
   
   
   domainAdministrationMBeanAuditingEnabled OBJECT-TYPE
      SYNTAX      OCTET STRING
      MAX-ACCESS  read-only
      STATUS      current
      DESCRIPTION "Specifies whether the Administration Server generates a log message when this WebLogic Server domain's configuration has been modified.  Any change to a server, module, or other item in the domain (either through the Administration Console, command-line utilities, or the APIs) will cause the Administration Server to generate this informational message.   This attribute has been deprecated in favor of ConfigurationAuditType. If values for both attributes are specified, the resultant behavior will be the logical OR condition of the two settings. "
      ::= { domainEntry 67  }
   
   
   domainServiceMigrationHistorySize OBJECT-TYPE
      SYNTAX      INTEGER
      MAX-ACCESS  read-only
      STATUS      current
      DESCRIPTION "Gets the history size of service migrations.  A value of -1 indicates that the history size is unlimited. "
      ::= { domainEntry 68  }
   
   
   domainExalogicOptimizationsEnabled OBJECT-TYPE
      SYNTAX      OCTET STRING
      MAX-ACCESS  read-only
      STATUS      current
      DESCRIPTION "Specifies whether optimizations for Oracle Exalogic should be enabled. Optimizations include improved thread management and request processing, and reduced lock contention. This attribute should be enabled only when configuring a WebLogic domain for Oracle Exalogic. "
      ::= { domainEntry 69  }
   
   
   domainJavaServiceConsoleEnabled OBJECT-TYPE
      SYNTAX      OCTET STRING
      MAX-ACCESS  read-only
      STATUS      current
      DESCRIPTION "Specifies whether the Administration Server automatically deploys the Java Service Administration Console in the current domain. "
      ::= { domainEntry 70  }
   
   
   domainJavaServiceEnabled OBJECT-TYPE
      SYNTAX      OCTET STRING
      MAX-ACCESS  read-only
      STATUS      current
      DESCRIPTION "Specifies whether features to support the use of this WebLogic Server as a Java Service in a cloud environment should be enabled. "
      ::= { domainEntry 71  }
   
   
   domainServerMigrationHistorySize OBJECT-TYPE
      SYNTAX      INTEGER
      MAX-ACCESS  read-only
      STATUS      current
      DESCRIPTION "Gets the history size of server migrations.  A value of -1 indicates that the history size is unlimited. "
      ::= { domainEntry 72  }
   
   
   domainTags OBJECT-TYPE
      SYNTAX      OCTET STRING
      MAX-ACCESS  read-only
      STATUS      current
      DESCRIPTION "Return all tags on this Configuration MBean "
      ::= { domainEntry 73  }
   
   
   domainLogFormatCompatibilityEnabled OBJECT-TYPE
      SYNTAX      OCTET STRING
      MAX-ACCESS  read-only
      STATUS      current
      DESCRIPTION "Configures whether log messages will be logged in legacy format without supplemental attributes. "
      ::= { domainEntry 74  }
   
   
   domainParallelDeployApplicationModules OBJECT-TYPE
      SYNTAX      OCTET STRING
      MAX-ACCESS  read-only
      STATUS      current
      DESCRIPTION "Determines if the modules of applications will be deployed in parallel.  This setting can be overridden at the per-partition or per-application levels. See {@link AppDeploymentMBean#isParallelDeployModules()} "
      ::= { domainEntry 75  }
   
   
   domainMaxConcurrentNewThreads OBJECT-TYPE
      SYNTAX      INTEGER
      MAX-ACCESS  read-only
      STATUS      current
      DESCRIPTION "The maximum number of running threads that can be created by all the Managed Thread Factories in the global/domain partition on the current server. "
      ::= { domainEntry 76  }
   
   
   domainDiagnosticContextCompatibilityModeEnabled OBJECT-TYPE
      SYNTAX      OCTET STRING
      MAX-ACCESS  read-only
      STATUS      current
      DESCRIPTION "Specifies whether WLDF sends a pre-12.2.1-style diagnostic context along with the current-style diagnostic context.  If outbound communication to pre-12.2.1 servers is possible, this setting should always be enabled to ensure that those servers receive a diagnostic context that they can process. Disabling this setting in those scenarios can result in correlation information being lost across tiers, and in information reported by WLDF and DMS to become of sync in some situations.  If there is no outbound communication to pre-12.2.1 servers possible, it is suggested to disable this mode as only the current-style diagnostic context is needed to be propagated outbound (propagating the old style will not cause a failure, but is unnecessary overhead in that situation).  This setting affects outbound only, inbound pre-12.2.1 style diagnostic contexts are always understood and handled. "
      ::= { domainEntry 77  }
   
   
   domainBatchJobsDataSourceJndiName OBJECT-TYPE
      SYNTAX      OCTET STRING
      MAX-ACCESS  read-only
      STATUS      current
      DESCRIPTION "Returns the Batch DataSource jndi name. This jndi name will be used to lookup an instance of a DataSource that will be used to store the Batch jobs data. "
      ::= { domainEntry 78  }
   
   
   domainEnableEECompliantClassloadingForEmbeddedAdapters OBJECT-TYPE
      SYNTAX      OCTET STRING
      MAX-ACCESS  read-only
      STATUS      current
      DESCRIPTION "Specifies the class loading behavior for embedded adapters. If you enable this option, embedded adapters deployed to all partitions in the domain will use Java EE compliant class loading. The embedded adapter's classes will be accessible from other modules in the same application. "
      ::= { domainEntry 79  }
   
   
   domainParallelDeployApplications OBJECT-TYPE
      SYNTAX      OCTET STRING
      MAX-ACCESS  read-only
      STATUS      current
      DESCRIPTION "Determines if applications will be deployed in parallel.  This setting can be overridden at the per-partition level.  See {@link PartitionMBean#isParallelDeployApplications()} "
      ::= { domainEntry 80  }
   
   
   domainBatchJobsExecutorServiceName OBJECT-TYPE
      SYNTAX      OCTET STRING
      MAX-ACCESS  read-only
      STATUS      current
      DESCRIPTION "Returns the name of the application-scoped ManagedExecutorService. This ManagedExecutorService instance will be used to run batch jobs that are submitted from applications deployed to the domain. The ManagedExecutorServiceTemplate by the same name must exit when a batch job is submitted in the domain. If this returns null, then the batch runtime will look to use the default Java EE ManagedExecutorService that is bound to the JNDI name: java:comp/DefaultManagedExecutorService. "
      ::= { domainEntry 81  }
   
   
   domainSiteName OBJECT-TYPE
      SYNTAX      OCTET STRING
      MAX-ACCESS  read-only
      STATUS      current
      DESCRIPTION "The name of the site this domain is associated with. "
      ::= { domainEntry 82  }
   
   
   domainMaxConcurrentLongRunningRequests OBJECT-TYPE
      SYNTAX      INTEGER
      MAX-ACCESS  read-only
      STATUS      current
      DESCRIPTION "The maximum number of running long-running requests that can be submitted to all the Managed Executor Services or Managed Scheduled Executor Services in the global/domain partition on the current server. "
      ::= { domainEntry 83  }
   
   
   domainPartitionUriSpace OBJECT-TYPE
      SYNTAX      OCTET STRING
      MAX-ACCESS  read-only
      STATUS      current
      DESCRIPTION "The URI prefix used for partition administrative virtual targets. "
      ::= { domainEntry 84  }
   
   
   domainDBPassiveMode OBJECT-TYPE
      SYNTAX      OCTET STRING
      MAX-ACCESS  read-only
      STATUS      current
      DESCRIPTION "Specifies whether the domain should enter database passive mode. "
      ::= { domainEntry 85  }
   
   
   domainDBPassiveModeGracePeriodSeconds OBJECT-TYPE
      SYNTAX      INTEGER
      MAX-ACCESS  read-only
      STATUS      current
      DESCRIPTION "Specifies the maximum amount of time, in seconds, that is allowed for in-progress work to complete before entering database passive mode. "
      ::= { domainEntry 86  }
   
   
   ejbComponentTable OBJECT-TYPE
      SYNTAX      SEQUENCE OF EjbComponentEntry
      MAX-ACCESS  not-accessible
      STATUS      current
      DESCRIPTION "Generated SNMP Table."
      ::= { wls 540  }
      
   
   ejbComponentEntry OBJECT-TYPE
      SYNTAX      EjbComponentEntry
      MAX-ACCESS  not-accessible
      STATUS      current
      DESCRIPTION "Entry of ejbComponentTable"
      INDEX { ejbComponentIndex}
      ::= { ejbComponentTable 1 }
      
   EjbComponentEntry ::=
      SEQUENCE
      {
         ejbComponentIndex    DisplayString,
         ejbComponentObjectName DisplayString,
         ejbComponentType     DisplayString,
         ejbComponentName     DisplayString,
         ejbComponentParent   DisplayString,
         ejbComponentJavaCompiler DisplayString,
         ejbComponentJavaCompilerPreClassPath DisplayString,
         ejbComponentJavaCompilerPostClassPath DisplayString,
         ejbComponentExtraRmicOptions DisplayString,
         ejbComponentKeepGenerated INTEGER,
         ejbComponentTmpPath  DisplayString,
         ejbComponentURI      DisplayString,
         ejbComponentVerboseEJBDeploymentEnabled OCTET STRING,
         ejbComponentForceGeneration OCTET STRING,
         ejbComponentExtraEjbcOptions OCTET STRING,
         ejbComponentDeploymentOrder INTEGER
      }
      
   
   ejbComponentIndex OBJECT-TYPE
      SYNTAX      DisplayString (SIZE (1..16))
      MAX-ACCESS  read-only
      STATUS      current
      DESCRIPTION "Unique value directed from ObjectName which is used as table index"
      ::= { ejbComponentEntry 1  }
   
   
   ejbComponentObjectName OBJECT-TYPE
      SYNTAX      DisplayString (SIZE (1..256))
      MAX-ACCESS  read-only
      STATUS      current
      DESCRIPTION "JMX-standard MBean name"
      ::= { ejbComponentEntry 5  }
   
   
   ejbComponentType OBJECT-TYPE
      SYNTAX      DisplayString (SIZE (1..64))
      MAX-ACCESS  read-only
      STATUS      current
      DESCRIPTION "BEA-proprietary MBean type"
      ::= { ejbComponentEntry 10  }
   
   
   ejbComponentName OBJECT-TYPE
      SYNTAX      DisplayString (SIZE (1..64))
      MAX-ACCESS  read-only
      STATUS      current
      DESCRIPTION "BEA-proprietary MBean name"
      ::= { ejbComponentEntry 15  }
   
   
   ejbComponentParent OBJECT-TYPE
      SYNTAX      DisplayString (SIZE (1..256))
      MAX-ACCESS  read-only
      STATUS      current
      DESCRIPTION "BEA-proprietary Parent object's identification, with syntax
      <type>:<name>"
      ::= { ejbComponentEntry 20  }
   
   
   ejbComponentJavaCompiler OBJECT-TYPE
      SYNTAX      DisplayString (SIZE (1..32))
      MAX-ACCESS  read-only
      STATUS      current
      DESCRIPTION "Return the path to the Java compiler to use to compile EJB's"
      ::= { ejbComponentEntry 25  }
   
   
   ejbComponentJavaCompilerPreClassPath OBJECT-TYPE
      SYNTAX      DisplayString (SIZE (1..256))
      MAX-ACCESS  read-only
      STATUS      current
      DESCRIPTION "Return the options to prepend to the Java compiler classpath for when
      we need to compile Java code."
      ::= { ejbComponentEntry 30  }
   
   
   ejbComponentJavaCompilerPostClassPath OBJECT-TYPE
      SYNTAX      DisplayString (SIZE (1..256))
      MAX-ACCESS  read-only
      STATUS      current
      DESCRIPTION "Return the options to append to the Java compiler classpath for when we
      need to compile Java code."
      ::= { ejbComponentEntry 35  }
   
   
   ejbComponentExtraRmicOptions OBJECT-TYPE
      SYNTAX      DisplayString (SIZE (1..256))
      MAX-ACCESS  read-only
      STATUS      current
      DESCRIPTION "Return the extra options passed to rmic during server-side
      generation.."
      ::= { ejbComponentEntry 40  }
   
   
   ejbComponentKeepGenerated OBJECT-TYPE
      SYNTAX      INTEGER
                  {
                     true(1),
                     false(2)
                  }
      
      MAX-ACCESS  read-only
      STATUS      current
      DESCRIPTION "A boolean value (true Or false). Return true if ejbc should keep its generated source files,
      false if it should delete them after compiling them."
      ::= { ejbComponentEntry 45  }
   
   
   ejbComponentTmpPath OBJECT-TYPE
      SYNTAX      DisplayString (SIZE (1..1024))
      MAX-ACCESS  read-only
      STATUS      current
      DESCRIPTION "Return the temporary directory where generated files are stored by ejbc."
      ::= { ejbComponentEntry 50  }
   
   
   ejbComponentURI OBJECT-TYPE
      SYNTAX      DisplayString (SIZE (1..256))
      MAX-ACCESS  read-only
      STATUS      current
      DESCRIPTION "Return a URI pointing to the application component, usually on the Admin Server."
      ::= { ejbComponentEntry 65  }
   
   
   ejbComponentVerboseEJBDeploymentEnabled OBJECT-TYPE
      SYNTAX      OCTET STRING
      MAX-ACCESS  read-only
      STATUS      current
      DESCRIPTION "Indicates whether the VerboseEJBDeployment is enabled."
      ::= { ejbComponentEntry 66  }
   
   
   ejbComponentForceGeneration OBJECT-TYPE
      SYNTAX      OCTET STRING
      MAX-ACCESS  read-only
      STATUS      current
      DESCRIPTION "Indicates whether the ForceGeneration is enabled."
      ::= { ejbComponentEntry 67  }
   
   
   ejbComponentExtraEjbcOptions OBJECT-TYPE
      SYNTAX      OCTET STRING
      MAX-ACCESS  read-only
      STATUS      current
      DESCRIPTION "Returns the extra options passed to ejbc during the dynamic ejbc of a jar file. For example: -J-mx128m By default this value is null. If no ExtraEJBCOptions are specified on the EJBComponent, the default will be pulled from the Server.ExtraEJBCOptions."
      ::= { ejbComponentEntry 68  }
   
   
   ejbComponentDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { ejbComponentEntry 69  }
   
   
   ejbContainerTable OBJECT-TYPE
      SYNTAX      SEQUENCE OF EjbContainerEntry
      MAX-ACCESS  not-accessible
      STATUS      current
      DESCRIPTION "This MBean is used to specify EJB container-wide settings.  These can be overridden by a specific EJBComponentMBean. "
      ::= { wls 545  }
      
   
   ejbContainerEntry OBJECT-TYPE
      SYNTAX      EjbContainerEntry
      MAX-ACCESS  not-accessible
      STATUS      current
      DESCRIPTION "Entry of ejbContainerTable"
      INDEX { ejbContainerIndex}
      ::= { ejbContainerTable 1 }
      
   EjbContainerEntry ::=
      SEQUENCE
      {
         ejbContainerIndex    DisplayString,
         ejbContainerObjectName DisplayString,
         ejbContainerType     DisplayString,
         ejbContainerName     DisplayString,
         ejbContainerParent   DisplayString,
         ejbContainerVerboseEJBDeploymentEnabled DisplayString,
         ejbContainerExtraRmicOptions DisplayString,
         ejbContainerForceGeneration DisplayString,
         ejbContainerJavaCompiler DisplayString,
         ejbContainerJavaCompilerPostClassPath DisplayString,
         ejbContainerJavaCompilerPreClassPath DisplayString,
         ejbContainerKeepGenerated DisplayString,
         ejbContainerTmpPath  DisplayString,
         ejbContainerExtraEjbcOptions DisplayString,
         ejbContainerTags     OCTET STRING
      }
      
   
   ejbContainerIndex OBJECT-TYPE
      SYNTAX      DisplayString (SIZE (1..16))
      MAX-ACCESS  read-only
      STATUS      current
      DESCRIPTION "Unique value directed from ObjectName which is used as table index"
      ::= { ejbContainerEntry 1  }
   
   
   ejbContainerObjectName OBJECT-TYPE
      SYNTAX      DisplayString (SIZE (1..256))
      MAX-ACCESS  read-only
      STATUS      current
      DESCRIPTION "JMX-standard MBean name"
      ::= { ejbContainerEntry 5  }
   
   
   ejbContainerType OBJECT-TYPE
      SYNTAX      DisplayString (SIZE (1..64))
      MAX-ACCESS  read-only
      STATUS      current
      DESCRIPTION "Returns the type of the MBean. "
      ::= { ejbContainerEntry 10  }
   
   
   ejbContainerName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { ejbContainerEntry 15  }
   
   
   ejbContainerParent OBJECT-TYPE
      SYNTAX      DisplayString (SIZE (1..256))
      MAX-ACCESS  read-only
      STATUS      current
      DESCRIPTION "BEA-proprietary Parent object's identification, with syntax
      <type>:<name>"
      ::= { ejbContainerEntry 20  }
   
   
   ejbContainerVerboseEJBDeploymentEnabled OBJECT-TYPE
      SYNTAX      DisplayString (SIZE (1..256))
      MAX-ACCESS  read-only
      STATUS      current
      DESCRIPTION "Indicates whether the VerboseEJBDeployment is enabled. "
      ::= { ejbContainerEntry 25  }
   
   
   ejbContainerExtraRmicOptions OBJECT-TYPE
      SYNTAX      DisplayString (SIZE (1..256))
      MAX-ACCESS  read-only
      STATUS      current
      DESCRIPTION "The extra options passed to rmic during server-side generation are noted here. The default for this attribute must be null. If no ExtraRmicOptions are specified on the EJBComponent, the default will be pulled from Server.ExtraRmicOptions. "
      ::= { ejbContainerEntry 30  }
   
   
   ejbContainerForceGeneration OBJECT-TYPE
      SYNTAX      DisplayString (SIZE (1..256))
      MAX-ACCESS  read-only
      STATUS      current
      DESCRIPTION "Indicates whether the ForceGeneration is enabled. "
      ::= { ejbContainerEntry 35  }
   
   
   ejbContainerJavaCompiler OBJECT-TYPE
      SYNTAX      DisplayString (SIZE (1..256))
      MAX-ACCESS  read-only
      STATUS      current
      DESCRIPTION "The path to the Java compiler to use to compile EJBs (e.g. 'sj' or 'javac'). Note: the default must be null. If no JavaCompiler is specified on this specific EJBComponent, the default will be pulled in the following order from - EJBContainerMBean - Server.JavaCompiler. "
      ::= { ejbContainerEntry 40  }
   
   
   ejbContainerJavaCompilerPostClassPath OBJECT-TYPE
      SYNTAX      DisplayString (SIZE (1..256))
      MAX-ACCESS  read-only
      STATUS      current
      DESCRIPTION "Provides a list of the options to append to the Java compiler classpath when you compile Java code. "
      ::= { ejbContainerEntry 45  }
   
   
   ejbContainerJavaCompilerPreClassPath OBJECT-TYPE
      SYNTAX      DisplayString (SIZE (1..256))
      MAX-ACCESS  read-only
      STATUS      current
      DESCRIPTION "Provides a list of the options to prepend to the Java compiler classpath when you compile Java code. "
      ::= { ejbContainerEntry 50  }
   
   
   ejbContainerKeepGenerated OBJECT-TYPE
      SYNTAX      DisplayString (SIZE (1..256))
      MAX-ACCESS  read-only
      STATUS      current
      DESCRIPTION "indicates whether KeepGenerated is enabled and the ejbc source files will be kept. "
      ::= { ejbContainerEntry 55  }
   
   
   ejbContainerTmpPath OBJECT-TYPE
      SYNTAX      DisplayString (SIZE (1..256))
      MAX-ACCESS  read-only
      STATUS      current
      DESCRIPTION "Return the temporary directory where generated files are stored by ejbc. Deprecated: All EJB compiler output is now stored in the EJBCompilerCache subdirectory of the server staging directory. This directory should not be described as 'temporary' since removing it would cause the EJB compiler to be rerun as necessary the next time the server is restarted. "
      ::= { ejbContainerEntry 60  }
   
   
   ejbContainerExtraEjbcOptions OBJECT-TYPE
      SYNTAX      DisplayString
      MAX-ACCESS  read-only
      STATUS      current
      DESCRIPTION "Returns the extra options passed to ejbc during the dynamic ejbc of a jar file. For example: -J-mx128m By default this value is null. If no ExtraEJBCOptions are specified on the EJBComponent, the default will be pulled from the Server.ExtraEJBCOptions. "
      ::= { ejbContainerEntry 61  }
   
   
   ejbContainerTags OBJECT-TYPE
      SYNTAX      OCTET STRING
      MAX-ACCESS  read-only
      STATUS      current
      DESCRIPTION "Return all tags on this Configuration MBean "
      ::= { ejbContainerEntry 62  }
   
   
   executeQueueTable OBJECT-TYPE
      SYNTAX      SEQUENCE OF ExecuteQueueEntry
      MAX-ACCESS  not-accessible
      STATUS      current
      DESCRIPTION "This bean is used to configure an execute queue and its associated thread pool. "
      ::= { wls 550  }
      
   
   executeQueueEntry OBJECT-TYPE
      SYNTAX      ExecuteQueueEntry
      MAX-ACCESS  not-accessible
      STATUS      current
      DESCRIPTION "Entry of executeQueueTable"
      INDEX { executeQueueIndex}
      ::= { executeQueueTable 1 }
      
   ExecuteQueueEntry ::=
      SEQUENCE
      {
         executeQueueIndex    DisplayString,
         executeQueueObjectName DisplayString,
         executeQueueType     DisplayString,
         executeQueueName     DisplayString,
         executeQueueParent   DisplayString,
         executeQueueThreadCount INTEGER,
         executeQueueThreadsMaximum INTEGER,
         executeQueueQueueLengthThresholdPercent INTEGER,
         executeQueueThreadsIncrease INTEGER,
         executeQueueThreadsMinimum INTEGER,
         executeQueueQueueLength INTEGER,
         executeQueueTags     OCTET STRING
      }
      
   
   executeQueueIndex OBJECT-TYPE
      SYNTAX      DisplayString (SIZE (1..16))
      MAX-ACCESS  read-only
      STATUS      current
      DESCRIPTION "Unique value directed from ObjectName which is used as table index"
      ::= { executeQueueEntry 1  }
   
   
   executeQueueObjectName OBJECT-TYPE
      SYNTAX      DisplayString (SIZE (1..256))
      MAX-ACCESS  read-only
      STATUS      current
      DESCRIPTION "JMX-standard MBean name"
      ::= { executeQueueEntry 5  }
   
   
   executeQueueType OBJECT-TYPE
      SYNTAX      DisplayString (SIZE (1..64))
      MAX-ACCESS  read-only
      STATUS      current
      DESCRIPTION "Returns the type of the MBean. "
      ::= { executeQueueEntry 10  }
   
   
   executeQueueName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { executeQueueEntry 15  }
   
   
   executeQueueParent OBJECT-TYPE
      SYNTAX      DisplayString (SIZE (1..256))
      MAX-ACCESS  read-only
      STATUS      current
      DESCRIPTION "BEA-proprietary Parent object's identification, with syntax
      <type>:<name>"
      ::= { executeQueueEntry 20  }
   
   
   executeQueueThreadCount OBJECT-TYPE
      SYNTAX      INTEGER
      MAX-ACCESS  read-only
      STATUS      current
      DESCRIPTION "The number of threads assigned to this queue. "
      ::= { executeQueueEntry 25  }
   
   
   executeQueueThreadsMaximum OBJECT-TYPE
      SYNTAX      INTEGER
      MAX-ACCESS  read-only
      STATUS      current
      DESCRIPTION "The maximum number of threads that this queue is allowed to have; this value prevents WebLogic Server from creating an overly high thread count in the queue in response to continual overflow conditions.  A note about dynamic nature of ThreadsMaximum and ThreadsIncrease attributes. If any of these attributes change during runtime, the changed value comes into effect when the next request is submitted to the execute queue and the scheduler decides to increase threads depending on the queue threshold conditions. Imagine a scenario where the queue capacity has already reached the max threshold and the current thread count is already equal to ThreadsMaximum value. If more work is coming into the queue and the administrator wishes to increase the ThreadsMaximum a little to add a few more threads, he/she can do so by changing these attributes dynamically. Please note that the changed value is evaluated when the next request is submitted. "
      ::= { executeQueueEntry 26  }
   
   
   executeQueueQueueLengthThresholdPercent OBJECT-TYPE
      SYNTAX      INTEGER
      MAX-ACCESS  read-only
      STATUS      current
      DESCRIPTION "The percentage of the Queue Length size that can be reached before this server indicates an overflow condition for the queue. If the overflow condition is reached and the current thread count has not reached the ThreadsMaximum value, then ThreadsIncrease number of threads are added. "
      ::= { executeQueueEntry 27  }
   
   
   executeQueueThreadsIncrease OBJECT-TYPE
      SYNTAX      INTEGER
      MAX-ACCESS  read-only
      STATUS      current
      DESCRIPTION "Specifies the number of threads to increase the queue length when the queue length theshold is reached. This threshold is determined by the QueueLengthThresholdPercent value.  The following consideration applies to the dynamic nature of ThreadsMaximum and ThreadsIncrease attributes. If any of these attributes change during runtime, the changed value comes into effect when the next request is submitted to the execute queue and the scheduler decides to increase threads depending on the queue threshold conditions. "
      ::= { executeQueueEntry 28  }
   
   
   executeQueueThreadsMinimum OBJECT-TYPE
      SYNTAX      INTEGER
      MAX-ACCESS  read-only
      STATUS      current
      DESCRIPTION "The minimum number of threads that WebLogic Server will maintain in the queue. "
      ::= { executeQueueEntry 29  }
   
   
   executeQueueQueueLength OBJECT-TYPE
      SYNTAX      INTEGER
      MAX-ACCESS  read-only
      STATUS      current
      DESCRIPTION "The maximum number of simultaneous requests that this server can hold in the queue. "
      ::= { executeQueueEntry 30  }
   
   
   executeQueueTags OBJECT-TYPE
      SYNTAX      OCTET STRING
      MAX-ACCESS  read-only
      STATUS      current
      DESCRIPTION "Return all tags on this Configuration MBean "
      ::= { executeQueueEntry 31  }
   
   
   iiopTable OBJECT-TYPE
      SYNTAX      SEQUENCE OF IiopEntry
      MAX-ACCESS  not-accessible
      STATUS      current
      DESCRIPTION "Configuration for IIOP properties. "
      ::= { wls 555  }
      
   
   iiopEntry OBJECT-TYPE
      SYNTAX      IiopEntry
      MAX-ACCESS  not-accessible
      STATUS      current
      DESCRIPTION "Entry of iiopTable"
      INDEX { iiopIndex}
      ::= { iiopTable 1 }
      
   IiopEntry ::=
      SEQUENCE
      {
         iiopIndex            DisplayString,
         iiopObjectName       DisplayString,
         iiopType             DisplayString,
         iiopName             DisplayString,
         iiopParent           DisplayString,
         iiopCompleteMessageTimeout INTEGER,
         iiopIdleConnectionTimeout INTEGER,
         iiopMaxMessageSize   INTEGER,
         iiopDefaultCharCodeset DisplayString,
         iiopDefaultMinorVersion INTEGER,
         iiopDefaultWideCharCodeset DisplayString,
         iiopTxMechanism      DisplayString,
         iiopUseStatefulAuthentication OCTET STRING,
         iiopUseJavaSerialization OCTET STRING,
         iiopUseFullRepositoryIdList OCTET STRING,
         iiopEnableIORServlet OCTET STRING,
         iiopSystemSecurity   OCTET STRING,
         iiopUseSerialFormatVersion2 OCTET STRING,
         iiopTags             OCTET STRING
      }
      
   
   iiopIndex OBJECT-TYPE
      SYNTAX      DisplayString (SIZE (1..16))
      MAX-ACCESS  read-only
      STATUS      current
      DESCRIPTION "Unique value directed from ObjectName which is used as table index"
      ::= { iiopEntry 1  }
   
   
   iiopObjectName OBJECT-TYPE
      SYNTAX      DisplayString (SIZE (1..256))
      MAX-ACCESS  read-only
      STATUS      current
      DESCRIPTION "JMX-standard MBean name"
      ::= { iiopEntry 5  }
   
   
   iiopType OBJECT-TYPE
      SYNTAX      DisplayString (SIZE (1..64))
      MAX-ACCESS  read-only
      STATUS      current
      DESCRIPTION "Returns the type of the MBean. "
      ::= { iiopEntry 10  }
   
   
   iiopName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { iiopEntry 15  }
   
   
   iiopParent OBJECT-TYPE
      SYNTAX      DisplayString (SIZE (1..256))
      MAX-ACCESS  read-only
      STATUS      current
      DESCRIPTION "BEA-proprietary Parent object's identification, with syntax
      <type>:<name>"
      ::= { iiopEntry 20  }
   
   
   iiopCompleteMessageTimeout OBJECT-TYPE
      SYNTAX      INTEGER
      MAX-ACCESS  read-only
      STATUS      current
      DESCRIPTION "The maximum number of seconds spent waiting for a complete IIOP message to be received. This timeout helps guard against denial of service attacks in which a caller indicates that they will be sending a message of a certain size which they never finish sending. "
      ::= { iiopEntry 25  }
   
   
   iiopIdleConnectionTimeout OBJECT-TYPE
      SYNTAX      INTEGER
      MAX-ACCESS  read-only
      STATUS      current
      DESCRIPTION "The maximum number of seconds an IIOP connection is allowed to be idle before it is closed by the server. This timeout helps guard against server deadlock through too many open connections. "
      ::= { iiopEntry 30  }
   
   
   iiopMaxMessageSize OBJECT-TYPE
      SYNTAX      INTEGER
      MAX-ACCESS  read-only
      STATUS      current
      DESCRIPTION "The maximum IIOP message size allowable in a message header. This attribute attempts to prevent a denial of service attack whereby a caller attempts to force the server to allocate more memory than is available thereby keeping the server from responding quickly to other requests. An IIOP client can set this value using the -Dweblogic.MaxMessageSize property. "
      ::= { iiopEntry 35  }
   
   
   iiopDefaultCharCodeset OBJECT-TYPE
      SYNTAX      DisplayString
      MAX-ACCESS  read-only
      STATUS      current
      DESCRIPTION "The standard character code set that this server will publish as its native code set. (Older ORBs may have trouble interoperating with anything other than the default.) "
      ::= { iiopEntry 36  }
   
   
   iiopDefaultMinorVersion OBJECT-TYPE
      SYNTAX      INTEGER
      MAX-ACCESS  read-only
      STATUS      current
      DESCRIPTION "The default GIOP (General Inter-ORB Protocol) version that this server will negotiate for incoming connections. (You may have to modify the default to work with other vendor's ORBs.)  This attribute is useful for client orbs with broken GIOP 1.2 implementations. "
      ::= { iiopEntry 37  }
   
   
   iiopDefaultWideCharCodeset OBJECT-TYPE
      SYNTAX      DisplayString
      MAX-ACCESS  read-only
      STATUS      current
      DESCRIPTION "The wide character code set that this server will publish as its native code set. (Older ORBs may have trouble interoperating with anything other than the default.) "
      ::= { iiopEntry 38  }
   
   
   iiopTxMechanism OBJECT-TYPE
      SYNTAX      DisplayString
      MAX-ACCESS  read-only
      STATUS      current
      DESCRIPTION "The transaction mechanism used by IIOP invocations. The default is the Object Transaction Service (OTS) required by J2EE 1.3. "
      ::= { iiopEntry 39  }
   
   
   iiopUseStatefulAuthentication OBJECT-TYPE
      SYNTAX      OCTET STRING
      MAX-ACCESS  read-only
      STATUS      current
      DESCRIPTION "Specify whether to advertise RMI objects and EJBs as supporting stateful CSIv2. Stateful CSIv2 is more efficient than stateless, requiring only a single authentication step for each remote principal. Stateless CSIv2 requires per-request authentication. Stateful CSIv2 is not required by J2EE 1.3 and so some ORBs do not support it. Stateful CSIv2 is enabled by default. This property can be changed at the object-level by changing the object's &lt;stateful-authentication&gt; runtime descriptor property. "
      ::= { iiopEntry 40  }
   
   
   iiopUseJavaSerialization OBJECT-TYPE
      SYNTAX      OCTET STRING
      MAX-ACCESS  read-only
      STATUS      current
      DESCRIPTION "Specity whether to use java serialization for marshalling objects. Setting this property improves performance when marshalling objects with very large object graphs. "
      ::= { iiopEntry 41  }
   
   
   iiopUseFullRepositoryIdList OBJECT-TYPE
      SYNTAX      OCTET STRING
      MAX-ACCESS  read-only
      STATUS      current
      DESCRIPTION "Specify whether to use full Repository ID lists when sending value type information for custom-marshaled types. Full Repository ID lists allow C++ ORBS to truncate values to base types. For RMI-IIOP and Java ORBs doing this merely increases transmission overhead. JDK ORBs are known to have problems with these so setting this will prevent JDK ORB access from working. "
      ::= { iiopEntry 42  }
   
   
   iiopEnableIORServlet OBJECT-TYPE
      SYNTAX      OCTET STRING
      MAX-ACCESS  read-only
      STATUS      current
      DESCRIPTION "Enable getior servlet used to publish COS Naming Service IORs "
      ::= { iiopEntry 43  }
   
   
   iiopSystemSecurity OBJECT-TYPE
      SYNTAX      OCTET STRING
      MAX-ACCESS  read-only
      STATUS      current
      DESCRIPTION "Specify the value System Security. The following variables are affected. clientCertAuthentication, clientAuthentication, identityAssertion confidentiality, integrity. The value set in this MBean would only be picked up if the value set in RTD.xml is 'config'. "
      ::= { iiopEntry 44  }
   
   
   iiopUseSerialFormatVersion2 OBJECT-TYPE
      SYNTAX      OCTET STRING
      MAX-ACCESS  read-only
      STATUS      current
      DESCRIPTION "Specify whether to advertise RMI objects and EJBs as supporting RMI-IIOP serial format version 2 for custom marshaled objects. "
      ::= { iiopEntry 45  }
   
   
   iiopTags OBJECT-TYPE
      SYNTAX      OCTET STRING
      MAX-ACCESS  read-only
      STATUS      current
      DESCRIPTION "Return all tags on this Configuration MBean "
      ::= { iiopEntry 46  }
   
   
   jdbcDataSourceFactoryTable OBJECT-TYPE
      SYNTAX      SEQUENCE OF JdbcDataSourceFactoryEntry
      MAX-ACCESS  not-accessible
      STATUS      current
      DESCRIPTION "This table represents a jdbcDataSourceFactory in the domain."
      ::= { wls 575  }
      
   
   jdbcDataSourceFactoryEntry OBJECT-TYPE
      SYNTAX      JdbcDataSourceFactoryEntry
      MAX-ACCESS  not-accessible
      STATUS      current
      DESCRIPTION "Entry of jdbcDataSourceFactoryTable"
      INDEX { jdbcDataSourceFactoryIndex}
      ::= { jdbcDataSourceFactoryTable 1 }
      
   JdbcDataSourceFactoryEntry ::=
      SEQUENCE
      {
         jdbcDataSourceFactoryIndex DisplayString,
         jdbcDataSourceFactoryObjectName DisplayString,
         jdbcDataSourceFactoryType DisplayString,
         jdbcDataSourceFactoryName DisplayString,
         jdbcDataSourceFactoryParent DisplayString,
         jdbcDataSourceFactoryDriverClassName DisplayString,
         jdbcDataSourceFactoryFactoryName DisplayString,
         jdbcDataSourceFactoryURL DisplayString,
         jdbcDataSourceFactoryUserName DisplayString
      }
      
   
   jdbcDataSourceFactoryIndex OBJECT-TYPE
      SYNTAX      DisplayString (SIZE (1..16))
      MAX-ACCESS  read-only
      STATUS      current
      DESCRIPTION "Unique value directed from ObjectName which is used as table index"
      ::= { jdbcDataSourceFactoryEntry 1  }
   
   
   jdbcDataSourceFactoryObjectName OBJECT-TYPE
      SYNTAX      DisplayString (SIZE (1..256))
      MAX-ACCESS  read-only
      STATUS      current
      DESCRIPTION "JMX-standard MBean name"
      ::= { jdbcDataSourceFactoryEntry 5  }
   
   
   jdbcDataSourceFactoryType OBJECT-TYPE
      SYNTAX      DisplayString (SIZE (1..64))
      MAX-ACCESS  read-only
      STATUS      current
      DESCRIPTION "BEA-proprietary MBean type"
      ::= { jdbcDataSourceFactoryEntry 10  }
   
   
   jdbcDataSourceFactoryName OBJECT-TYPE
      SYNTAX      DisplayString (SIZE (1..64))
      MAX-ACCESS  read-only
      STATUS      current
      DESCRIPTION "BEA-proprietary MBean name"
      ::= { jdbcDataSourceFactoryEntry 15  }
   
   
   jdbcDataSourceFactoryParent OBJECT-TYPE
      SYNTAX      DisplayString (SIZE (1..256))
      MAX-ACCESS  read-only
      STATUS      current
      DESCRIPTION "BEA-proprietary Parent object's identification, with syntax
      <type>:<name>"
      ::= { jdbcDataSourceFactoryEntry 20  }
   
   
   jdbcDataSourceFactoryDriverClassName OBJECT-TYPE
      SYNTAX      DisplayString (SIZE (1..256))
      MAX-ACCESS  read-only
      STATUS      current
      DESCRIPTION "The name of the driver. This may be overridden by
      * driver-name in the descriptor."
      ::= { jdbcDataSourceFactoryEntry 25  }
   
   
   jdbcDataSourceFactoryFactoryName OBJECT-TYPE
      SYNTAX      DisplayString (SIZE (1..256))
      MAX-ACCESS  read-only
      STATUS      current
      DESCRIPTION "The name of this data source factory. This is referenced
      * from the connection-factory element in weblogic-application.xml."
      ::= { jdbcDataSourceFactoryEntry 30  }
   
   
   jdbcDataSourceFactoryURL OBJECT-TYPE
      SYNTAX      DisplayString (SIZE (1..256))
      MAX-ACCESS  read-only
      STATUS      current
      DESCRIPTION "The connection URL. This may be overridden by url in the descriptor."
      ::= { jdbcDataSourceFactoryEntry 35  }
   
   
   jdbcDataSourceFactoryUserName OBJECT-TYPE
      SYNTAX      DisplayString (SIZE (1..256))
      MAX-ACCESS  read-only
      STATUS      current
      DESCRIPTION "The database user name. This may be overridden by
      * user-name in the descriptor."
      ::= { jdbcDataSourceFactoryEntry 40  }
   
   
   jmsBridgeDestinationTable OBJECT-TYPE
      SYNTAX      SEQUENCE OF JmsBridgeDestinationEntry
      MAX-ACCESS  not-accessible
      STATUS      current
      DESCRIPTION "This MBean represents a messaging bridge destination for a JMS messaging product. Each messaging bridge consists of two destinations that are being bridged:    Source: The message producing destination. A bridge instance consumes messages from the source destination.    Target: The destination where a bridge instance forwards messages produced by the source destination.   "
      ::= { wls 595  }
      
   
   jmsBridgeDestinationEntry OBJECT-TYPE
      SYNTAX      JmsBridgeDestinationEntry
      MAX-ACCESS  not-accessible
      STATUS      current
      DESCRIPTION "Entry of jmsBridgeDestinationTable"
      INDEX { jmsBridgeDestinationIndex}
      ::= { jmsBridgeDestinationTable 1 }
      
   JmsBridgeDestinationEntry ::=
      SEQUENCE
      {
         jmsBridgeDestinationIndex DisplayString,
         jmsBridgeDestinationObjectName DisplayString,
         jmsBridgeDestinationType DisplayString,
         jmsBridgeDestinationName DisplayString,
         jmsBridgeDestinationParent DisplayString,
         jmsBridgeDestinationConnectionFactoryJNDIName DisplayString,
         jmsBridgeDestinationConnectionURL DisplayString,
         jmsBridgeDestinationDestinationJNDIName DisplayString,
         jmsBridgeDestinationDestinationType DisplayString,
         jmsBridgeDestinationInitialContextFactory DisplayString,
         jmsBridgeDestinationAdapterJNDIName OCTET STRING,
         jmsBridgeDestinationClasspath OCTET STRING,
         jmsBridgeDestinationUserName OCTET STRING,
         jmsBridgeDestinationTags OCTET STRING
      }
      
   
   jmsBridgeDestinationIndex OBJECT-TYPE
      SYNTAX      DisplayString (SIZE (1..16))
      MAX-ACCESS  read-only
      STATUS      current
      DESCRIPTION "Unique value directed from ObjectName which is used as table index"
      ::= { jmsBridgeDestinationEntry 1  }
   
   
   jmsBridgeDestinationObjectName OBJECT-TYPE
      SYNTAX      DisplayString (SIZE (1..256))
      MAX-ACCESS  read-only
      STATUS      current
      DESCRIPTION "JMX-standard MBean name"
      ::= { jmsBridgeDestinationEntry 5  }
   
   
   jmsBridgeDestinationType OBJECT-TYPE
      SYNTAX      DisplayString (SIZE (1..64))
      MAX-ACCESS  read-only
      STATUS      current
      DESCRIPTION "Returns the type of the MBean. "
      ::= { jmsBridgeDestinationEntry 10  }
   
   
   jmsBridgeDestinationName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { jmsBridgeDestinationEntry 15  }
   
   
   jmsBridgeDestinationParent OBJECT-TYPE
      SYNTAX      DisplayString (SIZE (1..256))
      MAX-ACCESS  read-only
      STATUS      current
      DESCRIPTION "BEA-proprietary Parent object's identification, with syntax
      <type>:<name>"
      ::= { jmsBridgeDestinationEntry 20  }
   
   
   jmsBridgeDestinationConnectionFactoryJNDIName OBJECT-TYPE
      SYNTAX      DisplayString (SIZE (1..32))
      MAX-ACCESS  read-only
      STATUS      current
      DESCRIPTION "The connection factory's JNDI name for this JMS bridge destination. "
      ::= { jmsBridgeDestinationEntry 25  }
   
   
   jmsBridgeDestinationConnectionURL OBJECT-TYPE
      SYNTAX      DisplayString (SIZE (1..2048))
      MAX-ACCESS  read-only
      STATUS      current
      DESCRIPTION "The connection URL for this JMS bridge destination. "
      ::= { jmsBridgeDestinationEntry 30  }
   
   
   jmsBridgeDestinationDestinationJNDIName OBJECT-TYPE
      SYNTAX      DisplayString (SIZE (1..2048))
      MAX-ACCESS  read-only
      STATUS      current
      DESCRIPTION "The destination JNDI name for this JMS bridge destination. "
      ::= { jmsBridgeDestinationEntry 35  }
   
   
   jmsBridgeDestinationDestinationType OBJECT-TYPE
      SYNTAX      DisplayString (SIZE (1..2048))
      MAX-ACCESS  read-only
      STATUS      current
      DESCRIPTION "The destination type (queue or topic) for this JMS bridge destination. "
      ::= { jmsBridgeDestinationEntry 40  }
   
   
   jmsBridgeDestinationInitialContextFactory OBJECT-TYPE
      SYNTAX      DisplayString (SIZE (1..2048))
      MAX-ACCESS  read-only
      STATUS      current
      DESCRIPTION "The initial context factory name for this JMS bridge destination. "
      ::= { jmsBridgeDestinationEntry 45  }
   
   
   jmsBridgeDestinationAdapterJNDIName OBJECT-TYPE
      SYNTAX      OCTET STRING
      MAX-ACCESS  read-only
      STATUS      current
      DESCRIPTION "The JNDI name of the adapter used to communicate with the specified destination.  This name is specified in the adapter's deployment descriptor file and is used by the WebLogic Server Connector container to bind the adapter in WebLogic Server JNDI. "
      ::= { jmsBridgeDestinationEntry 46  }
   
   
   jmsBridgeDestinationClasspath OBJECT-TYPE
      SYNTAX      OCTET STRING
      MAX-ACCESS  read-only
      STATUS      current
      DESCRIPTION "The CLASSPATH of the bridge destination.    Used mainly to connect to WebLogic Server 6.0 or earlier.    When connecting to a destination that is running on WebLogic Server 6.0 or earlier, the bridge destination must supply a CLASSPATH that indicates the locations of the classes for the earlier WebLogic Server implementation.    "
      ::= { jmsBridgeDestinationEntry 47  }
   
   
   jmsBridgeDestinationUserName OBJECT-TYPE
      SYNTAX      OCTET STRING
      MAX-ACCESS  read-only
      STATUS      current
      DESCRIPTION "The optional user name the adapter uses to access the bridge destination.  All operations on the specified destination are done using this user name and the corresponding password. Therefore, the User Name/Password for the source and target destinations must have permission to the access the underlying destinations in order for the messaging bridge to work. "
      ::= { jmsBridgeDestinationEntry 48  }
   
   
   jmsBridgeDestinationTags OBJECT-TYPE
      SYNTAX      OCTET STRING
      MAX-ACCESS  read-only
      STATUS      current
      DESCRIPTION "Return all tags on this Configuration MBean "
      ::= { jmsBridgeDestinationEntry 49  }
   
   
   jmsConnectionConsumerTable OBJECT-TYPE
      SYNTAX      SEQUENCE OF JmsConnectionConsumerEntry
      MAX-ACCESS  not-accessible
      STATUS      current
      DESCRIPTION "This table defines a connection consumer."
      ::= { wls 600  }
      
   
   jmsConnectionConsumerEntry OBJECT-TYPE
      SYNTAX      JmsConnectionConsumerEntry
      MAX-ACCESS  not-accessible
      STATUS      current
      DESCRIPTION "Entry of jmsConnectionConsumerTable"
      INDEX { jmsConnectionConsumerIndex}
      ::= { jmsConnectionConsumerTable 1 }
      
   JmsConnectionConsumerEntry ::=
      SEQUENCE
      {
         jmsConnectionConsumerIndex DisplayString,
         jmsConnectionConsumerObjectName DisplayString,
         jmsConnectionConsumerType DisplayString,
         jmsConnectionConsumerName DisplayString,
         jmsConnectionConsumerParent DisplayString,
         jmsConnectionConsumerMessagesMaximum INTEGER,
         jmsConnectionConsumerSelector DisplayString,
         jmsConnectionConsumerDestination DisplayString
      }
      
   
   jmsConnectionConsumerIndex OBJECT-TYPE
      SYNTAX      DisplayString (SIZE (1..16))
      MAX-ACCESS  read-only
      STATUS      current
      DESCRIPTION "Unique value directed from ObjectName which is used as table index"
      ::= { jmsConnectionConsumerEntry 1  }
   
   
   jmsConnectionConsumerObjectName OBJECT-TYPE
      SYNTAX      DisplayString (SIZE (1..256))
      MAX-ACCESS  read-only
      STATUS      current
      DESCRIPTION "JMX-standard MBean name"
      ::= { jmsConnectionConsumerEntry 5  }
   
   
   jmsConnectionConsumerType OBJECT-TYPE
      SYNTAX      DisplayString (SIZE (1..64))
      MAX-ACCESS  read-only
      STATUS      current
      DESCRIPTION "BEA-proprietary MBean type"
      ::= { jmsConnectionConsumerEntry 10  }
   
   
   jmsConnectionConsumerName OBJECT-TYPE
      SYNTAX      DisplayString (SIZE (1..64))
      MAX-ACCESS  read-only
      STATUS      current
      DESCRIPTION "BEA-proprietary MBean name"
      ::= { jmsConnectionConsumerEntry 15  }
   
   
   jmsConnectionConsumerParent OBJECT-TYPE
      SYNTAX      DisplayString (SIZE (1..256))
      MAX-ACCESS  read-only
      STATUS      current
      DESCRIPTION "BEA-proprietary Parent object's identification, with syntax
      <type>:<name>"
      ::= { jmsConnectionConsumerEntry 20  }
   
   
   jmsConnectionConsumerMessagesMaximum OBJECT-TYPE
      SYNTAX      INTEGER
      MAX-ACCESS  read-only
      STATUS      current
      DESCRIPTION "Return the defined maximum number of messages that the connection 
      consumer may load at one time into a ServerSession's session."
      ::= { jmsConnectionConsumerEntry 25  }
   
   
   jmsConnectionConsumerSelector OBJECT-TYPE
      SYNTAX      DisplayString (SIZE (1..256))
      MAX-ACCESS  read-only
      STATUS      current
      DESCRIPTION "Return the defined selector of the connection consumer."
      ::= { jmsConnectionConsumerEntry 30  }
   
   
   jmsConnectionConsumerDestination OBJECT-TYPE
      SYNTAX      DisplayString (SIZE (1..256))
      MAX-ACCESS  read-only
      STATUS      current
      DESCRIPTION "Return the JNDI name of the destination for this connection consumer"
      ::= { jmsConnectionConsumerEntry 35  }
   
   
   jmsDestCommonTable OBJECT-TYPE
      SYNTAX      SEQUENCE OF JmsDestCommonEntry
      MAX-ACCESS  not-accessible
      STATUS      current
      DESCRIPTION "This table represents a jmsDestCommon in the domain."
      ::= { wls 612  }
      
   
   jmsDestCommonEntry OBJECT-TYPE
      SYNTAX      JmsDestCommonEntry
      MAX-ACCESS  not-accessible
      STATUS      current
      DESCRIPTION "Entry of jmsDestCommonTable"
      INDEX { jmsDestCommonIndex}
      ::= { jmsDestCommonTable 1 }
      
   JmsDestCommonEntry ::=
      SEQUENCE
      {
         jmsDestCommonIndex   DisplayString,
         jmsDestCommonObjectName DisplayString,
         jmsDestCommonType    DisplayString,
         jmsDestCommonName    DisplayString,
         jmsDestCommonParent  DisplayString,
         jmsDestCommonBytesMaximum INTEGER,
         jmsDestCommonBytesThresholdHigh INTEGER,
         jmsDestCommonBytesThresholdLow INTEGER,
         jmsDestCommonDeliveryModeOverride DisplayString,
         jmsDestCommonMessagesMaximum INTEGER,
         jmsDestCommonMessagesThresholdHigh INTEGER,
         jmsDestCommonMessagesThresholdLow INTEGER,
         jmsDestCommonPriorityOverride INTEGER,
         jmsDestCommonRedeliveryDelayOverride INTEGER,
         jmsDestCommonRedeliveryLimit INTEGER,
         jmsDestCommonTimeToDeliverOverride DisplayString,
         jmsDestCommonTimeToLiveOverride INTEGER
      }
      
   
   jmsDestCommonIndex OBJECT-TYPE
      SYNTAX      DisplayString (SIZE (1..16))
      MAX-ACCESS  read-only
      STATUS      current
      DESCRIPTION "Unique value directed from ObjectName which is used as table index"
      ::= { jmsDestCommonEntry 1  }
   
   
   jmsDestCommonObjectName OBJECT-TYPE
      SYNTAX      DisplayString (SIZE (1..256))
      MAX-ACCESS  read-only
      STATUS      current
      DESCRIPTION "JMX-standard MBean name"
      ::= { jmsDestCommonEntry 5  }
   
   
   jmsDestCommonType OBJECT-TYPE
      SYNTAX      DisplayString (SIZE (1..64))
      MAX-ACCESS  read-only
      STATUS      current
      DESCRIPTION "BEA-proprietary MBean type"
      ::= { jmsDestCommonEntry 10  }
   
   
   jmsDestCommonName OBJECT-TYPE
      SYNTAX      DisplayString (SIZE (1..64))
      MAX-ACCESS  read-only
      STATUS      current
      DESCRIPTION "BEA-proprietary MBean name"
      ::= { jmsDestCommonEntry 15  }
   
   
   jmsDestCommonParent OBJECT-TYPE
      SYNTAX      DisplayString (SIZE (1..256))
      MAX-ACCESS  read-only
      STATUS      current
      DESCRIPTION "BEA-proprietary Parent object's identification, with syntax
      <type>:<name>"
      ::= { jmsDestCommonEntry 20  }
   
   
   jmsDestCommonBytesMaximum OBJECT-TYPE
      SYNTAX      INTEGER
      MAX-ACCESS  read-only
      STATUS      current
      DESCRIPTION "Returns the value of BytesMaximum."
      ::= { jmsDestCommonEntry 25  }
   
   
   jmsDestCommonBytesThresholdHigh OBJECT-TYPE
      SYNTAX      INTEGER
      MAX-ACCESS  read-only
      STATUS      current
      DESCRIPTION "Returns the value of BytesThresholdHigh."
      ::= { jmsDestCommonEntry 30  }
   
   
   jmsDestCommonBytesThresholdLow OBJECT-TYPE
      SYNTAX      INTEGER
      MAX-ACCESS  read-only
      STATUS      current
      DESCRIPTION "Returns the value of BytesThresholdLow."
      ::= { jmsDestCommonEntry 35  }
   
   
   jmsDestCommonDeliveryModeOverride OBJECT-TYPE
      SYNTAX      DisplayString (SIZE (1..256))
      MAX-ACCESS  read-only
      STATUS      current
      DESCRIPTION "Returns the DeliveryModeOverride value."
      ::= { jmsDestCommonEntry 40  }
   
   
   jmsDestCommonMessagesMaximum OBJECT-TYPE
      SYNTAX      INTEGER
      MAX-ACCESS  read-only
      STATUS      current
      DESCRIPTION "Returns the values of MessagesMaximum."
      ::= { jmsDestCommonEntry 45  }
   
   
   jmsDestCommonMessagesThresholdHigh OBJECT-TYPE
      SYNTAX      INTEGER
      MAX-ACCESS  read-only
      STATUS      current
      DESCRIPTION "Returns the values of MessagesThresholdHigh."
      ::= { jmsDestCommonEntry 50  }
   
   
   jmsDestCommonMessagesThresholdLow OBJECT-TYPE
      SYNTAX      INTEGER
      MAX-ACCESS  read-only
      STATUS      current
      DESCRIPTION "Returns the values of MessagesThresholdLow."
      ::= { jmsDestCommonEntry 55  }
   
   
   jmsDestCommonPriorityOverride OBJECT-TYPE
      SYNTAX      INTEGER
      MAX-ACCESS  read-only
      STATUS      current
      DESCRIPTION "Returns the values of PriorityOverride."
      ::= { jmsDestCommonEntry 65  }
   
   
   jmsDestCommonRedeliveryDelayOverride OBJECT-TYPE
      SYNTAX      INTEGER
      MAX-ACCESS  read-only
      STATUS      current
      DESCRIPTION "Returns the values of RedeliveryDelayOverride."
      ::= { jmsDestCommonEntry 70  }
   
   
   jmsDestCommonRedeliveryLimit OBJECT-TYPE
      SYNTAX      INTEGER
      MAX-ACCESS  read-only
      STATUS      current
      DESCRIPTION "Returns the values of RedeliveryLimit."
      ::= { jmsDestCommonEntry 75  }
   
   
   jmsDestCommonTimeToDeliverOverride OBJECT-TYPE
      SYNTAX      DisplayString (SIZE (1..256))
      MAX-ACCESS  read-only
      STATUS      current
      DESCRIPTION "Returns the values of TimeToDeliverOverride."
      ::= { jmsDestCommonEntry 80  }
   
   
   jmsDestCommonTimeToLiveOverride OBJECT-TYPE
      SYNTAX      INTEGER
      MAX-ACCESS  read-only
      STATUS      current
      DESCRIPTION "Returns the values of TimeToLiveOverride."
      ::= { jmsDestCommonEntry 85  }
   
   
   jmsDestinationTable OBJECT-TYPE
      SYNTAX      SEQUENCE OF JmsDestinationEntry
      MAX-ACCESS  not-accessible
      STATUS      current
      DESCRIPTION "This table represents a jmsDestination in the domain."
      ::= { wls 615  }
      
   
   jmsDestinationEntry OBJECT-TYPE
      SYNTAX      JmsDestinationEntry
      MAX-ACCESS  not-accessible
      STATUS      current
      DESCRIPTION "Entry of jmsDestinationTable"
      INDEX { jmsDestinationIndex}
      ::= { jmsDestinationTable 1 }
      
   JmsDestinationEntry ::=
      SEQUENCE
      {
         jmsDestinationIndex  DisplayString,
         jmsDestinationObjectName DisplayString,
         jmsDestinationType   DisplayString,
         jmsDestinationName   DisplayString,
         jmsDestinationParent DisplayString,
         jmsDestinationBytesPagingEnabled DisplayString,
         jmsDestinationJNDIName DisplayString,
         jmsDestinationMessagesPagingEnabled DisplayString,
         jmsDestinationStoreEnabled DisplayString,
         jmsDestinationJNDINameReplicated DisplayString
      }
      
   
   jmsDestinationIndex OBJECT-TYPE
      SYNTAX      DisplayString (SIZE (1..16))
      MAX-ACCESS  read-only
      STATUS      current
      DESCRIPTION "Unique value directed from ObjectName which is used as table index"
      ::= { jmsDestinationEntry 1  }
   
   
   jmsDestinationObjectName OBJECT-TYPE
      SYNTAX      DisplayString (SIZE (1..256))
      MAX-ACCESS  read-only
      STATUS      current
      DESCRIPTION "JMX-standard MBean name"
      ::= { jmsDestinationEntry 5  }
   
   
   jmsDestinationType OBJECT-TYPE
      SYNTAX      DisplayString (SIZE (1..64))
      MAX-ACCESS  read-only
      STATUS      current
      DESCRIPTION "BEA-proprietary MBean type"
      ::= { jmsDestinationEntry 10  }
   
   
   jmsDestinationName OBJECT-TYPE
      SYNTAX      DisplayString (SIZE (1..64))
      MAX-ACCESS  read-only
      STATUS      current
      DESCRIPTION "BEA-proprietary MBean name"
      ::= { jmsDestinationEntry 15  }
   
   
   jmsDestinationParent OBJECT-TYPE
      SYNTAX      DisplayString (SIZE (1..256))
      MAX-ACCESS  read-only
      STATUS      current
      DESCRIPTION "BEA-proprietary Parent object's identification, with syntax
      <type>:<name>"
      ::= { jmsDestinationEntry 20  }
   
   
   jmsDestinationBytesPagingEnabled OBJECT-TYPE
      SYNTAX      DisplayString (SIZE (1..256))
      MAX-ACCESS  read-only
      STATUS      current
      DESCRIPTION "returns true or false."
      ::= { jmsDestinationEntry 25  }
   
   
   jmsDestinationJNDIName OBJECT-TYPE
      SYNTAX      DisplayString (SIZE (1..256))
      MAX-ACCESS  read-only
      STATUS      current
      DESCRIPTION "Returns the JNDI name of the destination."
      ::= { jmsDestinationEntry 30  }
   
   
   jmsDestinationMessagesPagingEnabled OBJECT-TYPE
      SYNTAX      DisplayString (SIZE (1..256))
      MAX-ACCESS  read-only
      STATUS      current
      DESCRIPTION "pagiing enablesd."
      ::= { jmsDestinationEntry 35  }
   
   
   jmsDestinationStoreEnabled OBJECT-TYPE
      SYNTAX      DisplayString (SIZE (1..256))
      MAX-ACCESS  read-only
      STATUS      current
      DESCRIPTION "store enablesd."
      ::= { jmsDestinationEntry 40  }
   
   
   jmsDestinationJNDINameReplicated OBJECT-TYPE
      SYNTAX      DisplayString (SIZE (1..256))
      MAX-ACCESS  read-only
      STATUS      current
      DESCRIPTION "jndi name enabled."
      ::= { jmsDestinationEntry 45  }
   
   
   jmsDistributedDestinationTable OBJECT-TYPE
      SYNTAX      SEQUENCE OF JmsDistributedDestinationEntry
      MAX-ACCESS  not-accessible
      STATUS      current
      DESCRIPTION "This table represents a key value for a destination"
      ::= { wls 623  }
      
   
   jmsDistributedDestinationEntry OBJECT-TYPE
      SYNTAX      JmsDistributedDestinationEntry
      MAX-ACCESS  not-accessible
      STATUS      current
      DESCRIPTION "Entry of jmsDistributedDestinationTable"
      INDEX { jmsDistributedDestinationIndex}
      ::= { jmsDistributedDestinationTable 1 }
      
   JmsDistributedDestinationEntry ::=
      SEQUENCE
      {
         jmsDistributedDestinationIndex DisplayString,
         jmsDistributedDestinationObjectName DisplayString,
         jmsDistributedDestinationType DisplayString,
         jmsDistributedDestinationName DisplayString,
         jmsDistributedDestinationParent DisplayString,
         jmsDistributedDestinationLoadBalancingPolicy DisplayString
      }
      
   
   jmsDistributedDestinationIndex OBJECT-TYPE
      SYNTAX      DisplayString (SIZE (1..16))
      MAX-ACCESS  read-only
      STATUS      current
      DESCRIPTION "Unique value directed from ObjectName which is used as table index"
      ::= { jmsDistributedDestinationEntry 1  }
   
   
   jmsDistributedDestinationObjectName OBJECT-TYPE
      SYNTAX      DisplayString (SIZE (1..256))
      MAX-ACCESS  read-only
      STATUS      current
      DESCRIPTION "JMX-standard MBean name"
      ::= { jmsDistributedDestinationEntry 5  }
   
   
   jmsDistributedDestinationType OBJECT-TYPE
      SYNTAX      DisplayString (SIZE (1..64))
      MAX-ACCESS  read-only
      STATUS      current
      DESCRIPTION "BEA-proprietary MBean type"
      ::= { jmsDistributedDestinationEntry 10  }
   
   
   jmsDistributedDestinationName OBJECT-TYPE
      SYNTAX      DisplayString (SIZE (1..64))
      MAX-ACCESS  read-only
      STATUS      current
      DESCRIPTION "BEA-proprietary MBean name"
      ::= { jmsDistributedDestinationEntry 15  }
   
   
   jmsDistributedDestinationParent OBJECT-TYPE
      SYNTAX      DisplayString (SIZE (1..256))
      MAX-ACCESS  read-only
      STATUS      current
      DESCRIPTION "BEA-proprietary Parent object's identification, with syntax
      <type>:<name>"
      ::= { jmsDistributedDestinationEntry 20  }
   
   
   jmsDistributedDestinationLoadBalancingPolicy OBJECT-TYPE
      SYNTAX      DisplayString
      MAX-ACCESS  read-only
      STATUS      current
      DESCRIPTION "Generated Object."
      ::= { jmsDistributedDestinationEntry 21  }
   
   
   jmsDistributedDestinationMemberTable OBJECT-TYPE
      SYNTAX      SEQUENCE OF JmsDistributedDestinationMemberEntry
      MAX-ACCESS  not-accessible
      STATUS      current
      DESCRIPTION "A JMS file based backing store."
      ::= { wls 624  }
      
   
   jmsDistributedDestinationMemberEntry OBJECT-TYPE
      SYNTAX      JmsDistributedDestinationMemberEntry
      MAX-ACCESS  not-accessible
      STATUS      current
      DESCRIPTION "Entry of jmsDistributedDestinationMemberTable"
      INDEX { jmsDistributedDestinationMemberIndex}
      ::= { jmsDistributedDestinationMemberTable 1 }
      
   JmsDistributedDestinationMemberEntry ::=
      SEQUENCE
      {
         jmsDistributedDestinationMemberIndex DisplayString,
         jmsDistributedDestinationMemberObjectName DisplayString,
         jmsDistributedDestinationMemberType DisplayString,
         jmsDistributedDestinationMemberName DisplayString,
         jmsDistributedDestinationMemberParent DisplayString,
         jmsDistributedDestinationMemberWeight INTEGER
      }
      
   
   jmsDistributedDestinationMemberIndex OBJECT-TYPE
      SYNTAX      DisplayString (SIZE (1..16))
      MAX-ACCESS  read-only
      STATUS      current
      DESCRIPTION "Unique value directed from ObjectName which is used as table index"
      ::= { jmsDistributedDestinationMemberEntry 1  }
   
   
   jmsDistributedDestinationMemberObjectName OBJECT-TYPE
      SYNTAX      DisplayString (SIZE (1..256))
      MAX-ACCESS  read-only
      STATUS      current
      DESCRIPTION "JMX-standard MBean name"
      ::= { jmsDistributedDestinationMemberEntry 5  }
   
   
   jmsDistributedDestinationMemberType OBJECT-TYPE
      SYNTAX      DisplayString (SIZE (1..64))
      MAX-ACCESS  read-only
      STATUS      current
      DESCRIPTION "BEA-proprietary MBean type"
      ::= { jmsDistributedDestinationMemberEntry 10  }
   
   
   jmsDistributedDestinationMemberName OBJECT-TYPE
      SYNTAX      DisplayString (SIZE (1..64))
      MAX-ACCESS  read-only
      STATUS      current
      DESCRIPTION "BEA-proprietary MBean name"
      ::= { jmsDistributedDestinationMemberEntry 15  }
   
   
   jmsDistributedDestinationMemberParent OBJECT-TYPE
      SYNTAX      DisplayString (SIZE (1..256))
      MAX-ACCESS  read-only
      STATUS      current
      DESCRIPTION "BEA-proprietary Parent object's identification, with syntax
      <type>:<name>"
      ::= { jmsDistributedDestinationMemberEntry 20  }
   
   
   jmsDistributedDestinationMemberWeight OBJECT-TYPE
      SYNTAX      INTEGER
      MAX-ACCESS  read-only
      STATUS      current
      DESCRIPTION "Generated Object."
      ::= { jmsDistributedDestinationMemberEntry 21  }
   
   
   jmsServerTable OBJECT-TYPE
      SYNTAX      SEQUENCE OF JmsServerEntry
      MAX-ACCESS  not-accessible
      STATUS      current
      DESCRIPTION "This class represents a JMS server. A JMS server manages connections and message requests on behalf of clients. "
      ::= { wls 660  }
      
   
   jmsServerEntry OBJECT-TYPE
      SYNTAX      JmsServerEntry
      MAX-ACCESS  not-accessible
      STATUS      current
      DESCRIPTION "Entry of jmsServerTable"
      INDEX { jmsServerIndex}
      ::= { jmsServerTable 1 }
      
   JmsServerEntry ::=
      SEQUENCE
      {
         jmsServerIndex       DisplayString,
         jmsServerObjectName  DisplayString,
         jmsServerType        DisplayString,
         jmsServerName        DisplayString,
         jmsServerParent      DisplayString,
         jmsServerBytesMaximum INTEGER,
         jmsServerBytesThresholdHigh INTEGER,
         jmsServerBytesThresholdLow INTEGER,
         jmsServerMessagesMaximum INTEGER,
         jmsServerMessagesThresholdHigh INTEGER,
         jmsServerMessagesThresholdLow INTEGER,
         jmsServerInsertionPausedAtStartup OCTET STRING,
         jmsServerStoreEnabled OCTET STRING,
         jmsServerAllowsPersistentDowngrade OCTET STRING,
         jmsServerExpirationScanInterval INTEGER,
         jmsServerProductionPausedAtStartup OCTET STRING,
         jmsServerTemporaryTemplateName OCTET STRING,
         jmsServerMaximumMessageSize INTEGER,
         jmsServerDeploymentOrder INTEGER,
         jmsServerMessageBufferSize Counter64,
         jmsServerBlockingSendPolicy OCTET STRING,
         jmsServerHostingTemporaryDestinations OCTET STRING,
         jmsServerPagingDirectory OCTET STRING,
         jmsServerTemporaryTemplateResource OCTET STRING,
         jmsServerConsumptionPausedAtStartup OCTET STRING,
         jmsServerMessagesPagingEnabled OCTET STRING,
         jmsServerBytesPagingEnabled OCTET STRING,
         jmsServerPagingMinWindowBufferSize INTEGER,
         jmsServerPagingFileLockingEnabled OCTET STRING,
         jmsServerPagingIoBufferSize INTEGER,
         jmsServerPagingBlockSize INTEGER,
         jmsServerPagingMaxFileSize Counter64,
         jmsServerPagingMaxWindowBufferSize INTEGER,
         jmsServerMessageCompressionOptions OCTET STRING,
         jmsServerPagingMessageCompressionEnabled OCTET STRING,
         jmsServerStoreMessageCompressionEnabled OCTET STRING,
         jmsServerTags        OCTET STRING
      }
      
   
   jmsServerIndex OBJECT-TYPE
      SYNTAX      DisplayString (SIZE (1..16))
      MAX-ACCESS  read-only
      STATUS      current
      DESCRIPTION "Unique value directed from ObjectName which is used as table index"
      ::= { jmsServerEntry 1  }
   
   
   jmsServerObjectName OBJECT-TYPE
      SYNTAX      DisplayString (SIZE (1..256))
      MAX-ACCESS  read-only
      STATUS      current
      DESCRIPTION "JMX-standard MBean name"
      ::= { jmsServerEntry 5  }
   
   
   jmsServerType OBJECT-TYPE
      SYNTAX      DisplayString (SIZE (1..64))
      MAX-ACCESS  read-only
      STATUS      current
      DESCRIPTION "Returns the type of the MBean. "
      ::= { jmsServerEntry 10  }
   
   
   jmsServerName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { jmsServerEntry 15  }
   
   
   jmsServerParent OBJECT-TYPE
      SYNTAX      DisplayString (SIZE (1..256))
      MAX-ACCESS  read-only
      STATUS      current
      DESCRIPTION "BEA-proprietary Parent object's identification, with syntax
      <type>:<name>"
      ::= { jmsServerEntry 20  }
   
   
   jmsServerBytesMaximum OBJECT-TYPE
      SYNTAX      INTEGER
      MAX-ACCESS  read-only
      STATUS      current
      DESCRIPTION "The maximum number of bytes that can be stored in this JMS server. A value of -1 removes any WebLogic Server limits.  Because excessive bytes volume can cause memory saturation, Oracle recommends that this maximum corresponds to the total amount of system memory available after accounting for the rest of your application load.  Range of Values: &gt;= BytesThresholdHigh "
      ::= { jmsServerEntry 45  }
   
   
   jmsServerBytesThresholdHigh OBJECT-TYPE
      SYNTAX      INTEGER
      MAX-ACCESS  read-only
      STATUS      current
      DESCRIPTION "The upper threshold (number of bytes stored in this JMS server) that triggers flow control and logging events. A value of -1 disables the events for this JMS server.  The triggered events are:   Log Messages - A message is logged on the server indicating a high threshold condition.   Flow Control - If flow control is enabled, the JMS server becomes armed and instructs producers to begin decreasing their message flow.    Range of Values: &lt;= BytesMaximum; &gt;= BytesThresholdLow "
      ::= { jmsServerEntry 50  }
   
   
   jmsServerBytesThresholdLow OBJECT-TYPE
      SYNTAX      INTEGER
      MAX-ACCESS  read-only
      STATUS      current
      DESCRIPTION "The lower threshold (number of bytes stored in this JMS server) that triggers flow control and logging events. A value of -1 disables the events for this JMS server.  If the number of bytes falls below this threshold, the triggered events are:   Log Messages - A message is logged on the server indicating that the threshold condition has cleared.   Flow Control - If flow control is enabled, the JMS server becomes disarmed and instructs producers to begin increasing their message flow.    Range of Values: &lt;= BytesThresholdHigh "
      ::= { jmsServerEntry 55  }
   
   
   jmsServerMessagesMaximum OBJECT-TYPE
      SYNTAX      INTEGER
      MAX-ACCESS  read-only
      STATUS      current
      DESCRIPTION "The maximum number of messages that can be stored in this JMS server. A value of -1 removes any WebLogic Server limits.  Because excessive message volume can cause memory saturation, Oracle recommends that this value corresponds to the total amount of system memory available after accounting for the rest of your application load.  Range of Values: &gt;= MessagesThresholdHigh. "
      ::= { jmsServerEntry 60  }
   
   
   jmsServerMessagesThresholdHigh OBJECT-TYPE
      SYNTAX      INTEGER
      MAX-ACCESS  read-only
      STATUS      current
      DESCRIPTION "The upper threshold (number of messages stored in this JMS server) that triggers flow control and logging events. A value of -1 disables the events for this JMS server.  If the number of messages exceeds this threshold, the triggered events are:   Log Messages - A message is logged on the server indicating a high threshold condition.   Flow Control - If flow control is enabled, the JMS server becomes armed and instructs producers to begin decreasing their message flow.    Range of Values: &lt;= MessagesMaximum; &gt;= MessagesThresholdLow. "
      ::= { jmsServerEntry 65  }
   
   
   jmsServerMessagesThresholdLow OBJECT-TYPE
      SYNTAX      INTEGER
      MAX-ACCESS  read-only
      STATUS      current
      DESCRIPTION "The lower threshold (number of messages stored in this JMS server) that triggers flow control and logging events. A value of -1 disables the events for this JMS server.  If the number of messages falls below this threshold, the triggered events are:   Log Messages - A message is logged on the server indicating that the threshold condition has cleared.   Flow Control - If flow control is enabled, the JMS server becomes disarmed and instructs producers to begin increasing their message flow.    Note: This attribute is dynamically configurable.  Range of Values: &lt;= MessagesThresholdHigh "
      ::= { jmsServerEntry 70  }
   
   
   jmsServerInsertionPausedAtStartup OBJECT-TYPE
      SYNTAX      OCTET STRING
      MAX-ACCESS  read-only
      STATUS      current
      DESCRIPTION "Indicates whether insertion is paused at startup on destinations targeted to this JMS server. A destination cannot receive any new messages while it is paused.  When the value is set to true, then immediately after the host server instance is booted, then this JMS server and its targeted destinations are modified such that they are in a 'insertion paused' state, which results preventing messages that are result of the 'in-flight' work completion to arrive on those destinations.  Note: For a detailed definition of 'in-flight' work/messages, see weblogic.management.runtime.JMSServerRuntimeMBean#resumeInsertion and weblogic.management.runtime.JMSDestinationRuntime#resumeInsertion  To allow in-flight work messages to appear on the destinations, later you will have to change the state of this JMS server to an 'insertion enabled' state by setting this value to false, and then either redeploy the JMS server or reboot the hosting server instance.  When the value is set to default, then the Insertion Paused At Startup is determined based on the corresponding setting on the individual destination.  If the value is changed and activated, you need to restart any servers to which the MBean is targeted before the value will take effect (even though you do not get a warning in the Console that the server needs to be restarted). "
      ::= { jmsServerEntry 71  }
   
   
   jmsServerStoreEnabled OBJECT-TYPE
      SYNTAX      OCTET STRING
      MAX-ACCESS  read-only
      STATUS      current
      DESCRIPTION " Specifies whether message persistence is supported for this JMS server.  When set to true: If the JMS server has no store configured, the targeted WebLogic Server instance's default store is used to store persistent messages. If the JMS server has a store configured, then the configured store is used to store persistent messages.   When set to false, then this JMS server does not support persistent messages, and instead downgrades them to non-persistent.  The default value is true.   Oracle recommends not setting this parameter to false. It is available to provide compatibility with older releases.  If the value is changed and activated, you need to restart any servers to which the MBean is targeted before the value will take effect (even though you do not get a warning in the Console that the server needs to be restarted). "
      ::= { jmsServerEntry 72  }
   
   
   jmsServerAllowsPersistentDowngrade OBJECT-TYPE
      SYNTAX      OCTET STRING
      MAX-ACCESS  read-only
      STATUS      current
      DESCRIPTION "Specifies whether JMS clients will get an exception when sending persistent messages to a destination targeted to a JMS server that does not have a persistent store configured. This parameter only has effect when the Store Enabled parameter is disabled (false).  When set to false, the default, clients will get an exception when sending persistent messages to a JMS server with no store configured. When set to true, then persistent messages are downgraded to non-persistent; however, the send operations are allowed to continue. "
      ::= { jmsServerEntry 73  }
   
   
   jmsServerExpirationScanInterval OBJECT-TYPE
      SYNTAX      INTEGER
      MAX-ACCESS  read-only
      STATUS      current
      DESCRIPTION "The number of seconds between this JMS server's cycles of scanning local destinations for expired messages. A value of 0 disables active scanning. A very large scan interval effectively disables active scanning.  With scanning disabled, users still do not receive expired messages and any expired messages that are discovered by other system activities are removed. However, expired messages sitting in idle destinations (such as an inactive queue or disconnected durable subscriber) are not removed and continue to consume system resources.  The scanning cycle for expired messages occurs as follows:   After the specified waiting period, the JMS server devotes a separate thread to scan all of its local destinations for expired messages.   After the scanning is completed, all located expired messages are processed according to the specified Expiration Policy on the destination (Discard, Log, or Redirect).   The entire process repeats after another specified waiting period.    Note: Because a new scan does not start until the current one is finished and until the specified waiting period ends, an expired message could still remain in the system for the maximum scan waiting period plus the amount of time it takes to perform the scan. "
      ::= { jmsServerEntry 74  }
   
   
   jmsServerProductionPausedAtStartup OBJECT-TYPE
      SYNTAX      OCTET STRING
      MAX-ACCESS  read-only
      STATUS      current
      DESCRIPTION "Specifies whether production is paused at server startup on destinations targeted to this JMS server. A destination cannot receive any new messages while it is paused.  When the value is set to true, then immediately after the host server instance is rebooted, then this JMS server and its targeted destinations are modified such that they are in a 'production paused' state, which results in preventing new message production activities on those destinations.  To resume normal new message production activity, later you will have to change the state of this JMS server to a 'production enabled' state by setting this value to false, and then either redeploy the JMS server or reboot the hosting server instance.   When the value is set to default, then the Production Paused At Startup is determined based on the corresponding setting on the individual destination.  If the value is changed and activated, you need to restart any servers to which the MBean is targeted before the value will take effect (even though you do not get a warning in the Console that the server needs to be restarted). "
      ::= { jmsServerEntry 75  }
   
   
   jmsServerTemporaryTemplateName OBJECT-TYPE
      SYNTAX      OCTET STRING
      MAX-ACCESS  read-only
      STATUS      current
      DESCRIPTION "The name of a configured JMS template that this JMS server uses to create temporary destinations.  Entering a template name, requires you to specify the JMS module that contains this template. However, a template name cannot be specified if the Hosting Temporary Destinations field is disabled.  Note: If the specified JMS template provides persistent store values, they are ignored because temporary destinations do not support persistent messaging. "
      ::= { jmsServerEntry 76  }
   
   
   jmsServerMaximumMessageSize OBJECT-TYPE
      SYNTAX      INTEGER
      MAX-ACCESS  read-only
      STATUS      current
      DESCRIPTION "The maximum number of bytes allowed in individual messages on this JMS server. The size of a message includes the message body, any user-defined properties, and the user-defined JMS header fields JMSCorrelationID and JMSType.  The maximum message size is only enforced for the initial production of a message. Messages that are redirected to an error destination or forwarded to a member of a distributed destination are not checked for size. For instance, if a destination and its corresponding error destination are configured with a maximum message size of 128K bytes and 64K bytes, respectively, a message of 96K bytes could be redirected to the error destination (even though it exceeds the 64K byte maximum), but a producer could not directly send the 96K byte message to the error destination.  Note: Any change to this maximum affects only incoming messages; stored messages are not affected. "
      ::= { jmsServerEntry 77  }
   
   
   jmsServerDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { jmsServerEntry 78  }
   
   
   jmsServerMessageBufferSize OBJECT-TYPE
      SYNTAX      Counter64
      MAX-ACCESS  read-only
      STATUS      current
      DESCRIPTION "The amount of memory (in bytes) that this JMS server can use to store message bodies before it writes them to disk. When the JMS server writes the message bodies to disk, it clears them from memory.  A value of -1 (the default) specifies that the server will automatically determine a size based on the maximum heap size of the JVM. This default will be set to either one-third the maximum heap size, or 512 megabytes, whichever is smaller.  The larger the buffer, the more memory JMS will consume when many messages are waiting on queues or topics. Once the buffer is surpassed, JMS may write message bodies to the directory specified by PagingDirectory in an effort to reduce memory usage below this buffer.  Surpassing the buffer size does not stop the JMS server from accepting new messages. It is still possible to run out of memory if messages are arriving faster than they can be written to disk. Users with high messaging loads who wish to support the highest possible availability should consider setting a quota or setting a threshold and enabling flow control.  Paging is always supported. "
      ::= { jmsServerEntry 79  }
   
   
   jmsServerBlockingSendPolicy OBJECT-TYPE
      SYNTAX      OCTET STRING
      MAX-ACCESS  read-only
      STATUS      current
      DESCRIPTION "Determines whether the JMS server delivers smaller messages before larger ones when a destination has exceeded its maximum number of messages. FIFO prevents the JMS server from delivering smaller messages when larger ones are already waiting for space. Preemptive allows smaller send requests to preempt previous larger ones when there is sufficient space for smaller messages on the destination.  This policy is defined only for the JMS server; it cannot be set on individual destinations.  Additional information on the FIFO and Preemptive policies is provided below.  FIFO (first in, first out) indicates that all send requests for the same destination are queued up one behind the other until space is available. No send request is permitted to successfully complete if there is another send request waiting for space before it. When space is limited, the FIFO policy prevents the starvation of larger requests because smaller requests cannot continuously use the remaining available space. Smaller requests are delayed, though not starved, until the larger request can be completed. When space does become available, requests are considered in the order in which they were made. If there is sufficient space for a given request, then that request is completed and the next request is considered. If there is insufficient space for a given request, then no further requests are considered until sufficient space becomes available for the current request to complete.  Preemptive indicates that a send operation can preempt other blocking send operations if space is available. That is, if there is sufficient space for the current request, then that space is used even if there are other requests waiting for space. When space is limited, the Preemptive policy can result in the starvation of larger requests. For example, if there is insufficient available space for a large request, then it is queued up behind other existing requests. When space does become available, all requests are considered in the order in which they were originally made. If there is sufficient space for a given request, then that request is allowed to continue and the next request is considered. If there is insufficient space for a given request, then that request is skipped and the next request is considered. "
      ::= { jmsServerEntry 80  }
   
   
   jmsServerHostingTemporaryDestinations OBJECT-TYPE
      SYNTAX      OCTET STRING
      MAX-ACCESS  read-only
      STATUS      current
      DESCRIPTION "Specifies whether this JMS server can be used to host temporary destinations.  If this field is enabled and no Temporary Template Name is defined, then the temporary destinations created on this JMS server will use all default destination values. If this field is enabled, then the JMS template to be used for creating temporary destinations is specified by the Temporary Template Name field. If this field is disabled, then this JMS server will not host temporary destinations. "
      ::= { jmsServerEntry 81  }
   
   
   jmsServerPagingDirectory OBJECT-TYPE
      SYNTAX      OCTET STRING
      MAX-ACCESS  read-only
      STATUS      current
      DESCRIPTION " Specifies where message bodies are written when the size of the message bodies in the JMS server exceeds the message buffer size.  If unspecified, messages are written to the default tmp directory inside the server-name subdirectory of a domain's root directory. For example, domain-name/servers/server-name/tmp, where domain-name is the root directory of your domain.   For best performance, this directory should not be the same as the directory used by the JMS server's persistent store.   If the value is changed and activated, you need to restart any servers to which the MBean is targeted before the value will take effect (even though you do not get a warning in the Console that the server needs to be restarted). "
      ::= { jmsServerEntry 82  }
   
   
   jmsServerTemporaryTemplateResource OBJECT-TYPE
      SYNTAX      OCTET STRING
      MAX-ACCESS  read-only
      STATUS      current
      DESCRIPTION "The name of a JMS module that contains a template that this JMS server can use to create temporary destinations.  Entering a JMS module name requires you to specify a temporary template name. However, a module name cannot be specified if the Hosting Temporary Destinations field is disabled. "
      ::= { jmsServerEntry 83  }
   
   
   jmsServerConsumptionPausedAtStartup OBJECT-TYPE
      SYNTAX      OCTET STRING
      MAX-ACCESS  read-only
      STATUS      current
      DESCRIPTION "Indicates whether consumption is paused at startup on destinations targeted to this JMS server at startup. A destination cannot receive any new messages while it is paused.  When the value is set to true, then immediately after the host server instance is booted, then this JMS server and its targeted destinations are modified such that they are in a 'consumption paused' state, which prevents any message consuming activity on those destinations.  To allow normal message consumption on the destinations, later you will have to change the state of this JMS server to a 'consumption enabled' state by setting this value to false, and then either redeploy the JMS server or reboot the hosting server instance.  When the value is set to default, then the Consumption Paused At Startup is determined based on the corresponding setting on the individual destination.  If the value is changed and activated, you need to restart any servers to which the MBean is targeted before the value will take effect (even though you do not get a warning in the Console that the server needs to be restarted). "
      ::= { jmsServerEntry 84  }
   
   
   jmsServerMessagesPagingEnabled OBJECT-TYPE
      SYNTAX      OCTET STRING
      MAX-ACCESS  read-only
      STATUS      current
      DESCRIPTION "This parameter has been deprecated. Paging is always enabled. The 'MessageBufferSize' parameter controls how much memory is used before paging kicks in. "
      ::= { jmsServerEntry 85  }
   
   
   jmsServerBytesPagingEnabled OBJECT-TYPE
      SYNTAX      OCTET STRING
      MAX-ACCESS  read-only
      STATUS      current
      DESCRIPTION "This parameter has been deprecated. Paging is always enabled. The 'MessageBufferSize' parameter controls how much memory is used before paging kicks in. "
      ::= { jmsServerEntry 86  }
   
   
   jmsServerPagingMinWindowBufferSize OBJECT-TYPE
      SYNTAX      INTEGER
      MAX-ACCESS  read-only
      STATUS      current
      DESCRIPTION "The minimum amount of data, in bytes and rounded down to the nearest power of 2, mapped into the JVM's address space per paging store file.  Applies only when a native wlfileio library is loaded. See Paging Maximum Window Buffer Size.  If the value is changed and activated, you need to restart any servers to which the MBean is targeted before the value will take effect (even though you do not get a warning in the Console that the server needs to be restarted). "
      ::= { jmsServerEntry 87  }
   
   
   jmsServerPagingFileLockingEnabled OBJECT-TYPE
      SYNTAX      OCTET STRING
      MAX-ACCESS  read-only
      STATUS      current
      DESCRIPTION "Determines whether OS file locking is used.  When file locking protection is enabled, a store boot fails if another store instance already has opened the store files. Do not disable this setting unless you have procedures in place to prevent multiple store instances from opening the same file. File locking is not required but helps prevent corruption in the event that two same-named file store instances attempt to operate in the same directories. This setting applies to both primary and cache files.  If the value is changed and activated, you need to restart any servers to which the MBean is targeted before the value will take effect (even though you do not get a warning in the Console that the server needs to be restarted). "
      ::= { jmsServerEntry 88  }
   
   
   jmsServerPagingIoBufferSize OBJECT-TYPE
      SYNTAX      INTEGER
      MAX-ACCESS  read-only
      STATUS      current
      DESCRIPTION "The I/O buffer size, in bytes, automatically rounded down to the nearest power of 2.  When a native wlfileio driver is available, the setting applies to off-heap (native) memory. When a native wlfileio driver is not available, the setting applies to JAVA heap memory. For the best runtime performance, Oracle recommends setting PagingIOBufferSize so that it is larger than the largest write (multiple concurrent store requests may be combined into a single write). See the JMS server runtime MBean attribute PagingAllocatedIOBufferBytes to find out the actual allocated off-heap (native) memory amount.   If the value is changed and activated, you need to restart any servers to which the MBean is targeted before the value will take effect (even though you do not get a warning in the Console that the server needs to be restarted). "
      ::= { jmsServerEntry 89  }
   
   
   jmsServerPagingBlockSize OBJECT-TYPE
      SYNTAX      INTEGER
      MAX-ACCESS  read-only
      STATUS      current
      DESCRIPTION "The smallest addressable block, in bytes, of a file. When a native wlfileio driver is available and the paging block size has not been configured by the user, the store selects the minimum OS specific value for unbuffered (direct) I/O, if it is within the range [512, 8192]. A paging store's block size does not change once the paging store creates its files. Changes to block size only take effect for new paging stores or after the current files have been deleted. See 'Tuning the Persistent Store' in Performance and Tuning for Oracle WebLogic Server. If the value is changed and activated, you need to restart any servers to which the MBean is targeted before the value will take effect (even though you do not get a warning in the Console that the server needs to be restarted). "
      ::= { jmsServerEntry 90  }
   
   
   jmsServerPagingMaxFileSize OBJECT-TYPE
      SYNTAX      Counter64
      MAX-ACCESS  read-only
      STATUS      current
      DESCRIPTION "The paging maximum file size, in bytes.  The PagingMaxFileSize value affects the number of files needed to accommodate a paging store of a particular size (number of files = paging store size/MaxFileSize rounded up).  A paging store automatically reuses space freed by deleted records and automatically expands individual files up to PagingMaxFileSize if there is not enough space for a new record. If there is no space left in exiting files for a new record, a paging store creates an additional file.   A small number of larger files is normally preferred over a large number of smaller files as each file allocates Window Buffer and file handles.    If PagingMaxFileSize is larger than 2^24 * PagingBlockSize, then MaxFileSize is ignored, and the value becomes 2^24 * PagingBlockSize. The default PagingBlockSize is 512, and 2^24 * 512 is 8 GB.   Oracle recommends not setting the Paging Max File Size above the default value of 1,342,177,280.   If the value is changed and activated, you need to restart any servers to which the MBean is targeted before the value will take effect (even though you do not get a warning in the Console that the server needs to be restarted). "
      ::= { jmsServerEntry 91  }
   
   
   jmsServerPagingMaxWindowBufferSize OBJECT-TYPE
      SYNTAX      INTEGER
      MAX-ACCESS  read-only
      STATUS      current
      DESCRIPTION "The maximum amount of data, in bytes and rounded down to the nearest power of 2, mapped into the JVM's address space per paging store file. Applies only when a native wlfileio library is loaded.  A window buffer does not consume Java heap memory, but does consume off-heap (native) memory. If the paging store is unable to allocate the requested buffer size, it allocates smaller and smaller buffers until it reaches PagingMinWindowBufferSize, and then fails if it cannot honor PagingMinWindowBufferSize.  Oracle recommends setting the max window buffer size to more than double the size of the largest write (multiple concurrently updated records may be combined into a single write), and greater than or equal to the file size, unless there are other constraints. 32-bit JVMs may impose a total limit of between 2 and 4GB for combined Java heap plus off-heap (native) memory usage.  See the JMS server runtime MBean attribute PagingAllocatedWindowBufferBytes to find out the actual allocated Window Buffer Size.  If the value is changed and activated, you need to restart any servers to which the MBean is targeted before the value will take effect (even though you do not get a warning in the Console that the server needs to be restarted). "
      ::= { jmsServerEntry 92  }
   
   
   jmsServerMessageCompressionOptions OBJECT-TYPE
      SYNTAX      OCTET STRING
      MAX-ACCESS  read-only
      STATUS      current
      DESCRIPTION "Specifies the type of message compression used when JMS message body compression is enabled for Persistent Stores and JMS Paging Stores.  Use GZIP_DEFAULT_COMPRESSION to enable message compression using the JDK GZIP API with DEFAULT_COMPRESSION level. Use GZIP_BEST_COMPRESSION to enable message compression using the JDK GZIP API with BEST_COMPRESSION level. Use GZIP_BEST_SPEED to enable message compression using the JDK GZIP API with BEST_SPEED level. Use LZF to enable message compression using Open Source LZF.  "
      ::= { jmsServerEntry 93  }
   
   
   jmsServerPagingMessageCompressionEnabled OBJECT-TYPE
      SYNTAX      OCTET STRING
      MAX-ACCESS  read-only
      STATUS      current
      DESCRIPTION "Enables the JMS paging store to perform message body compression on persistent and non-persistent messages. When false, the default value, no compression is performed. "
      ::= { jmsServerEntry 94  }
   
   
   jmsServerStoreMessageCompressionEnabled OBJECT-TYPE
      SYNTAX      OCTET STRING
      MAX-ACCESS  read-only
      STATUS      current
      DESCRIPTION "Enables the JMS store to perform message body compression. When set to false, the default value, no compression is performed. "
      ::= { jmsServerEntry 95  }
   
   
   jmsServerTags OBJECT-TYPE
      SYNTAX      OCTET STRING
      MAX-ACCESS  read-only
      STATUS      current
      DESCRIPTION "Return all tags on this Configuration MBean "
      ::= { jmsServerEntry 96  }
   
   
   jmsSessionPoolTable OBJECT-TYPE
      SYNTAX      SEQUENCE OF JmsSessionPoolEntry
      MAX-ACCESS  not-accessible
      STATUS      current
      DESCRIPTION "This table represents a JMS session pool."
      ::= { wls 670  }
      
   
   jmsSessionPoolEntry OBJECT-TYPE
      SYNTAX      JmsSessionPoolEntry
      MAX-ACCESS  not-accessible
      STATUS      current
      DESCRIPTION "Entry of jmsSessionPoolTable"
      INDEX { jmsSessionPoolIndex}
      ::= { jmsSessionPoolTable 1 }
      
   JmsSessionPoolEntry ::=
      SEQUENCE
      {
         jmsSessionPoolIndex  DisplayString,
         jmsSessionPoolObjectName DisplayString,
         jmsSessionPoolType   DisplayString,
         jmsSessionPoolName   DisplayString,
         jmsSessionPoolParent DisplayString,
         jmsSessionPoolConnectionFactory DisplayString,
         jmsSessionPoolListenerClass DisplayString,
         jmsSessionPoolAcknowledgeMode DisplayString,
         jmsSessionPoolSessionsMaximum INTEGER,
         jmsSessionPoolTransacted INTEGER
      }
      
   
   jmsSessionPoolIndex OBJECT-TYPE
      SYNTAX      DisplayString (SIZE (1..16))
      MAX-ACCESS  read-only
      STATUS      current
      DESCRIPTION "Unique value directed from ObjectName which is used as table index"
      ::= { jmsSessionPoolEntry 1  }
   
   
   jmsSessionPoolObjectName OBJECT-TYPE
      SYNTAX      DisplayString (SIZE (1..256))
      MAX-ACCESS  read-only
      STATUS      current
      DESCRIPTION "JMX-standard MBean name"
      ::= { jmsSessionPoolEntry 5  }
   
   
   jmsSessionPoolType OBJECT-TYPE
      SYNTAX      DisplayString (SIZE (1..64))
      MAX-ACCESS  read-only
      STATUS      current
      DESCRIPTION "BEA-proprietary MBean type"
      ::= { jmsSessionPoolEntry 10  }
   
   
   jmsSessionPoolName OBJECT-TYPE
      SYNTAX      DisplayString (SIZE (1..64))
      MAX-ACCESS  read-only
      STATUS      current
      DESCRIPTION "BEA-proprietary MBean name"
      ::= { jmsSessionPoolEntry 15  }
   
   
   jmsSessionPoolParent OBJECT-TYPE
      SYNTAX      DisplayString (SIZE (1..256))
      MAX-ACCESS  read-only
      STATUS      current
      DESCRIPTION "BEA-proprietary Parent object's identification, with syntax
      <type>:<name>"
      ::= { jmsSessionPoolEntry 20  }
   
   
   jmsSessionPoolConnectionFactory OBJECT-TYPE
      SYNTAX      DisplayString (SIZE (1..256))
      MAX-ACCESS  read-only
      STATUS      current
      DESCRIPTION "Return the JNDI name of the connection factory for the session pool"
      ::= { jmsSessionPoolEntry 30  }
   
   
   jmsSessionPoolListenerClass OBJECT-TYPE
      SYNTAX      DisplayString (SIZE (1..256))
      MAX-ACCESS  read-only
      STATUS      current
      DESCRIPTION "Return the name of the listener class for the SessionPool."
      ::= { jmsSessionPoolEntry 35  }
   
   
   jmsSessionPoolAcknowledgeMode OBJECT-TYPE
      SYNTAX      DisplayString (SIZE (1..32))
      MAX-ACCESS  read-only
      STATUS      current
      DESCRIPTION "Return the acknowledge mode of the SessionPool."
      ::= { jmsSessionPoolEntry 40  }
   
   
   jmsSessionPoolSessionsMaximum OBJECT-TYPE
      SYNTAX      INTEGER
      MAX-ACCESS  read-only
      STATUS      current
      DESCRIPTION "Return the maximum number of sessions allowed for the SessionPool."
      ::= { jmsSessionPoolEntry 45  }
   
   
   jmsSessionPoolTransacted OBJECT-TYPE
      SYNTAX      INTEGER
                  {
                     true(1),
                     false(2)
                  }
      
      MAX-ACCESS  read-only
      STATUS      current
      DESCRIPTION "returns boolean true if the SessionPool is transacted"
      ::= { jmsSessionPoolEntry 50  }
   
   
   jmsVirtualDestinationTable OBJECT-TYPE
      SYNTAX      SEQUENCE OF JmsVirtualDestinationEntry
      MAX-ACCESS  not-accessible
      STATUS      current
      DESCRIPTION "This table represents a key value for a destination"
      ::= { wls 682  }
      
   
   jmsVirtualDestinationEntry OBJECT-TYPE
      SYNTAX      JmsVirtualDestinationEntry
      MAX-ACCESS  not-accessible
      STATUS      current
      DESCRIPTION "Entry of jmsVirtualDestinationTable"
      INDEX { jmsVirtualDestinationIndex}
      ::= { jmsVirtualDestinationTable 1 }
      
   JmsVirtualDestinationEntry ::=
      SEQUENCE
      {
         jmsVirtualDestinationIndex DisplayString,
         jmsVirtualDestinationObjectName DisplayString,
         jmsVirtualDestinationType DisplayString,
         jmsVirtualDestinationName DisplayString,
         jmsVirtualDestinationParent DisplayString,
         jmsVirtualDestinationJNDIName INTEGER
      }
      
   
   jmsVirtualDestinationIndex OBJECT-TYPE
      SYNTAX      DisplayString (SIZE (1..16))
      MAX-ACCESS  read-only
      STATUS      current
      DESCRIPTION "Unique value directed from ObjectName which is used as table index"
      ::= { jmsVirtualDestinationEntry 1  }
   
   
   jmsVirtualDestinationObjectName OBJECT-TYPE
      SYNTAX      DisplayString (SIZE (1..256))
      MAX-ACCESS  read-only
      STATUS      current
      DESCRIPTION "JMX-standard MBean name"
      ::= { jmsVirtualDestinationEntry 5  }
   
   
   jmsVirtualDestinationType OBJECT-TYPE
      SYNTAX      DisplayString (SIZE (1..64))
      MAX-ACCESS  read-only
      STATUS      current
      DESCRIPTION "BEA-proprietary MBean type"
      ::= { jmsVirtualDestinationEntry 10  }
   
   
   jmsVirtualDestinationName OBJECT-TYPE
      SYNTAX      DisplayString (SIZE (1..64))
      MAX-ACCESS  read-only
      STATUS      current
      DESCRIPTION "BEA-proprietary MBean name"
      ::= { jmsVirtualDestinationEntry 15  }
   
   
   jmsVirtualDestinationParent OBJECT-TYPE
      SYNTAX      DisplayString (SIZE (1..256))
      MAX-ACCESS  read-only
      STATUS      current
      DESCRIPTION "BEA-proprietary Parent object's identification, with syntax
      <type>:<name>"
      ::= { jmsVirtualDestinationEntry 20  }
   
   
   jmsVirtualDestinationJNDIName OBJECT-TYPE
      SYNTAX      INTEGER
      MAX-ACCESS  read-only
      STATUS      current
      DESCRIPTION "Return the JNDI name of the distributed destination."
      ::= { jmsVirtualDestinationEntry 25  }
   
   
   jtaTable OBJECT-TYPE
      SYNTAX      SEQUENCE OF JtaEntry
      MAX-ACCESS  not-accessible
      STATUS      current
      DESCRIPTION "This interface provides access to the JTA configuration attributes.  The methods defined herein are applicable for JTA configuration at the domain level. "
      ::= { wls 690  }
      
   
   jtaEntry OBJECT-TYPE
      SYNTAX      JtaEntry
      MAX-ACCESS  not-accessible
      STATUS      current
      DESCRIPTION "Entry of jtaTable"
      INDEX { jtaIndex}
      ::= { jtaTable 1 }
      
   JtaEntry ::=
      SEQUENCE
      {
         jtaIndex             DisplayString,
         jtaObjectName        DisplayString,
         jtaType              DisplayString,
         jtaName              DisplayString,
         jtaParent            DisplayString,
         jtaTimeoutSeconds    INTEGER,
         jtaAbandonTimeoutSeconds INTEGER,
         jtaForgetHeuristics  INTEGER,
         jtaBeforeCompletionIterationLimit INTEGER,
         jtaMaxTransactions   INTEGER,
         jtaMaxUniqueNameStatistics INTEGER,
         jtaMaxResourceRequestsOnServer INTEGER,
         jtaMaxResourceUnavailableMillis Counter64,
         jtaCheckpointIntervalSeconds INTEGER,
         jtaSerializeEnlistmentsGCIntervalMillis Counter64,
         jtaUnregisterResourceGracePeriod INTEGER,
         jtaSecurityInteropMode OCTET STRING,
         jtaMaxXACallMillis   Counter64,
         jtaWSATIssuedTokenEnabled OCTET STRING,
         jtaCompletionTimeoutSeconds INTEGER,
         jtaParallelXAEnabled OCTET STRING,
         jtaWSATTransportSecurityMode OCTET STRING,
         jtaTwoPhaseEnabled   OCTET STRING,
         jtaTightlyCoupledTransactionsEnabled OCTET STRING,
         jtaClusterwideRecoveryEnabled OCTET STRING,
         jtaDeterminers       OCTET STRING,
         jtaTLOGWriteWhenDeterminerExistsEnabled OCTET STRING,
         jtaMaxRetrySecondsBeforeDeterminerFail INTEGER,
         jtaShutdownGracePeriod INTEGER,
         jtaRecoverySiteName  OCTET STRING,
         jtaTags              OCTET STRING,
         jtaCrossDomainRecoveryRetryInterval INTEGER,
         jtaCrossSiteRecoveryRetryInterval INTEGER,
         jtaCrossSiteRecoveryLeaseUpdate INTEGER,
         jtaCrossSiteRecoveryLeaseExpiration INTEGER,
         jtaUsePublicAddressesForRemoteDomains OCTET STRING,
         jtaUseNonSecureAddressesForDomains OCTET STRING
      }
      
   
   jtaIndex OBJECT-TYPE
      SYNTAX      DisplayString (SIZE (1..16))
      MAX-ACCESS  read-only
      STATUS      current
      DESCRIPTION "Unique value directed from ObjectName which is used as table index"
      ::= { jtaEntry 1  }
   
   
   jtaObjectName OBJECT-TYPE
      SYNTAX      DisplayString (SIZE (1..256))
      MAX-ACCESS  read-only
      STATUS      current
      DESCRIPTION "JMX-standard MBean name"
      ::= { jtaEntry 5  }
   
   
   jtaType OBJECT-TYPE
      SYNTAX      DisplayString (SIZE (1..64))
      MAX-ACCESS  read-only
      STATUS      current
      DESCRIPTION "Returns the type of the MBean. "
      ::= { jtaEntry 10  }
   
   
   jtaName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { jtaEntry 15  }
   
   
   jtaParent OBJECT-TYPE
      SYNTAX      DisplayString (SIZE (1..256))
      MAX-ACCESS  read-only
      STATUS      current
      DESCRIPTION "BEA-proprietary Parent object's identification, with syntax
      <type>:<name>"
      ::= { jtaEntry 20  }
   
   
   jtaTimeoutSeconds OBJECT-TYPE
      SYNTAX      INTEGER
      MAX-ACCESS  read-only
      STATUS      current
      DESCRIPTION "Specifies the maximum amount of time, in seconds, an active transaction is allowed to be in the first phase of a two-phase commit transaction. If the specified amount of time expires, the transaction is automatically rolled back. "
      ::= { jtaEntry 25  }
   
   
   jtaAbandonTimeoutSeconds OBJECT-TYPE
      SYNTAX      INTEGER
      MAX-ACCESS  read-only
      STATUS      current
      DESCRIPTION "Specifies the maximum amount of time, in seconds, a transaction manager persists in attempting to complete the second phase of a two-phase commit transaction.   During the second phase of a two-phase commit transaction, the transaction manager continues to try to complete the transaction until all resource managers indicate that the transaction is completed. After the abandon transaction timer expires, no further attempt is made to resolve the transaction. If the transaction is in a prepared state before being abandoned, the transaction manager rolls back the transaction to release any locks held on behalf of the abandoned transaction. "
      ::= { jtaEntry 30  }
   
   
   jtaForgetHeuristics OBJECT-TYPE
      SYNTAX      INTEGER
                  {
                     true(1),
                     false(2)
                  }
      
      MAX-ACCESS  read-only
      STATUS      current
      DESCRIPTION "Specifies whether the transaction manager automatically performs an XA Resource forget operation for heuristic transaction completions.  When enabled, the transaction manager automatically performs an XA Resource forget() operation for all resources as soon as the transaction learns of a heuristic outcome. Disable this feature only if you know what to do with the resource when it reports a heuristic decision. "
      ::= { jtaEntry 35  }
   
   
   jtaBeforeCompletionIterationLimit OBJECT-TYPE
      SYNTAX      INTEGER
      MAX-ACCESS  read-only
      STATUS      current
      DESCRIPTION "The maximum number of cycles that the transaction manager performs the beforeCompletion synchronization callback for this WebLogic Server domain.  Nothing prevents a Synchronization object from registering another during beforeCompletion, even those whose beforeCompletions have already been called. For example, an EJB can call another in its ejbStore() method. To accommodate this, the transaction manager calls all Synchronization objects, then repeats the cycle if new ones have been registered. This count sets a limit to the number of cycles that synchronization occurs. "
      ::= { jtaEntry 40  }
   
   
   jtaMaxTransactions OBJECT-TYPE
      SYNTAX      INTEGER
      MAX-ACCESS  read-only
      STATUS      current
      DESCRIPTION "The maximum number of simultaneous in-progress transactions allowed on a server in this WebLogic Server domain. "
      ::= { jtaEntry 45  }
   
   
   jtaMaxUniqueNameStatistics OBJECT-TYPE
      SYNTAX      INTEGER
      MAX-ACCESS  read-only
      STATUS      current
      DESCRIPTION "The maximum number of unique transaction names for which statistics are maintained.  The first 1001 unique transaction names are maintained as their own transaction name and stored in each statistic. After the 1001st transaction name is reached, the transaction name is stored as weblogic.transaction.statistics.namedOverflow, and the transaction statistic is also merged and maintained in weblogic.transaction.statistics.namedOverflow.  A transaction name typically represents a category of business transactions, such as 'funds-transfer.' "
      ::= { jtaEntry 50  }
   
   
   jtaMaxResourceRequestsOnServer OBJECT-TYPE
      SYNTAX      INTEGER
      MAX-ACCESS  read-only
      STATUS      current
      DESCRIPTION "Maximum number of concurrent requests to resources allowed for each server. "
      ::= { jtaEntry 51  }
   
   
   jtaMaxResourceUnavailableMillis OBJECT-TYPE
      SYNTAX      Counter64
      MAX-ACCESS  read-only
      STATUS      current
      DESCRIPTION "Maximum duration time, in milliseconds, that a resource is declared dead. After the duration, the resource is declared available again, even if the resource provider does not explicitly re-register the resource. "
      ::= { jtaEntry 52  }
   
   
   jtaCheckpointIntervalSeconds OBJECT-TYPE
      SYNTAX      INTEGER
      MAX-ACCESS  read-only
      STATUS      current
      DESCRIPTION "The interval at which the transaction manager creates a new transaction log file and checks all old transaction log files to see if they are ready to be deleted. "
      ::= { jtaEntry 53  }
   
   
   jtaSerializeEnlistmentsGCIntervalMillis OBJECT-TYPE
      SYNTAX      Counter64
      MAX-ACCESS  read-only
      STATUS      current
      DESCRIPTION "The time interval, in milliseconds, at which internal objects used to serialize resource enlistment are cleaned up. "
      ::= { jtaEntry 54  }
   
   
   jtaUnregisterResourceGracePeriod OBJECT-TYPE
      SYNTAX      INTEGER
      MAX-ACCESS  read-only
      STATUS      current
      DESCRIPTION "The amount of time, in seconds, a  transaction manager waits for transactions involving the resource to complete before unregistering a resource. This grace period helps minimize the risk of abandoned transactions because of an unregistered resource, such as a JDBC data source module packaged with an application.  During the specified grace period, the unregisterResource call blocks until the call returns and no new transactions are started for the associated resource. If the number of outstanding transactions for the resource goes to 0, the unregisterResource call returns immediately.  At the end of the grace period, if outstanding transactions are associated with the resource, the unregisterResource call returns and a log message is written to the server on which the resource was previously registered.  "
      ::= { jtaEntry 55  }
   
   
   jtaSecurityInteropMode OBJECT-TYPE
      SYNTAX      OCTET STRING
      MAX-ACCESS  read-only
      STATUS      current
      DESCRIPTION "Specifies the security mode of the communication channel used for XA calls between servers that participate in a global transaction. All server instances in a domain must have the same security mode setting.  Security Interoperability Mode options:  default  The transaction coordinator makes calls using the kernel identity over an admin channel if it is enabled, and anonymous otherwise. Man-in-the-middle attacks are possible if the admin channel is not enabled.  performance  The transaction coordinator makes calls using anonymous at all times. This implies a security risk since a malicious third party could then try to affect the outcome of transactions using a man-in-the-middle attack.  compatibility  The transaction coordinator makes calls as the kernel identity over an insecure channel. This is a high security risk because a successful man-in-the-middle attack would allow the attacker to gain administrative control over both domains. This setting should only be used when strong network security is in place.   "
      ::= { jtaEntry 56  }
   
   
   jtaMaxXACallMillis OBJECT-TYPE
      SYNTAX      Counter64
      MAX-ACCESS  read-only
      STATUS      current
      DESCRIPTION "Maximum allowed time duration, in milliseconds,  for XA calls to resources. If a particular XA call to a resource exceeds the limit, the resource is declared unavailable. "
      ::= { jtaEntry 57  }
   
   
   jtaWSATIssuedTokenEnabled OBJECT-TYPE
      SYNTAX      OCTET STRING
      MAX-ACCESS  read-only
      STATUS      current
      DESCRIPTION "Specifies whether to use issuedtoken to enable authentication between the WS-AT coordinator and participant. "
      ::= { jtaEntry 59  }
   
   
   jtaCompletionTimeoutSeconds OBJECT-TYPE
      SYNTAX      INTEGER
      MAX-ACCESS  read-only
      STATUS      current
      DESCRIPTION "Specifies the maximum amount of time, in seconds, a transaction manager waits for all resource managers to respond and indicate if the transaction can be committed or rolled back.   The default value is 0, which sets the value to approximately twice the default transaction-timeout value with a maximum value of 120 seconds. This value provides backward compatibility for prior releases without this setting. If the specified value is -1, the maximum value supported by this attribute is used.  If the specified value exceeds the value set for abandon-timeout-seconds, the value of abandon-timeout-seconds is used.   "
      ::= { jtaEntry 60  }
   
   
   jtaParallelXAEnabled OBJECT-TYPE
      SYNTAX      OCTET STRING
      MAX-ACCESS  read-only
      STATUS      current
      DESCRIPTION "Indicates that XA calls are executed in parallel if there are available threads. "
      ::= { jtaEntry 61  }
   
   
   jtaWSATTransportSecurityMode OBJECT-TYPE
      SYNTAX      OCTET STRING
      MAX-ACCESS  read-only
      STATUS      current
      DESCRIPTION " Specifies transport security mode required by WebService Transaction endpoints. Transport Security options:  SSLNotRequired All WebService Transaction protocol messages are exchanged over the HTTP channel.  SSLRequired All WebService Transaction protocol messages are and can only be exchanged over the HTTPS.  ClientCertRequired All WebService Transaction protocol messages are and can only be exchanged over the HTTPS, and WLS enforces the presence of client certificate   "
      ::= { jtaEntry 62  }
   
   
   jtaTwoPhaseEnabled OBJECT-TYPE
      SYNTAX      OCTET STRING
      MAX-ACCESS  read-only
      STATUS      current
      DESCRIPTION "Indicates that the two-phase commit protocol is used to coordinate transactions across two or more resource managers.  If not selected:   Two-phase commit is disabled and any attempt to use two-phase commit results in a RollbackException being thrown.  All transaction logging is disabled, including checkpoint records.  "
      ::= { jtaEntry 63  }
   
   
   jtaTightlyCoupledTransactionsEnabled OBJECT-TYPE
      SYNTAX      OCTET STRING
      MAX-ACCESS  read-only
      STATUS      current
      DESCRIPTION "Indicates tight coupling of transaction branches that span different transaction manager systems.  When enabled, WebLogic uses the transaction identifier of a transaction imported by the InterposedTransactionManager for XA calls rather than an internally mapped Xid. This applies to inter-domain WebLogic transactions and transactions imported from Tuxedo. This allows for tight coupling of transaction branches for transactions that span across different transaction manager systems.  If a transaction between WebLogic and Tuxedo resources uses a GridLink Data Source with GridLink Affinity enabled, the XA Affinity context is automatically used for the transaction. "
      ::= { jtaEntry 64  }
   
   
   jtaClusterwideRecoveryEnabled OBJECT-TYPE
      SYNTAX      OCTET STRING
      MAX-ACCESS  read-only
      STATUS      current
      DESCRIPTION "Indicates that cluster-wide recovery is used for distributed transactions.  When enabled, recovery operations for a distributed transaction are applied to all the servers of the cluster hosting a InterposedTransactionManager rather than just the server hosting the InterposedTransactionManager. "
      ::= { jtaEntry 65  }
   
   
   jtaDeterminers OBJECT-TYPE
      SYNTAX      OCTET STRING
      MAX-ACCESS  read-only
      STATUS      current
      DESCRIPTION "Select a transaction resource (determiner) from the list of resources. For JMS, select WebLogic JMS as the determiner. When a determiner is configured, the determiner's in-doubt transaction records are used during transaction recovery. "
      ::= { jtaEntry 66  }
   
   
   jtaTLOGWriteWhenDeterminerExistsEnabled OBJECT-TYPE
      SYNTAX      OCTET STRING
      MAX-ACCESS  read-only
      STATUS      current
      DESCRIPTION "Indicates two-phase transaction recovery logs are written even if one or more determiners are configured. "
      ::= { jtaEntry 67  }
   
   
   jtaMaxRetrySecondsBeforeDeterminerFail OBJECT-TYPE
      SYNTAX      INTEGER
      MAX-ACCESS  read-only
      STATUS      current
      DESCRIPTION "The maximum amount of time, in seconds, WebLogic Server waits for the determiner to recover from a failure. If the determiner does not recover after this period, WebLogic Server sets the TLog health state to HEALTH_FAILED. "
      ::= { jtaEntry 68  }
   
   
   jtaShutdownGracePeriod OBJECT-TYPE
      SYNTAX      INTEGER
      MAX-ACCESS  read-only
      STATUS      current
      DESCRIPTION "Indicates how long the server should wait for active transactions to complete before allowing shutdown. "
      ::= { jtaEntry 69  }
   
   
   jtaRecoverySiteName OBJECT-TYPE
      SYNTAX      OCTET STRING
      MAX-ACCESS  read-only
      STATUS      current
      DESCRIPTION "The name of the site whose transactions this site/domain will recover in the event that intra-cluster transaction service migration is not successful or efficient. "
      ::= { jtaEntry 70  }
   
   
   jtaTags OBJECT-TYPE
      SYNTAX      OCTET STRING
      MAX-ACCESS  read-only
      STATUS      current
      DESCRIPTION "Return all tags on this Configuration MBean "
      ::= { jtaEntry 71  }
   
   
   jtaCrossDomainRecoveryRetryInterval OBJECT-TYPE
      SYNTAX      INTEGER
      MAX-ACCESS  read-only
      STATUS      current
      DESCRIPTION "The interval at which a store lock for a given server in a recovery domain will be checked for takeover eligibility. "
      ::= { jtaEntry 72  }
   
   
   jtaCrossSiteRecoveryRetryInterval OBJECT-TYPE
      SYNTAX      INTEGER
      MAX-ACCESS  read-only
      STATUS      current
      DESCRIPTION "The interval at which a lease for a given server in a recovery domain will be checked for takeover eligibility. "
      ::= { jtaEntry 73  }
   
   
   jtaCrossSiteRecoveryLeaseUpdate OBJECT-TYPE
      SYNTAX      INTEGER
      MAX-ACCESS  read-only
      STATUS      current
      DESCRIPTION "The time in seconds in which to update a lease timestamp. "
      ::= { jtaEntry 74  }
   
   
   jtaCrossSiteRecoveryLeaseExpiration OBJECT-TYPE
      SYNTAX      INTEGER
      MAX-ACCESS  read-only
      STATUS      current
      DESCRIPTION "The time in seconds after which a lease expires making it eligible for recovery by another site. "
      ::= { jtaEntry 75  }
   
   
   jtaUsePublicAddressesForRemoteDomains OBJECT-TYPE
      SYNTAX      OCTET STRING
      MAX-ACCESS  read-only
      STATUS      current
      DESCRIPTION "Returns the remote domains for which public addresses should be used if the servers in the domains are configured to use network channels for internal JTA communication. "
      ::= { jtaEntry 76  }
   
   
   jtaUseNonSecureAddressesForDomains OBJECT-TYPE
      SYNTAX      OCTET STRING
      MAX-ACCESS  read-only
      STATUS      current
      DESCRIPTION "Returns the domains for which non-secure protocols should be used for internal JTA communication if the servers in the domains are configured to use network channels. "
      ::= { jtaEntry 77  }
   
   
   kernelTable OBJECT-TYPE
      SYNTAX      SEQUENCE OF KernelEntry
      MAX-ACCESS  not-accessible
      STATUS      current
      DESCRIPTION "This bean represents the configuration of the core message passing kernel on both WebLogic clients and servers.   {@link ServerMBean ServerMBean} extends this bean to represent the configuration of a server. "
      ::= { wls 692  }
      
   
   kernelEntry OBJECT-TYPE
      SYNTAX      KernelEntry
      MAX-ACCESS  not-accessible
      STATUS      current
      DESCRIPTION "Entry of kernelTable"
      INDEX { kernelIndex}
      ::= { kernelTable 1 }
      
   KernelEntry ::=
      SEQUENCE
      {
         kernelIndex          DisplayString,
         kernelObjectName     DisplayString,
         kernelType           DisplayString,
         kernelName           DisplayString,
         kernelParent         DisplayString,
         kernelCompleteCOMMessageTimeout INTEGER,
         kernelCompleteHTTPMessageTimeout INTEGER,
         kernelCompleteIIOPMessageTimeout INTEGER,
         kernelCompleteT3MessageTimeout INTEGER,
         kernelDefaultProtocol DisplayString,
         kernelDefaultSecureProtocol DisplayString,
         kernelDGCIdlePeriodsUntilTimeout INTEGER,
         kernelIdleIIOPConnectionTimeout INTEGER,
         kernelMaxCOMMessageSize INTEGER,
         kernelMaxHTTPMessageSize INTEGER,
         kernelMaxIIOPMessageSize INTEGER,
         kernelMaxOpenSockCount INTEGER,
         kernelMaxT3MessageSize INTEGER,
         kernelStuckThreadMaxTime INTEGER,
         kernelStuckThreadTimerInterval INTEGER,
         kernelThreadPoolPercentSocketReaders INTEGER,
         kernelInstrumentStackTraceEnabled INTEGER,
         kernelLogRemoteExceptionsEnabled INTEGER,
         kernelNativeIOEnabled INTEGER,
         kernelReverseDNSAllowed INTEGER,
         kernelIdleConnectionTimeout INTEGER,
         kernelIIOPTxMechanism OCTET STRING,
         kernelCompleteMessageTimeout INTEGER,
         kernelConnectTimeout INTEGER,
         kernelUse81StyleExecuteQueues OCTET STRING,
         kernelMuxerClass     OCTET STRING,
         kernelPeriodLength   INTEGER,
         kernelSocketReaders  INTEGER,
         kernelIdlePeriodsUntilTimeout INTEGER,
         kernelMessagingBridgeThreadPoolSize INTEGER,
         kernelAdministrationProtocol OCTET STRING,
         kernelOutboundPrivateKeyEnabled OCTET STRING,
         kernelSocketBufferSizeAsChunkSize OCTET STRING,
         kernelMaxMessageSize INTEGER,
         kernelOutboundEnabled OCTET STRING,
         kernelGatheredWritesEnabled OCTET STRING,
         kernelScatteredReadsEnabled OCTET STRING,
         kernelUseDetailedThreadName OCTET STRING,
         kernelCompleteWriteTimeout INTEGER,
         kernelUseConcurrentQueueForRequestManager OCTET STRING,
         kernelUseEnhancedPriorityQueueForRequestManager OCTET STRING,
         kernelPrintStackTraceInProduction OCTET STRING,
         kernelAddWorkManagerThreadsByCpuCount OCTET STRING,
         kernelAllowShrinkingPriorityRequestQueue OCTET STRING,
         kernelUseEnhancedIncrementAdvisor OCTET STRING,
         kernelTags           OCTET STRING,
         kernelEagerThreadLocalCleanup OCTET STRING,
         kernelIsolatePartitionThreadLocals OCTET STRING
      }
      
   
   kernelIndex OBJECT-TYPE
      SYNTAX      DisplayString (SIZE (1..16))
      MAX-ACCESS  read-only
      STATUS      current
      DESCRIPTION "Unique value directed from ObjectName which is used as table index"
      ::= { kernelEntry 1  }
   
   
   kernelObjectName OBJECT-TYPE
      SYNTAX      DisplayString (SIZE (1..256))
      MAX-ACCESS  read-only
      STATUS      current
      DESCRIPTION "JMX-standard MBean name"
      ::= { kernelEntry 5  }
   
   
   kernelType OBJECT-TYPE
      SYNTAX      DisplayString (SIZE (1..64))
      MAX-ACCESS  read-only
      STATUS      current
      DESCRIPTION "Returns the type of the MBean. "
      ::= { kernelEntry 10  }
   
   
   kernelName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { kernelEntry 15  }
   
   
   kernelParent OBJECT-TYPE
      SYNTAX      DisplayString (SIZE (1..256))
      MAX-ACCESS  read-only
      STATUS      current
      DESCRIPTION "BEA-proprietary Parent object's identification, with syntax
      <type>:<name>"
      ::= { kernelEntry 20  }
   
   
   kernelCompleteCOMMessageTimeout OBJECT-TYPE
      SYNTAX      INTEGER
      MAX-ACCESS  read-only
      STATUS      current
      DESCRIPTION "The maximum number of seconds spent waiting for a complete COM message to be received. This setting does not apply to any network channels that you have configured for this server.  This timeout helps guard against a denial of service attack in which a caller indicates that they will be sending a message of a certain size which they never finish sending. "
      ::= { kernelEntry 25  }
   
   
   kernelCompleteHTTPMessageTimeout OBJECT-TYPE
      SYNTAX      INTEGER
      MAX-ACCESS  read-only
      STATUS      current
      DESCRIPTION "The maximum number of seconds spent waiting for a complete HTTP message to be received. If you configure network channels for this server, each channel can override this HTTP message timeout.  This timeout helps guard against a denial of service attack in which a caller indicates that it will be sending a message of a certain size which it never finishes sending.  A value of -1 indicates that this value should be obtained from network channels configured for this server. "
      ::= { kernelEntry 30  }
   
   
   kernelCompleteIIOPMessageTimeout OBJECT-TYPE
      SYNTAX      INTEGER
      MAX-ACCESS  read-only
      STATUS      current
      DESCRIPTION "The maximum number of seconds spent waiting for a complete IIOP message to be received. This timeout helps guard against denial of service attacks in which a caller indicates that they will be sending a message of a certain size which they never finish sending. "
      ::= { kernelEntry 35  }
   
   
   kernelCompleteT3MessageTimeout OBJECT-TYPE
      SYNTAX      INTEGER
      MAX-ACCESS  read-only
      STATUS      current
      DESCRIPTION "The maximum number of seconds spent waiting for a complete T3 message to be received. If you configure network channels for this server, each channel can override this T3 message timeout.  This timeout helps guard against a denial of service attack in which a caller indicates that it will be sending a message of a certain size which it never finishes sending. "
      ::= { kernelEntry 40  }
   
   
   kernelDefaultProtocol OBJECT-TYPE
      SYNTAX      DisplayString (SIZE (1..256))
      MAX-ACCESS  read-only
      STATUS      current
      DESCRIPTION "The protocol to use for connections when none is specified. "
      ::= { kernelEntry 55  }
   
   
   kernelDefaultSecureProtocol OBJECT-TYPE
      SYNTAX      DisplayString (SIZE (1..256))
      MAX-ACCESS  read-only
      STATUS      current
      DESCRIPTION "The protocol to use for secure connections when none is specified. "
      ::= { kernelEntry 60  }
   
   
   kernelDGCIdlePeriodsUntilTimeout OBJECT-TYPE
      SYNTAX      INTEGER
      MAX-ACCESS  read-only
      STATUS      current
      DESCRIPTION "The number of idle periods allowed before the object is collected. "
      ::= { kernelEntry 65  }
   
   
   kernelIdleIIOPConnectionTimeout OBJECT-TYPE
      SYNTAX      INTEGER
      MAX-ACCESS  read-only
      STATUS      current
      DESCRIPTION "The maximum number of seconds an IIOP connection is allowed to be idle before it is closed by the server. This timeout helps guard against server deadlock through too many open connections. "
      ::= { kernelEntry 70  }
   
   
   kernelMaxCOMMessageSize OBJECT-TYPE
      SYNTAX      INTEGER
      MAX-ACCESS  read-only
      STATUS      current
      DESCRIPTION "The maximum number of bytes allowed in messages that are received over the COM protocol. If you configure custom network channels for this server, each channel can override this maximum message size.  This maximum message size helps guard against a denial of service attack in which a caller attempts to force the server to allocate more memory than is available thereby keeping the server from responding quickly to other requests.  A value of -1 causes the COM protocol to use the maximums that are specified elsewhere along the order of precedence. "
      ::= { kernelEntry 75  }
   
   
   kernelMaxHTTPMessageSize OBJECT-TYPE
      SYNTAX      INTEGER
      MAX-ACCESS  read-only
      STATUS      current
      DESCRIPTION "The maximum number of bytes allowed in messages that are received over the HTTP protocol. If you configure custom network channels for this server, each channel can override this maximum message size.  This maximum message size helps guard against a denial of service attack in which a caller attempts to force the server to allocate more memory than is available thereby keeping the server from responding quickly to other requests.  A value of -1 causes the HTTP protocol to use the maximums that are specified elsewhere along the order of precedence. "
      ::= { kernelEntry 85  }
   
   
   kernelMaxIIOPMessageSize OBJECT-TYPE
      SYNTAX      INTEGER
      MAX-ACCESS  read-only
      STATUS      current
      DESCRIPTION "The maximum number of bytes allowed in messages that are received over the IIOP protocol. If you configure custom network channels for this server, each channel can override this maximum message size.  This maximum message size helps guard against a denial of service attack in which a caller attempts to force the server to allocate more memory than is available thereby keeping the server from responding quickly to other requests.  A value of -1 causes the IIOP protocol to use the maximums that are specified elsewhere along the order of precedence. "
      ::= { kernelEntry 90  }
   
   
   kernelMaxOpenSockCount OBJECT-TYPE
      SYNTAX      INTEGER
      MAX-ACCESS  read-only
      STATUS      current
      DESCRIPTION "The maximum number of open sockets allowed in server at a given point of time.  When the maximum threshold is reached, the server stops accepting new requests until the number of sockets drops below the threshold.  A value less than 0 indicates an unlimited size. "
      ::= { kernelEntry 95  }
   
   
   kernelMaxT3MessageSize OBJECT-TYPE
      SYNTAX      INTEGER
      MAX-ACCESS  read-only
      STATUS      current
      DESCRIPTION "The maximum number of bytes allowed in messages that are received over the T3 protocol. If you configure custom network channels for this server, each channel can override this maximum message size.  This maximum message size helps guard against a denial of service attack in which a caller attempts to force the server to allocate more memory than is available thereby keeping the server from responding quickly to other requests.  A value of -1 causes the T3 protocol to use the maximums that are specified elsewhere along the order of precedence. "
      ::= { kernelEntry 100  }
   
   
   kernelStuckThreadMaxTime OBJECT-TYPE
      SYNTAX      INTEGER
      MAX-ACCESS  read-only
      STATUS      current
      DESCRIPTION "The number of seconds that a thread must be continually working before this server considers the thread stuck.  For example, if you set this to 600 seconds, WebLogic Server considers a thread to be 'stuck' after 600 seconds of continuous use.  In WebLogic Server 9.x and later, it is recommended that you use the ServerFailureTriggerMBean in the OverloadProtectionMBean. The ServerFailureTriggerMBean transitions the server to a FAILED state after the specified number of stuck threads are detected. The OverloadProtectionMBean has options to suspend or shutdown a failed server.  "
      ::= { kernelEntry 115  }
   
   
   kernelStuckThreadTimerInterval OBJECT-TYPE
      SYNTAX      INTEGER
      MAX-ACCESS  read-only
      STATUS      current
      DESCRIPTION "The number of seconds after which WebLogic Server periodically scans threads to see if they have been continually working for the configured maximum length of time. "
      ::= { kernelEntry 120  }
   
   
   kernelThreadPoolPercentSocketReaders OBJECT-TYPE
      SYNTAX      INTEGER
      MAX-ACCESS  read-only
      STATUS      current
      DESCRIPTION "The percentage of execute threads from the default queue that can be used as socket readers. "
      ::= { kernelEntry 125  }
   
   
   kernelInstrumentStackTraceEnabled OBJECT-TYPE
      SYNTAX      INTEGER
      MAX-ACCESS  read-only
      STATUS      current
      DESCRIPTION "Specifies whether the server returns stack traces for RMI calls that generate exceptions.  With RMI stack tracking enabled, if a client issues an RMI call to a server subsystem or to a module running within the server, and if the subsystem or module generates an exception that includes a stack trace, the server will return the exception as well as the stack trace. With it disabled, the server will return the exception without the stack trace details. "
      ::= { kernelEntry 130  }
   
   
   kernelLogRemoteExceptionsEnabled OBJECT-TYPE
      SYNTAX      INTEGER
      MAX-ACCESS  read-only
      STATUS      current
      DESCRIPTION "Specifies whether the server message log includes exceptions that are raised in remote systems. "
      ::= { kernelEntry 135  }
   
   
   kernelNativeIOEnabled OBJECT-TYPE
      SYNTAX      INTEGER
      MAX-ACCESS  read-only
      STATUS      current
      DESCRIPTION "Specifies whether native I/O is enabled for the server. "
      ::= { kernelEntry 140  }
   
   
   kernelReverseDNSAllowed OBJECT-TYPE
      SYNTAX      INTEGER
      MAX-ACCESS  read-only
      STATUS      current
      DESCRIPTION "Specifies whether the kernel is allowed to perform reverse DNS lookups. "
      ::= { kernelEntry 145  }
   
   
   kernelIdleConnectionTimeout OBJECT-TYPE
      SYNTAX      INTEGER
      MAX-ACCESS  read-only
      STATUS      current
      DESCRIPTION "The maximum number of seconds that a connection is allowed to be idle before it is closed by the server. The T3 and T3S protocols ignore this attribute. If you configure network channels for this server, each channel can override this idle connection message timeout.  This timeout helps guard against server deadlock through too many open connections. "
      ::= { kernelEntry 161  }
   
   
   kernelIIOPTxMechanism OBJECT-TYPE
      SYNTAX      OCTET STRING
      MAX-ACCESS  read-only
      STATUS      current
      DESCRIPTION "Configures IIOP propagate transactions using either WebLogic-specific JTA or the OMG-specified OTS.  It is not possible to use both because it affects the way transactions are negotiated. "
      ::= { kernelEntry 162  }
   
   
   kernelCompleteMessageTimeout OBJECT-TYPE
      SYNTAX      INTEGER
      MAX-ACCESS  read-only
      STATUS      current
      DESCRIPTION "The maximum number of seconds that this server waits for a complete message to be received. If you configure network channels for this server, each channel can override this message timeout.  This timeout helps guard against a denial of service attack in which a caller indicates that it will be sending a message of a certain size which it never finishes sending.  CompleteMessageTimeout affects the HTTP Response, such that if WebLogic Server discovers sockets inactive for longer than the CompleteMessageTimeout, the server will close these sockets. "
      ::= { kernelEntry 163  }
   
   
   kernelConnectTimeout OBJECT-TYPE
      SYNTAX      INTEGER
      MAX-ACCESS  read-only
      STATUS      current
      DESCRIPTION "The amount of time that this server should wait to establish an outbound socket connection before timing out. A value of 0 disables server connect timeout. "
      ::= { kernelEntry 164  }
   
   
   kernelUse81StyleExecuteQueues OBJECT-TYPE
      SYNTAX      OCTET STRING
      MAX-ACCESS  read-only
      STATUS      current
      DESCRIPTION "Backward compatibility mode to switch to 8.1 execute queues instead of WorkManagers. Each of the WorkManagers is converted to an individual execute queue. Setting this attribute requires a server restart.  "
      ::= { kernelEntry 165  }
   
   
   kernelMuxerClass OBJECT-TYPE
      SYNTAX      OCTET STRING
      MAX-ACCESS  read-only
      STATUS      current
      DESCRIPTION "Non-blocking IO is enabled by default on the server side. The default value is weblogic.socket.NIOSocketMuxer.  The Certicom SSL implementation is not supported with NIOSocketMuxer. If you need to secure internet communication, Oracle recommends enabling JSSE (Java Secure Socket Extension). "
      ::= { kernelEntry 166  }
   
   
   kernelPeriodLength OBJECT-TYPE
      SYNTAX      INTEGER
      MAX-ACCESS  read-only
      STATUS      current
      DESCRIPTION "The time interval in milliseconds of the heartbeat period. A value of 0 indicates that heartbeats are turned off. "
      ::= { kernelEntry 167  }
   
   
   kernelSocketReaders OBJECT-TYPE
      SYNTAX      INTEGER
      MAX-ACCESS  read-only
      STATUS      current
      DESCRIPTION "The number of socket reader threads. "
      ::= { kernelEntry 168  }
   
   
   kernelIdlePeriodsUntilTimeout OBJECT-TYPE
      SYNTAX      INTEGER
      MAX-ACCESS  read-only
      STATUS      current
      DESCRIPTION "The number of idle periods until peer is considered unreachable. "
      ::= { kernelEntry 169  }
   
   
   kernelMessagingBridgeThreadPoolSize OBJECT-TYPE
      SYNTAX      INTEGER
      MAX-ACCESS  read-only
      STATUS      current
      DESCRIPTION "Returns the size of the messaging bridge execute thread pool. "
      ::= { kernelEntry 170  }
   
   
   kernelAdministrationProtocol OBJECT-TYPE
      SYNTAX      OCTET STRING
      MAX-ACCESS  read-only
      STATUS      current
      DESCRIPTION "Returns the protocol to be used for administrative connections when none is specified. "
      ::= { kernelEntry 171  }
   
   
   kernelOutboundPrivateKeyEnabled OBJECT-TYPE
      SYNTAX      OCTET STRING
      MAX-ACCESS  read-only
      STATUS      current
      DESCRIPTION "Specifies whether the SSL identity specified by {@link SSLMBean#getServerPrivateKeyAlias() getSSLMBean#ServerPrivateKeyAlias} for this server should be used for outbound SSL connections on the default server channel. In normal circumstances the outbound identity is determined by the caller's environment. "
      ::= { kernelEntry 172  }
   
   
   kernelSocketBufferSizeAsChunkSize OBJECT-TYPE
      SYNTAX      OCTET STRING
      MAX-ACCESS  read-only
      STATUS      current
      DESCRIPTION "Specifies whether the server's buffer size for sending or receiving data through a raw socket should be set to 4KB.  Otherwise, the server does not impose a limit to the buffer size and defers to the operating system. This option is useful only on some operating systems for improving performance. It should be disabled in most environments. "
      ::= { kernelEntry 173  }
   
   
   kernelMaxMessageSize OBJECT-TYPE
      SYNTAX      INTEGER
      MAX-ACCESS  read-only
      STATUS      current
      DESCRIPTION "The maximum number of bytes allowed in messages that are received over all supported protocols, unless overridden by a protocol-specific setting or a custom channel setting.  The order of precedence for setting message size maximums is as follows:    A channel-wide maximum in a custom network channel.    A protocol-specific setting in the default network channel. See  {@link #getMaxCOMMessageSize() getMaxCOMMessageSize} {@link #getMaxHTTPMessageSize() getMaxHTTPMessageSize} {@link #getMaxIIOPMessageSize() getMaxIIOPessageSize} {@link #getMaxT3MessageSize() getMaxT3MessageSize}     The message maximum in this attribute.    This maximum message size helps guard against a denial of service attack in which a caller attempts to force the server to allocate more memory than is available thereby keeping the server from responding quickly to other requests. A client can set this value using the -Dweblogic.MaxMessageSize property. "
      ::= { kernelEntry 174  }
   
   
   kernelOutboundEnabled OBJECT-TYPE
      SYNTAX      OCTET STRING
      MAX-ACCESS  read-only
      STATUS      current
      DESCRIPTION "Specifies whether new server-to-server connections may consider the default server channel when initiating a connection. This is only relevant if the connection needs to be bound to the default listen address. This will only work for binary protocols that support both outbound and inbound traffic.  When this feature is not enabled, connections are initiated using a local address selected by the underlying hardware. For the default channel this is usually what is wanted for IP-routing to be effective. Note that since the default is false, other outbound channels will be considered in preference to the default channel.  Default administration channels, created when the domain-wide administration port is turned on, are always considered and bound when initiating an administrative connection. To allow IP-routing for administration traffic create custom admin with {@link NetworkAccessPointMBean#isOutboundEnabled isOutboundEnabled} set to false instead of enabling the domain-wide ADMIN port. "
      ::= { kernelEntry 175  }
   
   
   kernelGatheredWritesEnabled OBJECT-TYPE
      SYNTAX      OCTET STRING
      MAX-ACCESS  read-only
      STATUS      current
      DESCRIPTION "Enables gathered writes over NIO socket channels. Enabling this attribute increases efficiency during I/O in environments with high network throughput and should be used only when configuring a WebLogic domain for Oracle Exalogic. "
      ::= { kernelEntry 176  }
   
   
   kernelScatteredReadsEnabled OBJECT-TYPE
      SYNTAX      OCTET STRING
      MAX-ACCESS  read-only
      STATUS      current
      DESCRIPTION "Enables scattered reads over NIO socket channels. Enabling this attribute increases efficiency during I/O in environments with high network throughput and should be used only when configuring a WebLogic domain for Oracle Exalogic. "
      ::= { kernelEntry 177  }
   
   
   kernelUseDetailedThreadName OBJECT-TYPE
      SYNTAX      OCTET STRING
      MAX-ACCESS  read-only
      STATUS      current
      DESCRIPTION "Specifies whether to includes detailed information in self-tuning thread pool thread names. Setting this flag as true would include additional information, such as the name of the Work Manager for which the execute thread is executing the task, but at the expense of overhead in keeping the thread name updated with such information. "
      ::= { kernelEntry 178  }
   
   
   kernelCompleteWriteTimeout OBJECT-TYPE
      SYNTAX      INTEGER
      MAX-ACCESS  read-only
      STATUS      current
      DESCRIPTION "The maximum number of seconds that this server waits for a complete HTTP response to be sent.  A value of 0 disables the complete write timeout. The default value is derived from the CompleteHTTPMessageTimeout. If it is -1, then the CompleteMessageTimeout value is used for the default value. "
      ::= { kernelEntry 179  }
   
   
   kernelUseConcurrentQueueForRequestManager OBJECT-TYPE
      SYNTAX      OCTET STRING
      MAX-ACCESS  read-only
      STATUS      current
      DESCRIPTION "Reduces lock contention by using concurrent buffer queue to park incoming requests. Enabling this attribute increases throughput as requests are scheduled without acquiring any locks.  "
      ::= { kernelEntry 180  }
   
   
   kernelUseEnhancedPriorityQueueForRequestManager OBJECT-TYPE
      SYNTAX      OCTET STRING
      MAX-ACCESS  read-only
      STATUS      current
      DESCRIPTION "Reduces lock contention by using the enhanced ConcurrentCalendarQueue as the priority based queue for pending requests that are waiting for a thread.  This attribute should be enabled only in an Oracle Exalogic environment. "
      ::= { kernelEntry 181  }
   
   
   kernelPrintStackTraceInProduction OBJECT-TYPE
      SYNTAX      OCTET STRING
      MAX-ACCESS  read-only
      STATUS      current
      DESCRIPTION "Specifies whether the server message log includes exception stack trace that are raised in remote systems. "
      ::= { kernelEntry 182  }
   
   
   kernelAddWorkManagerThreadsByCpuCount OBJECT-TYPE
      SYNTAX      OCTET STRING
      MAX-ACCESS  read-only
      STATUS      current
      DESCRIPTION "Enables increased efficiency of the self-tuning thread pool by aligning it with the Exalogic processor architecture threading capabilities. Use only when configuring a WebLogic domain for Oracle Exalogic.  Enabling this attribute increases efficiency during I/O in environments with high network throughput. Disabling this attribute allows the thread pool to self-tune to match the demand of the workload at the expense of longer ramp up time.  "
      ::= { kernelEntry 183  }
   
   
   kernelAllowShrinkingPriorityRequestQueue OBJECT-TYPE
      SYNTAX      OCTET STRING
      MAX-ACCESS  read-only
      STATUS      current
      DESCRIPTION "Specifies whether self-tuning should allow shrinking of its priority based queue for pending requests after it has grown in size due to busy workload, and whether it should try to purge work requests that have already been picked up for processing due to minimum threads constraints before growing the queue. Setting this to true would help reduce memory footprint after the busy work period has ended, at the expense of the overhead of growing the request queue again at the next period of busy workload. It would also help to reduce the amount of memory allocated for the request queue, at the expense of the overhead required in purging already processed work requests from the queue. "
      ::= { kernelEntry 184  }
   
   
   kernelUseEnhancedIncrementAdvisor OBJECT-TYPE
      SYNTAX      OCTET STRING
      MAX-ACCESS  read-only
      STATUS      current
      DESCRIPTION "Specifies whether self-tuning should use the enhanced IncrementAdvisor implementation that uses a different algorithm to adjust the size of the self-tuning thread pool. "
      ::= { kernelEntry 185  }
   
   
   kernelTags OBJECT-TYPE
      SYNTAX      OCTET STRING
      MAX-ACCESS  read-only
      STATUS      current
      DESCRIPTION "Return all tags on this Configuration MBean "
      ::= { kernelEntry 186  }
   
   
   kernelEagerThreadLocalCleanup OBJECT-TYPE
      SYNTAX      OCTET STRING
      MAX-ACCESS  read-only
      STATUS      current
      DESCRIPTION "Specifies whether to clean up all ThreadLocals storage from self-tuning thread pool threads after they have finished processing each work request. By default, the self-tuning thread pool only cleans up ThreadLocal storage in its threads after an application is undeployed to avoid ClassLoader memory leak. "
      ::= { kernelEntry 187  }
   
   
   kernelIsolatePartitionThreadLocals OBJECT-TYPE
      SYNTAX      OCTET STRING
      MAX-ACCESS  read-only
      STATUS      current
      DESCRIPTION "Specified whether the server needs to ensure that threadlocals storage from self-tuning thread pool threads must be cleaned up before the threads are used for processing work requests from a different partition. This helps ensure that no threadlocals from a different partition can be retrieved from work requests while being processed by a self-tuning thread pool thread.  The different between this attribute and the eagerThreadLocalCleanup attribute is that threadlocals storage will not be cleared if the previous work request processed by the self-tuning thread pool thread was for the same partition, whereas with eagerThreadLocalCleanup set, the threadlocals storage will also be cleared in this case. "
      ::= { kernelEntry 188  }
   
   
   logTable OBJECT-TYPE
      SYNTAX      SEQUENCE OF LogEntry
      MAX-ACCESS  not-accessible
      STATUS      current
      DESCRIPTION "Configures the threshold severity level and filter settings for logging output. Specifies whether the server logging is based on a Log4j implementation or the default Java Logging APIs. Redirects the JVM stdout and stderr output to the registered log destinations. "
      ::= { wls 700  }
      
   
   logEntry OBJECT-TYPE
      SYNTAX      LogEntry
      MAX-ACCESS  not-accessible
      STATUS      current
      DESCRIPTION "Entry of logTable"
      INDEX { logIndex}
      ::= { logTable 1 }
      
   LogEntry ::=
      SEQUENCE
      {
         logIndex             DisplayString,
         logObjectName        DisplayString,
         logType              DisplayString,
         logName              DisplayString,
         logParent            DisplayString,
         logFileName          DisplayString,
         logRotationType      DisplayString,
         logNumberOfFilesLimited INTEGER,
         logFileCount         INTEGER,
         logFileTimeSpan      INTEGER,
         logFileMinSize       INTEGER,
         logRedirectStderrToServerLogEnabled OCTET STRING,
         logLogFileSeverity   OCTET STRING,
         logLoggerSeverity    OCTET STRING,
         logBufferSizeKB      INTEGER,
         logMemoryBufferSeverity OCTET STRING,
         logLog4jLoggingEnabled OCTET STRING,
         logRotationTime      OCTET STRING,
         logStdoutLogStack    OCTET STRING,
         logRotateLogOnStartup OCTET STRING,
         logRedirectStdoutToServerLogEnabled OCTET STRING,
         logMemoryBufferSize  INTEGER,
         logStdoutFormat      OCTET STRING,
         logDomainLogBroadcasterBufferSize INTEGER,
         logDateFormatPattern OCTET STRING,
         logDomainLogBroadcastSeverity OCTET STRING,
         logStdoutSeverity    OCTET STRING,
         logLogFileRotationDir OCTET STRING,
         logServerLoggingBridgeUseParentLoggersEnabled OCTET STRING,
         logLogMonitoringEnabled OCTET STRING,
         logLogMonitoringThrottleThreshold INTEGER,
         logLogMonitoringThrottleMessageLength INTEGER,
         logTags              OCTET STRING,
         logLogMonitoringIntervalSecs INTEGER,
         logLogMonitoringMaxThrottleMessageSignatureCount INTEGER
      }
      
   
   logIndex OBJECT-TYPE
      SYNTAX      DisplayString (SIZE (1..16))
      MAX-ACCESS  read-only
      STATUS      current
      DESCRIPTION "Unique value directed from ObjectName which is used as table index"
      ::= { logEntry 1  }
   
   
   logObjectName OBJECT-TYPE
      SYNTAX      DisplayString (SIZE (1..256))
      MAX-ACCESS  read-only
      STATUS      current
      DESCRIPTION "JMX-standard MBean name"
      ::= { logEntry 5  }
   
   
   logType OBJECT-TYPE
      SYNTAX      DisplayString (SIZE (1..64))
      MAX-ACCESS  read-only
      STATUS      current
      DESCRIPTION "Returns the type of the MBean. "
      ::= { logEntry 10  }
   
   
   logName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { logEntry 15  }
   
   
   logParent OBJECT-TYPE
      SYNTAX      DisplayString (SIZE (1..256))
      MAX-ACCESS  read-only
      STATUS      current
      DESCRIPTION "BEA-proprietary Parent object's identification, with syntax
      <type>:<name>"
      ::= { logEntry 20  }
   
   
   logFileName OBJECT-TYPE
      SYNTAX      DisplayString (SIZE (1..256))
      MAX-ACCESS  read-only
      STATUS      current
      DESCRIPTION "The name of the file that stores current log messages. Usually it is a computed value based on the name of the parent of this MBean. For example, for a server log, it is SERVER_NAME.log.  However, if the name of the parent cannot be obtained, the file name is weblogic.log. If you specify a relative pathname, it is interpreted as relative to the server's root directory.  To include a time and date stamp in the file name when the log file is rotated, add java.text.SimpleDateFormat variables to the file name. Surround each variable with percentage (%) characters.  For example, if the file name is defined to be myserver_%yyyy%_%MM%_%dd%_%hh%_%mm%.log, the log file will be named myserver_yyyy_mm_dd_hh_mm.log.  When the log file is rotated, the rotated file name contains the date stamp. For example, if the log file is rotated for the first time on 2 April, 2003 at 10:05 AM, the log file that contains the old messages will be named myserver_2003_04_02_10_05.log00001.  If you do not include a time and date stamp, the rotated log files are numbered in order of creation. For example, myserver.log00007. "
      ::= { logEntry 25  }
   
   
   logRotationType OBJECT-TYPE
      SYNTAX      DisplayString (SIZE (1..16))
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as SERVER_NAME.lognnnnn.  TIME At each time interval that you specify in TimeSpan, the server renames the file as SERVER_NAME.lognnnnn.   After the server renames a file, subsequent messages accumulate in a new file with the name that you specified as the log file name. "
      ::= { logEntry 30  }
   
   
   logNumberOfFilesLimited OBJECT-TYPE
      SYNTAX      INTEGER
                  {
                     true(1),
                     false(2)
                  }
      
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require. "
      ::= { logEntry 35  }
   
   
   logFileCount OBJECT-TYPE
      SYNTAX      INTEGER
      MAX-ACCESS  read-only
      STATUS      current
      DESCRIPTION "The maximum number of log files that the server creates when it rotates the log. This number does not include the file that the server uses to store current messages. (Requires that you enable Number of Files Limited.) "
      ::= { logEntry 40  }
   
   
   logFileTimeSpan OBJECT-TYPE
      SYNTAX      INTEGER
      MAX-ACCESS  read-only
      STATUS      current
      DESCRIPTION "The interval (in hours) at which the server saves old log messages to another file. (Requires that you specify a file rotation type of TIME.) "
      ::= { logEntry 45  }
   
   
   logFileMinSize OBJECT-TYPE
      SYNTAX      INTEGER
      MAX-ACCESS  read-only
      STATUS      current
      DESCRIPTION "The size (1 - 2097150 kilobytes) that triggers the server to move log messages to a separate file. The default is 500 kilobytes. After the log file reaches the specified minimum size, the next time the server checks the file size, it will rename the current log file as SERVER_NAME.lognnnnn and create a new one to store subsequent messages. (Requires that you specify a file rotation type of Size.) "
      ::= { logEntry 50  }
   
   
   logRedirectStderrToServerLogEnabled OBJECT-TYPE
      SYNTAX      OCTET STRING
      MAX-ACCESS  read-only
      STATUS      current
      DESCRIPTION "Specifies whether the stderr of the JVM in which a WebLogic Server instance runs is redirected to the WebLogic Logging system. When this attribute is enabled, the stderr content is published to all the registered log destinations, such as the server terminal console and log file.  Note that JVM messages are redirected asynchronously. In the event of an overload situation, these messages may be dropped. As a best practice, Oracle recommends using one of the supported logging APIs instead. "
      ::= { logEntry 51  }
   
   
   logLogFileSeverity OBJECT-TYPE
      SYNTAX      OCTET STRING
      MAX-ACCESS  read-only
      STATUS      current
      DESCRIPTION "The minimum severity of log messages going to the server log file. By default all messages go to the log file. "
      ::= { logEntry 52  }
   
   
   logLoggerSeverity OBJECT-TYPE
      SYNTAX      OCTET STRING
      MAX-ACCESS  read-only
      STATUS      current
      DESCRIPTION "The minimum severity of log messages going to all log destinations. "
      ::= { logEntry 53  }
   
   
   logBufferSizeKB OBJECT-TYPE
      SYNTAX      INTEGER
      MAX-ACCESS  read-only
      STATUS      current
      DESCRIPTION "Gets the underlying log buffer size in kilobytes "
      ::= { logEntry 54  }
   
   
   logMemoryBufferSeverity OBJECT-TYPE
      SYNTAX      OCTET STRING
      MAX-ACCESS  read-only
      STATUS      current
      DESCRIPTION "The minimum severity of log messages going to the memory buffer of recent log events. Messages with a lower severity than the specified value will not be cached in the buffer. "
      ::= { logEntry 55  }
   
   
   logLog4jLoggingEnabled OBJECT-TYPE
      SYNTAX      OCTET STRING
      MAX-ACCESS  read-only
      STATUS      current
      DESCRIPTION "Specifies whether the server logging is based on a Log4j implementation. By default, WebLogic logging uses an implementation based on the Java Logging APIs which are part of the JDK.  Applications that use the WebLogic Message Catalog framework or the NonCatalogLogger will not be affected by the underlying Logging implementation. "
      ::= { logEntry 56  }
   
   
   logRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  Note that WebLogic Server sets a threshold size limit of 500 MB before it forces a hard rotation to prevent excessive log file growth.  Use the following format: H:mm, where  H is Hour in day (0-23) mm is the minute in hour  "
      ::= { logEntry 57  }
   
   
   logStdoutLogStack OBJECT-TYPE
      SYNTAX      OCTET STRING
      MAX-ACCESS  read-only
      STATUS      current
      DESCRIPTION "Specifies whether to dump stack traces to the console when included in logged message. "
      ::= { logEntry 58  }
   
   
   logRotateLogOnStartup OBJECT-TYPE
      SYNTAX      OCTET STRING
      MAX-ACCESS  read-only
      STATUS      current
      DESCRIPTION "Specifies whether a server rotates its log file during its startup cycle. The default value in production mode is false. "
      ::= { logEntry 59  }
   
   
   logRedirectStdoutToServerLogEnabled OBJECT-TYPE
      SYNTAX      OCTET STRING
      MAX-ACCESS  read-only
      STATUS      current
      DESCRIPTION "Specifies whether the stdout of the JVM in which a WebLogic Server instance runs is redirected to the WebLogic logging system. When this attribute is enabled, the stdout content is published to all the registered log destinations, such as the server terminal console and log file.  Note that JVM messages are redirected asynchronously. In the event of an overload situation, these messages may be dropped. As a best practice, Oracle recommends using one of the supported logging APIs instead. "
      ::= { logEntry 60  }
   
   
   logMemoryBufferSize OBJECT-TYPE
      SYNTAX      INTEGER
      MAX-ACCESS  read-only
      STATUS      current
      DESCRIPTION "The size of the memory buffer that holds the last n log records. This is used to support viewing the most recent log record entries (tail viewing) from the WebLogic Administration Console. "
      ::= { logEntry 61  }
   
   
   logStdoutFormat OBJECT-TYPE
      SYNTAX      OCTET STRING
      MAX-ACCESS  read-only
      STATUS      current
      DESCRIPTION "The output format to use when logging to the console. "
      ::= { logEntry 62  }
   
   
   logDomainLogBroadcasterBufferSize OBJECT-TYPE
      SYNTAX      INTEGER
      MAX-ACCESS  read-only
      STATUS      current
      DESCRIPTION "Broadcasts log messages to the domain log in batch mode.  The size of the buffer for log messages that are sent to the domain log. The buffer is maintained on the Managed Server and is broadcasted to the domain log when it is full.  If you notice performance issues due to a high rate of log messages being generated, set this value higher. This will cause the buffer to be broadcasted less frequently from the Managed Server to the domain log. In production environments, it is not recommended to set the buffer size lower than the production default of 10. "
      ::= { logEntry 63  }
   
   
   logDateFormatPattern OBJECT-TYPE
      SYNTAX      OCTET STRING
      MAX-ACCESS  read-only
      STATUS      current
      DESCRIPTION "The date format pattern used for rendering dates in the  log. The DateFormatPattern string conforms to the specification of the java.text.SimpleDateFormat class. "
      ::= { logEntry 64  }
   
   
   logDomainLogBroadcastSeverity OBJECT-TYPE
      SYNTAX      OCTET STRING
      MAX-ACCESS  read-only
      STATUS      current
      DESCRIPTION "The minimum severity of log messages going to the domain log from this server's log broadcaster. Messages with a lower severity than the specified value will not be published to the domain log. "
      ::= { logEntry 65  }
   
   
   logStdoutSeverity OBJECT-TYPE
      SYNTAX      OCTET STRING
      MAX-ACCESS  read-only
      STATUS      current
      DESCRIPTION "The minimum severity of log messages going to the standard out. Messages with a lower severity than the specified value will not be published to standard out. "
      ::= { logEntry 66  }
   
   
   logLogFileRotationDir OBJECT-TYPE
      SYNTAX      OCTET STRING
      MAX-ACCESS  read-only
      STATUS      current
      DESCRIPTION "The directory where the rotated log files will be stored. By default the rotated files are stored in the same directory where the log file is stored. "
      ::= { logEntry 67  }
   
   
   logServerLoggingBridgeUseParentLoggersEnabled OBJECT-TYPE
      SYNTAX      OCTET STRING
      MAX-ACCESS  read-only
      STATUS      current
      DESCRIPTION "Specifies whether application log messages are propagated to the parent node in the Logger tree or to the WebLogic Server log by means of the Logging Bridge. By default, this attribute is disabled, which results in application log messages being propagated to the WebLogic Server log.  Note the following behavior:  If WebLogic Server is configured to be based upon the the Java Logging API (the default), the Logging Bridge is made available as a java.util.logging.Handler object. If  WebLogic Server is configured to be based upon a Log4j implementation, the Logging Bridge is made available as a org.apache.log4j.Appender object. If the ServerLoggingBridgeUseParentLoggersEnabled is disabled, applications that use either the Java Logging API or Log4j have their log messages redirected by the Logging Bridge to the WebLogic Server log.  If the ServerLoggingBridgeUseParentLoggersEnabled is enabled, applications that use the Java Logging API have their log messages propagated to the parent node in the global Java Logging Logger tree. If the ServerLoggingBridgeUseParentLoggersEnabled is enabled, applications that use Log4j have their log messages propagated to the parent node in the Log4j Logger tree.  "
      ::= { logEntry 68  }
   
   
   logLogMonitoringEnabled OBJECT-TYPE
      SYNTAX      OCTET STRING
      MAX-ACCESS  read-only
      STATUS      current
      DESCRIPTION "Enable or disable log monitoring. "
      ::= { logEntry 69  }
   
   
   logLogMonitoringThrottleThreshold OBJECT-TYPE
      SYNTAX      INTEGER
      MAX-ACCESS  read-only
      STATUS      current
      DESCRIPTION "The threshold number of messages logged during the evaluation period which enables or disables the throttling.  Once throttling is enabled messages with the same repeating message signatures are throttled. Every nth repeated message specified by this attribute is logged in a monitoring cycle.  "
      ::= { logEntry 70  }
   
   
   logLogMonitoringThrottleMessageLength OBJECT-TYPE
      SYNTAX      INTEGER
      MAX-ACCESS  read-only
      STATUS      current
      DESCRIPTION "Cut-off length of the log message for evaluation during throttle period. The log message length is truncated to this length for evaluation of repeated logging events. "
      ::= { logEntry 71  }
   
   
   logTags OBJECT-TYPE
      SYNTAX      OCTET STRING
      MAX-ACCESS  read-only
      STATUS      current
      DESCRIPTION "Return all tags on this Configuration MBean "
      ::= { logEntry 72  }
   
   
   logLogMonitoringIntervalSecs OBJECT-TYPE
      SYNTAX      INTEGER
      MAX-ACCESS  read-only
      STATUS      current
      DESCRIPTION "Timer interval in seconds to check the counts of messages logged during the interval. "
      ::= { logEntry 73  }
   
   
   logLogMonitoringMaxThrottleMessageSignatureCount OBJECT-TYPE
      SYNTAX      INTEGER
      MAX-ACCESS  read-only
      STATUS      current
      DESCRIPTION "Maximum number of unique message signatures that will be monitored during the throttle interval. "
      ::= { logEntry 74  }
   
   
   networkChannelTable OBJECT-TYPE
      SYNTAX      SEQUENCE OF NetworkChannelEntry
      MAX-ACCESS  not-accessible
      STATUS      current
      DESCRIPTION "This table represents a networkChannel in the domain."
      ::= { wls 703  }
      
   
   networkChannelEntry OBJECT-TYPE
      SYNTAX      NetworkChannelEntry
      MAX-ACCESS  not-accessible
      STATUS      current
      DESCRIPTION "Entry of networkChannelTable"
      INDEX { networkChannelIndex}
      ::= { networkChannelTable 1 }
      
   NetworkChannelEntry ::=
      SEQUENCE
      {
         networkChannelIndex  DisplayString,
         networkChannelObjectName DisplayString,
         networkChannelType   DisplayString,
         networkChannelName   DisplayString,
         networkChannelParent DisplayString,
         networkChannelAcceptBacklog INTEGER,
         networkChannelChannelWeight INTEGER,
         networkChannelClusterAddress DisplayString,
         networkChannelCompleteCOMMessageTimeout INTEGER,
         networkChannelCompleteHTTPMessageTimeout INTEGER,
         networkChannelCompleteT3MessageTimeout INTEGER,
         networkChannelDescription DisplayString,
         networkChannelListenPort INTEGER,
         networkChannelLoginTimeoutMillis INTEGER,
         networkChannelLoginTimeoutMillisSSL INTEGER,
         networkChannelMaxCOMMessageSize INTEGER,
         networkChannelMaxT3MessageSize INTEGER,
         networkChannelMaxHTTPMessageSize INTEGER,
         networkChannelSSLListenPort INTEGER,
         networkChannelTunnelingClientPingSecs INTEGER,
         networkChannelTunnelingClientTimeoutSecs INTEGER,
         networkChannelBoundOutgoingEnabled INTEGER,
         networkChannelCOMEnabled INTEGER,
         networkChannelHTTPEnabled INTEGER,
         networkChannelHTTPSEnabled INTEGER,
         networkChannelListenPortEnabled INTEGER,
         networkChannelOutgoingEnabled INTEGER,
         networkChannelSSLListenPortEnabled INTEGER,
         networkChannelT3Enabled INTEGER,
         networkChannelT3SEnabled INTEGER,
         networkChannelTunnelingEnabled INTEGER,
         networkChannelDeploymentOrder INTEGER
      }
      
   
   networkChannelIndex OBJECT-TYPE
      SYNTAX      DisplayString (SIZE (1..16))
      MAX-ACCESS  read-only
      STATUS      current
      DESCRIPTION "Unique value directed from ObjectName which is used as table index"
      ::= { networkChannelEntry 1  }
   
   
   networkChannelObjectName OBJECT-TYPE
      SYNTAX      DisplayString (SIZE (1..256))
      MAX-ACCESS  read-only
      STATUS      current
      DESCRIPTION "JMX-standard MBean name"
      ::= { networkChannelEntry 5  }
   
   
   networkChannelType OBJECT-TYPE
      SYNTAX      DisplayString (SIZE (1..64))
      MAX-ACCESS  read-only
      STATUS      current
      DESCRIPTION "BEA-proprietary MBean type"
      ::= { networkChannelEntry 10  }
   
   
   networkChannelName OBJECT-TYPE
      SYNTAX      DisplayString (SIZE (1..64))
      MAX-ACCESS  read-only
      STATUS      current
      DESCRIPTION "BEA-proprietary MBean name"
      ::= { networkChannelEntry 15  }
   
   
   networkChannelParent OBJECT-TYPE
      SYNTAX      DisplayString (SIZE (1..256))
      MAX-ACCESS  read-only
      STATUS      current
      DESCRIPTION "BEA-proprietary Parent object's identification, with syntax
      <type>:<name>"
      ::= { networkChannelEntry 20  }
   
   
   networkChannelAcceptBacklog OBJECT-TYPE
      SYNTAX      INTEGER
      MAX-ACCESS  read-only
      STATUS      current
      DESCRIPTION "Allowed backlog of connection requests on the listen port(s).
      * Individual servers may override this value using a NetworkAccessPointMBean.
      * Setting the backlog to 0 may prevent accepting any incoming connection on
      * some of the OS."
      ::= { networkChannelEntry 25  }
   
   
   networkChannelChannelWeight OBJECT-TYPE
      SYNTAX      INTEGER
      MAX-ACCESS  read-only
      STATUS      current
      DESCRIPTION "A weight to give this channel when creating server-to-server
      * connections."
      ::= { networkChannelEntry 30  }
   
   
   networkChannelClusterAddress OBJECT-TYPE
      SYNTAX      DisplayString (SIZE (1..256))
      MAX-ACCESS  read-only
      STATUS      current
      DESCRIPTION "This channel's cluster address.  If this
      * is not set, the cluster address from the cluster
      * configuration is used in its place."
      ::= { networkChannelEntry 35  }
   
   
   networkChannelCompleteCOMMessageTimeout OBJECT-TYPE
      SYNTAX      INTEGER
      MAX-ACCESS  read-only
      STATUS      current
      DESCRIPTION "The maximum number of seconds spent
      * waiting for a complete COM message to be received.
      * This attribute helps guard against denial of
      * service attacks in which a caller indicates that
      * they will be sending a message of a certain size
      * which they never finish sending."
      ::= { networkChannelEntry 40  }
   
   
   networkChannelCompleteHTTPMessageTimeout OBJECT-TYPE
      SYNTAX      INTEGER
      MAX-ACCESS  read-only
      STATUS      current
      DESCRIPTION "The maximum number of seconds spent
      * waiting for a complete HTTP message to be received.
      * This attribute helps guard against denial of
      * service attacks in which a caller indicates that
      * they will be sending a message of a certain size
      * which they never finish sending."
      ::= { networkChannelEntry 45  }
   
   
   networkChannelCompleteT3MessageTimeout OBJECT-TYPE
      SYNTAX      INTEGER
      MAX-ACCESS  read-only
      STATUS      current
      DESCRIPTION "The maximum number of seconds spent
      * waiting for a complete T3 message to be received.
      * This attribute helps guard against denial of
      * service attacks in which a caller indicates that
      * they will be sending a message of a certain size
      * which they never finish sending.
      * Individual servers may override this value using a NetworkAccessPointMBean."
      ::= { networkChannelEntry 50  }
   
   
   networkChannelDescription OBJECT-TYPE
      SYNTAX      DisplayString (SIZE (1..64))
      MAX-ACCESS  read-only
      STATUS      current
      DESCRIPTION "Optional short description of this channel for console display
      * purposes."
      ::= { networkChannelEntry 55  }
   
   
   networkChannelListenPort OBJECT-TYPE
      SYNTAX      INTEGER
      MAX-ACCESS  read-only
      STATUS      current
      DESCRIPTION "he plaintext (non-SSL) listen port for the channel.  Individual servers
      * may override
      * this value, but may not enable the port if disabled here
      * and may not disable the port if enabled here.
      * Individual servers may override this value using a NetworkAccessPointMBean."
      ::= { networkChannelEntry 60  }
   
   
   networkChannelLoginTimeoutMillis OBJECT-TYPE
      SYNTAX      INTEGER
      MAX-ACCESS  read-only
      STATUS      current
      DESCRIPTION "The login timeout for the server, in milliseconds. This
      * value must be equal to or greater than 0.
      * Individual servers may override this value using a NetworkAccessPointMBean."
      ::= { networkChannelEntry 65  }
   
   
   networkChannelLoginTimeoutMillisSSL OBJECT-TYPE
      SYNTAX      INTEGER
      MAX-ACCESS  read-only
      STATUS      current
      DESCRIPTION "Duration allowed for an SSL login sequence.  If the duration is exceeded, the
      * login is timed out.  0 to disable.
      * Individual servers may override this value using a NetworkAccessPointMBean."
      ::= { networkChannelEntry 70  }
   
   
   networkChannelMaxCOMMessageSize OBJECT-TYPE
      SYNTAX      INTEGER
      MAX-ACCESS  read-only
      STATUS      current
      DESCRIPTION "The maximum COM message size allowable in a message header.
      * This attribute attempts to prevent a denial of service attack whereby
      * a caller attempts to force the server to allocate more memory than
      * is available thereby keeping the server from responding quickly to
      * other requests."
      ::= { networkChannelEntry 75  }
   
   
   networkChannelMaxT3MessageSize OBJECT-TYPE
      SYNTAX      INTEGER
      MAX-ACCESS  read-only
      STATUS      current
      DESCRIPTION "The maximum T3 message size allowable in a message header.
      * This attribute attempts to prevent a denial of service attack whereby
      * a caller attempts to force the server to allocate more memory than
      * is available thereby keeping the server from responding quickly to
      * other requests."
      ::= { networkChannelEntry 80  }
   
   
   networkChannelMaxHTTPMessageSize OBJECT-TYPE
      SYNTAX      INTEGER
      MAX-ACCESS  read-only
      STATUS      current
      DESCRIPTION "The SSL listen port for the channel.  Individual server's may override
      * this value, but may not enable the port if disabled here
      * and may not disable the port if enabled here.   SSL must be configured
      * and enabled for this port to work.
      * Individual servers may override this value using a NetworkAccessPointMBean."
      ::= { networkChannelEntry 85  }
   
   
   networkChannelSSLListenPort OBJECT-TYPE
      SYNTAX      INTEGER
      MAX-ACCESS  read-only
      STATUS      current
      DESCRIPTION "The maximum number of seconds spent
      * waiting for a complete HTTP message to be received.
      * This attribute helps guard against denial of
      * service attacks in which a caller indicates that
      * they will be sending a message of a certain size
      * which they never finish sending."
      ::= { networkChannelEntry 90  }
   
   
   networkChannelTunnelingClientPingSecs OBJECT-TYPE
      SYNTAX      INTEGER
      MAX-ACCESS  read-only
      STATUS      current
      DESCRIPTION "Interval (in seconds) at which to ping an http-tunneled client to see
      * if its still alive.
      * Individual servers may override this value using a NetworkAccessPointMBean."
      ::= { networkChannelEntry 95  }
   
   
   networkChannelTunnelingClientTimeoutSecs OBJECT-TYPE
      SYNTAX      INTEGER
      MAX-ACCESS  read-only
      STATUS      current
      DESCRIPTION "Duration (in seconds) after which a missing http-tunneled client is
      * considered dead.
      * Individual servers may override this value using a NetworkAccessPointMBean."
      ::= { networkChannelEntry 100  }
   
   
   networkChannelBoundOutgoingEnabled OBJECT-TYPE
      SYNTAX      INTEGER
      MAX-ACCESS  read-only
      STATUS      current
      DESCRIPTION "Bind new outgoing server side T3 or T3S connections 
      * to the server channel's listen address.  Other
      * protocols ignore this field.  This field is ignored
      * for connections initiated via URLs, it takes
      * effect if and only if the connection was initiated
      * by accessing a remote reference (such as an EJB
      * or RMI stub.)."
      ::= { networkChannelEntry 105  }
   
   
   networkChannelCOMEnabled OBJECT-TYPE
      SYNTAX      INTEGER
      MAX-ACCESS  read-only
      STATUS      current
      DESCRIPTION "Whether or not plaintext (non-SSL) COM traffic is enabled."
      ::= { networkChannelEntry 110  }
   
   
   networkChannelHTTPEnabled OBJECT-TYPE
      SYNTAX      INTEGER
      MAX-ACCESS  read-only
      STATUS      current
      DESCRIPTION "Whether or not plaintext (non-SSL) HTTP traffic is enabled."
      ::= { networkChannelEntry 115  }
   
   
   networkChannelHTTPSEnabled OBJECT-TYPE
      SYNTAX      INTEGER
      MAX-ACCESS  read-only
      STATUS      current
      DESCRIPTION "Whether or not secure (SSL) HTTP traffic is enabled."
      ::= { networkChannelEntry 120  }
   
   
   networkChannelListenPortEnabled OBJECT-TYPE
      SYNTAX      INTEGER
      MAX-ACCESS  read-only
      STATUS      current
      DESCRIPTION "Whether or not plaintext port is enabled for the channel."
      ::= { networkChannelEntry 125  }
   
   
   networkChannelOutgoingEnabled OBJECT-TYPE
      SYNTAX      INTEGER
      MAX-ACCESS  read-only
      STATUS      current
      DESCRIPTION "Whether or not new server-to-server connections may
      * consider this channel when initiating"
      ::= { networkChannelEntry 130  }
   
   
   networkChannelSSLListenPortEnabled OBJECT-TYPE
      SYNTAX      INTEGER
      MAX-ACCESS  read-only
      STATUS      current
      DESCRIPTION "Whether or not SSL port is enabled for the channel.  SSL must be configured
      * and enabled in addition to this setting for the SSL port to work"
      ::= { networkChannelEntry 135  }
   
   
   networkChannelT3Enabled OBJECT-TYPE
      SYNTAX      INTEGER
      MAX-ACCESS  read-only
      STATUS      current
      DESCRIPTION "Whether or not plaintext (non-SSL) T3 traffic is enabled.
      * Note that it is not possible to disable T3 traffic on the default channel(s)"
      ::= { networkChannelEntry 140  }
   
   
   networkChannelT3SEnabled OBJECT-TYPE
      SYNTAX      INTEGER
      MAX-ACCESS  read-only
      STATUS      current
      DESCRIPTION "Whether or not secure T3 traffic is enabled.
      * Note that it is not possible to disable T3 traffic on the default channel(s)"
      ::= { networkChannelEntry 145  }
   
   
   networkChannelTunnelingEnabled OBJECT-TYPE
      SYNTAX      INTEGER
      MAX-ACCESS  read-only
      STATUS      current
      DESCRIPTION "Enables tunneling via http."
      ::= { networkChannelEntry 150  }
   
   
   networkChannelDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { networkChannelEntry 151  }
   
   
   networkAccessPointTable OBJECT-TYPE
      SYNTAX      SEQUENCE OF NetworkAccessPointEntry
      MAX-ACCESS  not-accessible
      STATUS      current
      DESCRIPTION "A server can specify additional network connections by using a NetworkAccessPointMBean.  The NetworkAccessPointMBean is also used to set the listen address and external DNS name that a server uses for a particular channel. "
      ::= { wls 705  }
      
   
   networkAccessPointEntry OBJECT-TYPE
      SYNTAX      NetworkAccessPointEntry
      MAX-ACCESS  not-accessible
      STATUS      current
      DESCRIPTION "Entry of networkAccessPointTable"
      INDEX { networkAccessPointIndex}
      ::= { networkAccessPointTable 1 }
      
   NetworkAccessPointEntry ::=
      SEQUENCE
      {
         networkAccessPointIndex DisplayString,
         networkAccessPointObjectName DisplayString,
         networkAccessPointType DisplayString,
         networkAccessPointName DisplayString,
         networkAccessPointParent DisplayString,
         networkAccessPointAcceptBacklog INTEGER,
         networkAccessPointListenAddress DisplayString,
         networkAccessPointListenPort INTEGER,
         networkAccessPointLoginTimeoutMillis INTEGER,
         networkAccessPointTunnelingClientPingSecs INTEGER,
         networkAccessPointTunnelingClientTimeoutSecs INTEGER,
         networkAccessPointUseFastSerialization OCTET STRING,
         networkAccessPointProxyPort INTEGER,
         networkAccessPointTwoWaySSLEnabled OCTET STRING,
         networkAccessPointChannelWeight INTEGER,
         networkAccessPointHttpEnabledForThisProtocol OCTET STRING,
         networkAccessPointTimeoutConnectionWithPendingResponses OCTET STRING,
         networkAccessPointOutboundEnabled OCTET STRING,
         networkAccessPointEnabled OCTET STRING,
         networkAccessPointCustomPrivateKeyAlias OCTET STRING,
         networkAccessPointConnectTimeout INTEGER,
         networkAccessPointMaxConnectedClients INTEGER,
         networkAccessPointIdleConnectionTimeout INTEGER,
         networkAccessPointMaxBackoffBetweenFailures INTEGER,
         networkAccessPointProtocol OCTET STRING,
         networkAccessPointPrivateKeyAlias OCTET STRING,
         networkAccessPointTunnelingEnabled OCTET STRING,
         networkAccessPointClusterAddress OCTET STRING,
         networkAccessPointChannelIdentityCustomized OCTET STRING,
         networkAccessPointMaxMessageSize INTEGER,
         networkAccessPointPublicPort INTEGER,
         networkAccessPointOutboundPrivateKeyEnabled OCTET STRING,
         networkAccessPointCompleteMessageTimeout INTEGER,
         networkAccessPointPublicAddress OCTET STRING,
         networkAccessPointClientCertificateEnforced OCTET STRING,
         networkAccessPointPrivateKeyPassPhrase OCTET STRING,
         networkAccessPointProxyAddress OCTET STRING,
         networkAccessPointSDPEnabled OCTET STRING,
         networkAccessPointOutboundPrivateKeyPassPhrase OCTET STRING,
         networkAccessPointOutboundPrivateKeyAlias OCTET STRING,
         networkAccessPointResolveDNSName OCTET STRING,
         networkAccessPointOutboundCertificateValidation OCTET STRING,
         networkAccessPointAllowUnencryptedNullCipher OCTET STRING,
         networkAccessPointCustomIdentityKeyStoreFileName OCTET STRING,
         networkAccessPointInboundCertificateValidation OCTET STRING,
         networkAccessPointHostnameVerificationIgnored OCTET STRING,
         networkAccessPointCustomIdentityKeyStoreType OCTET STRING,
         networkAccessPointCiphersuites OCTET STRING,
         networkAccessPointHostnameVerifier OCTET STRING,
         networkAccessPointTags OCTET STRING,
         networkAccessPointMinimumTLSProtocolVersion OCTET STRING,
         networkAccessPointSSLv2HelloEnabled OCTET STRING,
         networkAccessPointClientInitSecureRenegotiationAccepted OCTET STRING
      }
      
   
   networkAccessPointIndex OBJECT-TYPE
      SYNTAX      DisplayString (SIZE (1..16))
      MAX-ACCESS  read-only
      STATUS      current
      DESCRIPTION "Unique value directed from ObjectName which is used as table index"
      ::= { networkAccessPointEntry 1  }
   
   
   networkAccessPointObjectName OBJECT-TYPE
      SYNTAX      DisplayString (SIZE (1..256))
      MAX-ACCESS  read-only
      STATUS      current
      DESCRIPTION "JMX-standard MBean name"
      ::= { networkAccessPointEntry 5  }
   
   
   networkAccessPointType OBJECT-TYPE
      SYNTAX      DisplayString (SIZE (1..64))
      MAX-ACCESS  read-only
      STATUS      current
      DESCRIPTION "Returns the type of the MBean. "
      ::= { networkAccessPointEntry 10  }
   
   
   networkAccessPointName OBJECT-TYPE
      SYNTAX      DisplayString (SIZE (1..64))
      MAX-ACCESS  read-only
      STATUS      current
      DESCRIPTION "The name of this network channel. "
      ::= { networkAccessPointEntry 15  }
   
   
   networkAccessPointParent OBJECT-TYPE
      SYNTAX      DisplayString (SIZE (1..256))
      MAX-ACCESS  read-only
      STATUS      current
      DESCRIPTION "BEA-proprietary Parent object's identification, with syntax
      <type>:<name>"
      ::= { networkAccessPointEntry 20  }
   
   
   networkAccessPointAcceptBacklog OBJECT-TYPE
      SYNTAX      INTEGER
      MAX-ACCESS  read-only
      STATUS      current
      DESCRIPTION "The number of backlogged, new TCP connection requests that this network channel allows. A value of -1 indicates that the network channel obtains its backlog configuration from the server's configuration. "
      ::= { networkAccessPointEntry 25  }
   
   
   networkAccessPointListenAddress OBJECT-TYPE
      SYNTAX      DisplayString (SIZE (1..256))
      MAX-ACCESS  read-only
      STATUS      current
      DESCRIPTION "The IP address or DNS name this network channel uses to listen for incoming connections. A value of null indicates that the network channel should obtain this value from the server's configuration. "
      ::= { networkAccessPointEntry 45  }
   
   
   networkAccessPointListenPort OBJECT-TYPE
      SYNTAX      INTEGER
      MAX-ACCESS  read-only
      STATUS      current
      DESCRIPTION "The default TCP port this network channel uses to listen for regular (non-SSL) incoming connections. A value of -1 indicates that the network channel should obtain this value from the server's configuration. "
      ::= { networkAccessPointEntry 50  }
   
   
   networkAccessPointLoginTimeoutMillis OBJECT-TYPE
      SYNTAX      INTEGER
      MAX-ACCESS  read-only
      STATUS      current
      DESCRIPTION "The amount of time that this network channel should wait for a connection before timing out. A value of 0 disables network channel login timeout. A value of -1 indicates that the network channel obtains this timeout value from the server's configuration. "
      ::= { networkAccessPointEntry 60  }
   
   
   networkAccessPointTunnelingClientPingSecs OBJECT-TYPE
      SYNTAX      INTEGER
      MAX-ACCESS  read-only
      STATUS      current
      DESCRIPTION "The interval (in seconds) at which this network channel should ping an HTTP-tunneled client to see if its still alive. A value of -1 indicates that the network channel obtains this interval from the ServerTemplateMBean. (Requires you to enable tunneling for the network channel.) "
      ::= { networkAccessPointEntry 70  }
   
   
   networkAccessPointTunnelingClientTimeoutSecs OBJECT-TYPE
      SYNTAX      INTEGER
      MAX-ACCESS  read-only
      STATUS      current
      DESCRIPTION "The amount of time (in seconds) after which this network channel considers a missing HTTP-tunneled client to be dead. A value of -1 indicates that the network channel obtains this timeout value from the ServerTemplateMBean. (Requires you to enable tunneling for the network channel.) "
      ::= { networkAccessPointEntry 75  }
   
   
   networkAccessPointUseFastSerialization OBJECT-TYPE
      SYNTAX      OCTET STRING
      MAX-ACCESS  read-only
      STATUS      current
      DESCRIPTION "Specifies whether to use non-standard object serialization for performance. This option works in different ways for different protocols. In particular under IIOP this option uses Java serialization rather than RMI-IIOP serialization. In general using non-standard serialization is not suitable for interop scenarios and may imply some feature loss. "
      ::= { networkAccessPointEntry 76  }
   
   
   networkAccessPointProxyPort OBJECT-TYPE
      SYNTAX      INTEGER
      MAX-ACCESS  read-only
      STATUS      current
      DESCRIPTION "The port of the HTTP proxy to use for outbound connections on this channel. The HTTP proxy must support the CONNECT tunneling command.  This option is only effective when OutboundEnabled and ProxyHost are set on the channel. "
      ::= { networkAccessPointEntry 77  }
   
   
   networkAccessPointTwoWaySSLEnabled OBJECT-TYPE
      SYNTAX      OCTET STRING
      MAX-ACCESS  read-only
      STATUS      current
      DESCRIPTION "Specifies whether this network channel uses two way SSL. "
      ::= { networkAccessPointEntry 78  }
   
   
   networkAccessPointChannelWeight OBJECT-TYPE
      SYNTAX      INTEGER
      MAX-ACCESS  read-only
      STATUS      current
      DESCRIPTION "A weight to give this channel when creating server-to-server connections. "
      ::= { networkAccessPointEntry 79  }
   
   
   networkAccessPointHttpEnabledForThisProtocol OBJECT-TYPE
      SYNTAX      OCTET STRING
      MAX-ACCESS  read-only
      STATUS      current
      DESCRIPTION "Specifies whether HTTP traffic should be allowed over this network channel.  HTTP is generally required by binary protocols for downloading stubs and other resources. "
      ::= { networkAccessPointEntry 80  }
   
   
   networkAccessPointTimeoutConnectionWithPendingResponses OBJECT-TYPE
      SYNTAX      OCTET STRING
      MAX-ACCESS  read-only
      STATUS      current
      DESCRIPTION "Determines if connections with pending responses are allowed to timeout. It defaults to false. If set to true, the connection will be timed out for this channel if it exceeds the idleConnectionTimeout value.  Note: This setting only applies to IIOP connections. "
      ::= { networkAccessPointEntry 81  }
   
   
   networkAccessPointOutboundEnabled OBJECT-TYPE
      SYNTAX      OCTET STRING
      MAX-ACCESS  read-only
      STATUS      current
      DESCRIPTION "Specifies whether new server-to-server connections may consider this network channel when initiating a connection. This is only relevant if the connection needs to be bound to the network channel's listen address. This will only work for binary protocols that support both outbound and inbound traffic.   When this feature is not enabled, connections are initiated using a local address selected by the underlying hardware.  The default is false.  Outbound channels are selected at runtime either by virtue of the fact of being the only outbound-enabled channel for the required protocol, or by name in weblogic.jndi.Environment#setProviderChannel.  The HTTP protocol is implicitly enabled for all the outbound channels, but you need to use the WLS client library (HTTP client) and set the channel on the connection.  "
      ::= { networkAccessPointEntry 82  }
   
   
   networkAccessPointEnabled OBJECT-TYPE
      SYNTAX      OCTET STRING
      MAX-ACCESS  read-only
      STATUS      current
      DESCRIPTION "Specifies whether this channel should be started. "
      ::= { networkAccessPointEntry 83  }
   
   
   networkAccessPointCustomPrivateKeyAlias OBJECT-TYPE
      SYNTAX      OCTET STRING
      MAX-ACCESS  read-only
      STATUS      current
      DESCRIPTION "The string alias used to store and retrieve the channel's private key in the keystore. This private key is associated with the server's digital certificate. A value of null indicates that the network channel uses the alias specified in the server's SSL configuration. "
      ::= { networkAccessPointEntry 84  }
   
   
   networkAccessPointConnectTimeout OBJECT-TYPE
      SYNTAX      INTEGER
      MAX-ACCESS  read-only
      STATUS      current
      DESCRIPTION "The amount of time that this network channel should wait to establish an outbound socket connection before timing out. A value of 0 disables network channel connect timeout. "
      ::= { networkAccessPointEntry 85  }
   
   
   networkAccessPointMaxConnectedClients OBJECT-TYPE
      SYNTAX      INTEGER
      MAX-ACCESS  read-only
      STATUS      current
      DESCRIPTION "The maximum number of clients that can be connected on this network channel. "
      ::= { networkAccessPointEntry 86  }
   
   
   networkAccessPointIdleConnectionTimeout OBJECT-TYPE
      SYNTAX      INTEGER
      MAX-ACCESS  read-only
      STATUS      current
      DESCRIPTION "The maximum amount of time (in seconds) that a connection is allowed to be idle before it is closed by this network channel. A value of -1 indicates that the network channel obtains this timeout value from the ServerTemplateMBean.  This timeout helps guard against server deadlock through too many open connections. "
      ::= { networkAccessPointEntry 87  }
   
   
   networkAccessPointMaxBackoffBetweenFailures OBJECT-TYPE
      SYNTAX      INTEGER
      MAX-ACCESS  read-only
      STATUS      current
      DESCRIPTION "The maximum back off time between failures while accepting client connections. -1 implies that this value is inherited from the server. "
      ::= { networkAccessPointEntry 88  }
   
   
   networkAccessPointProtocol OBJECT-TYPE
      SYNTAX      OCTET STRING
      MAX-ACCESS  read-only
      STATUS      current
      DESCRIPTION "The protocol this network channel should use for connections. "
      ::= { networkAccessPointEntry 89  }
   
   
   networkAccessPointPrivateKeyAlias OBJECT-TYPE
      SYNTAX      OCTET STRING
      MAX-ACCESS  read-only
      STATUS      current
      DESCRIPTION "The string alias used to store and retrieve the channel's private key in the keystore. This private key is associated with the server's digital certificate. This value is derived from other settings on the channel and cannot be physically set. "
      ::= { networkAccessPointEntry 90  }
   
   
   networkAccessPointTunnelingEnabled OBJECT-TYPE
      SYNTAX      OCTET STRING
      MAX-ACCESS  read-only
      STATUS      current
      DESCRIPTION "Specifies whether tunneling via HTTP should be enabled for this network channel. This value is not inherited from the server's configuration. "
      ::= { networkAccessPointEntry 91  }
   
   
   networkAccessPointClusterAddress OBJECT-TYPE
      SYNTAX      OCTET STRING
      MAX-ACCESS  read-only
      STATUS      current
      DESCRIPTION "The address this network channel uses to generate EJB handles and failover addresses for use in a cluster. This value is determined according to the following order of precedence:  If the cluster address is specified via the NAPMBean, then that value is used If this value is not specified, the value of PublicAddress is used. If PublicAddress is not set, this value is derive from the ClusterAddress attribute of the ClusterMbean. If ClusterMbean.clusterAddress is not set, this value is derive from the listen address of the NAPMbean.  "
      ::= { networkAccessPointEntry 92  }
   
   
   networkAccessPointChannelIdentityCustomized OBJECT-TYPE
      SYNTAX      OCTET STRING
      MAX-ACCESS  read-only
      STATUS      current
      DESCRIPTION "Whether or not the channel's custom identity should be used. This setting only has an effect if the server is using a customized keystore. By default the channel's identity is inherited from the server's identity. "
      ::= { networkAccessPointEntry 93  }
   
   
   networkAccessPointMaxMessageSize OBJECT-TYPE
      SYNTAX      INTEGER
      MAX-ACCESS  read-only
      STATUS      current
      DESCRIPTION "The maximum message size allowable in a message header.  This maximum attempts to prevent a denial of service attack whereby a caller attempts to force the server to allocate more memory than is available thereby keeping the server from responding quickly to other requests. A client can set this value using the -Dweblogic.MaxMessageSize property. "
      ::= { networkAccessPointEntry 94  }
   
   
   networkAccessPointPublicPort OBJECT-TYPE
      SYNTAX      INTEGER
      MAX-ACCESS  read-only
      STATUS      current
      DESCRIPTION "The externally published listen port for this network channel. A value of -1 indicates that the network channel's Listen Port is also its public listen port. If the Listen Port is -1,the network channel obtains its public listen port from the server's configuration. "
      ::= { networkAccessPointEntry 95  }
   
   
   networkAccessPointOutboundPrivateKeyEnabled OBJECT-TYPE
      SYNTAX      OCTET STRING
      MAX-ACCESS  read-only
      STATUS      current
      DESCRIPTION "Specifies whether the identity specified by {@link #getCustomPrivateKeyAlias} should be used for outbound SSL connections on this channel. In normal circumstances the outbound identity is determined by the caller's environment. "
      ::= { networkAccessPointEntry 96  }
   
   
   networkAccessPointCompleteMessageTimeout OBJECT-TYPE
      SYNTAX      INTEGER
      MAX-ACCESS  read-only
      STATUS      current
      DESCRIPTION "The maximum amount of time this network channel waits for a complete message to be received. A value of 0 disables network channel complete message timeout. A value of -1 indicates that the network channel obtains this timeout value from the ServerTemplateMBean.  This timeout helps guard against denial of service attacks in which a caller indicates that they will be sending a message of a certain size which they never finish sending. "
      ::= { networkAccessPointEntry 97  }
   
   
   networkAccessPointPublicAddress OBJECT-TYPE
      SYNTAX      OCTET STRING
      MAX-ACCESS  read-only
      STATUS      current
      DESCRIPTION "The IP address or DNS name representing the external identity of this network channel. A value of null indicates that the network channel's Listen Address is also its external address. If the Listen Address is null,the network channel obtains its external identity from the server's configuration.  This is required for the configurations which need to cross a firewall doing Network Address Translation. "
      ::= { networkAccessPointEntry 98  }
   
   
   networkAccessPointClientCertificateEnforced OBJECT-TYPE
      SYNTAX      OCTET STRING
      MAX-ACCESS  read-only
      STATUS      current
      DESCRIPTION "Specifies whether clients must present digital certificates from a trusted certificate authority to WebLogic Server on this channel. "
      ::= { networkAccessPointEntry 99  }
   
   
   networkAccessPointPrivateKeyPassPhrase OBJECT-TYPE
      SYNTAX      OCTET STRING
      MAX-ACCESS  read-only
      STATUS      current
      DESCRIPTION "The passphrase used to retrieve the server's private key from the keystore. This passphrase is assigned to the private key when it is generated. This value is derived from other settings on the channel and cannot be physically set. "
      ::= { networkAccessPointEntry 100  }
   
   
   networkAccessPointProxyAddress OBJECT-TYPE
      SYNTAX      OCTET STRING
      MAX-ACCESS  read-only
      STATUS      current
      DESCRIPTION "The IP address or DNS name of the HTTP proxy to use for outbound connections on this channel. The HTTP proxy must support the CONNECT tunneling command.  This option is only effective when OutboundEnabled is set on the channel. "
      ::= { networkAccessPointEntry 101  }
   
   
   networkAccessPointSDPEnabled OBJECT-TYPE
      SYNTAX      OCTET STRING
      MAX-ACCESS  read-only
      STATUS      current
      DESCRIPTION "Enables Socket Direct Protocol (SDP) on this channel. Enable this attribute when configuring session replication enhancements for Managed Servers in a WebLogic cluster for Oracle Exalogic. "
      ::= { networkAccessPointEntry 102  }
   
   
   networkAccessPointOutboundPrivateKeyPassPhrase OBJECT-TYPE
      SYNTAX      OCTET STRING
      MAX-ACCESS  read-only
      STATUS      current
      DESCRIPTION "The passphrase used to retrieve the outbound private key from the keystore. This passphrase is assigned to the private key when it is generated. This attribute value is derived from other settings and cannot be physically set.  The returned value is determined as follows:  If {@link #isOutboundPrivateKeyEnabled} and {@link #isChannelIdentityCustomized} return true, the value from {@link #getCustomPrivateKeyPassPhrase} is returned.  Otherwise, the value from {@link SSLMBean#getOutboundPrivateKeyPassPhrase} is returned from the {@link ServerMBean} for the channel.  "
      ::= { networkAccessPointEntry 103  }
   
   
   networkAccessPointOutboundPrivateKeyAlias OBJECT-TYPE
      SYNTAX      OCTET STRING
      MAX-ACCESS  read-only
      STATUS      current
      DESCRIPTION "The string alias used to store and retrieve the outbound private key in the keystore. This private key is associated with either a server or a client digital certificate. This attribute value is derived from other settings and cannot be physically set.  The returned value is determined as follows:  If {@link #isOutboundPrivateKeyEnabled} and {@link #isChannelIdentityCustomized} return true, the value from {@link #getCustomPrivateKeyAlias} is returned.  Otherwise, the value from {@link SSLMBean#getOutboundPrivateKeyAlias} is returned from the {@link ServerMBean} for the channel.  "
      ::= { networkAccessPointEntry 104  }
   
   
   networkAccessPointResolveDNSName OBJECT-TYPE
      SYNTAX      OCTET STRING
      MAX-ACCESS  read-only
      STATUS      current
      DESCRIPTION "Resolve the listen address to use for all T3 communication "
      ::= { networkAccessPointEntry 105  }
   
   
   networkAccessPointOutboundCertificateValidation OBJECT-TYPE
      SYNTAX      OCTET STRING
      MAX-ACCESS  read-only
      STATUS      current
      DESCRIPTION "Indicates the server certificate validation rules for outbound SSL.  This attribute always applies to outbound SSL that is part of WebLogic Server (that is, an Administration Server talking to the Node Manager). It does not apply to application code in the server that is using outbound SSL unless the application code uses a weblogic.security.SSL.ServerTrustManager that is configured to use outbound SSL validation. "
      ::= { networkAccessPointEntry 106  }
   
   
   networkAccessPointAllowUnencryptedNullCipher OBJECT-TYPE
      SYNTAX      OCTET STRING
      MAX-ACCESS  read-only
      STATUS      current
      DESCRIPTION "Test if the AllowUnEncryptedNullCipher is enabled see setAllowUnencryptedNullCipher(boolean enable) for the NullCipher feature. "
      ::= { networkAccessPointEntry 107  }
   
   
   networkAccessPointCustomIdentityKeyStoreFileName OBJECT-TYPE
      SYNTAX      OCTET STRING
      MAX-ACCESS  read-only
      STATUS      current
      DESCRIPTION "The source of the identity keystore. For a JKS keystore, the source is the path and file name. For an Oracle Key Store Service (KSS) keystore, the source is the KSS URI.  If using a JKS keystore, the keystore path name must either be absolute or relative to where the server was booted.  If using a KSS keystore, the keystore URI must be of the form:  kss://system/keystorename  where keystorename is the name of the keystore registered in KSS.  The value in this attribute is only used if ServerMBean.KeyStores is CUSTOM_IDENTITY_AND_JAVA_STANDARD_TRUST, CUSTOM_IDENTITY_AND_CUSTOM_TRUST or CUSTOM_IDENTITY_AND_COMMAND_LINE_TRUST. "
      ::= { networkAccessPointEntry 108  }
   
   
   networkAccessPointInboundCertificateValidation OBJECT-TYPE
      SYNTAX      OCTET STRING
      MAX-ACCESS  read-only
      STATUS      current
      DESCRIPTION "Indicates the client certificate validation rules for inbound SSL.  This attribute only applies to ports and network channels using 2-way SSL. "
      ::= { networkAccessPointEntry 109  }
   
   
   networkAccessPointHostnameVerificationIgnored OBJECT-TYPE
      SYNTAX      OCTET STRING
      MAX-ACCESS  read-only
      STATUS      current
      DESCRIPTION "Specifies whether to ignore the installed implementation of the weblogic.security.SSL.HostnameVerifier interface (when this server is acting as a client to another application server). "
      ::= { networkAccessPointEntry 110  }
   
   
   networkAccessPointCustomIdentityKeyStoreType OBJECT-TYPE
      SYNTAX      OCTET STRING
      MAX-ACCESS  read-only
      STATUS      current
      DESCRIPTION "The type of the keystore. Generally, this is JKS. If using the Oracle Key Store Service, this would be KSS  If empty or null, then the JDK's default keystore type (specified in java.security) is used. The custom identity key store type is only used if ServerMBean.KeyStores is CUSTOM_IDENTITY_AND_JAVA_STANDARD_TRUST, CUSTOM_IDENTITY_AND_CUSTOM_TRUST or CUSTOM_IDENTITY_AND_COMMAND_LINE_TRUST. "
      ::= { networkAccessPointEntry 111  }
   
   
   networkAccessPointCiphersuites OBJECT-TYPE
      SYNTAX      OCTET STRING
      MAX-ACCESS  read-only
      STATUS      current
      DESCRIPTION "Indicates the cipher suites being used on a particular WebLogic Server channel.  The strongest negotiated cipher suite is chosen during the SSL handshake. The set of cipher suites used by default by JSEE depends on the specific JDK version with which WebLogic Server is configured.  For a list of possible values, see Cipher Suites. "
      ::= { networkAccessPointEntry 112  }
   
   
   networkAccessPointHostnameVerifier OBJECT-TYPE
      SYNTAX      OCTET STRING
      MAX-ACCESS  read-only
      STATUS      current
      DESCRIPTION "The name of the class that implements the weblogic.security.SSL.HostnameVerifier interface.  This class verifies whether the connection to the host with the hostname from URL should be allowed. The class is used to prevent man-in-the-middle attacks. The weblogic.security.SSL.HostnameVerifier has a verify() method that WebLogic Server calls on the client during the SSL handshake. "
      ::= { networkAccessPointEntry 113  }
   
   
   networkAccessPointTags OBJECT-TYPE
      SYNTAX      OCTET STRING
      MAX-ACCESS  read-only
      STATUS      current
      DESCRIPTION "Return all tags on this Configuration MBean "
      ::= { networkAccessPointEntry 114  }
   
   
   networkAccessPointMinimumTLSProtocolVersion OBJECT-TYPE
      SYNTAX      OCTET STRING
      MAX-ACCESS  read-only
      STATUS      current
      DESCRIPTION "Get the minimum SSL/TLS protocol version to be used in a network channel. "
      ::= { networkAccessPointEntry 115  }
   
   
   networkAccessPointSSLv2HelloEnabled OBJECT-TYPE
      SYNTAX      OCTET STRING
      MAX-ACCESS  read-only
      STATUS      current
      DESCRIPTION "Indicate whether SSLv2Hello is enabled in a network channel. "
      ::= { networkAccessPointEntry 116  }
   
   
   networkAccessPointClientInitSecureRenegotiationAccepted OBJECT-TYPE
      SYNTAX      OCTET STRING
      MAX-ACCESS  read-only
      STATUS      current
      DESCRIPTION "Indicate whether TLS client initiated secure renegotiation is accepted. "
      ::= { networkAccessPointEntry 117  }
   
   
   nodeManagerTable OBJECT-TYPE
      SYNTAX      SEQUENCE OF NodeManagerEntry
      MAX-ACCESS  not-accessible
      STATUS      current
      DESCRIPTION "This bean is represents a Node Manager that is associated with a machine. "
      ::= { wls 707  }
      
   
   nodeManagerEntry OBJECT-TYPE
      SYNTAX      NodeManagerEntry
      MAX-ACCESS  not-accessible
      STATUS      current
      DESCRIPTION "Entry of nodeManagerTable"
      INDEX { nodeManagerIndex}
      ::= { nodeManagerTable 1 }
      
   NodeManagerEntry ::=
      SEQUENCE
      {
         nodeManagerIndex     DisplayString,
         nodeManagerObjectName DisplayString,
         nodeManagerType      DisplayString,
         nodeManagerName      DisplayString,
         nodeManagerParent    DisplayString,
         nodeManagerListenAddress DisplayString,
         nodeManagerListenPort INTEGER,
         nodeManagerShellCommand OCTET STRING,
         nodeManagerNodeManagerHome OCTET STRING,
         nodeManagerDebugEnabled OCTET STRING,
         nodeManagerNMType    OCTET STRING,
         nodeManagerUserName  OCTET STRING,
         nodeManagerInstalledVMMAdapters OCTET STRING,
         nodeManagerAdapterVersion OCTET STRING,
         nodeManagerAdapterName OCTET STRING,
         nodeManagerAdapter   OCTET STRING,
         nodeManagerTags      OCTET STRING,
         nodeManagerNMSocketCreateTimeoutInMillis INTEGER
      }
      
   
   nodeManagerIndex OBJECT-TYPE
      SYNTAX      DisplayString (SIZE (1..16))
      MAX-ACCESS  read-only
      STATUS      current
      DESCRIPTION "Unique value directed from ObjectName which is used as table index"
      ::= { nodeManagerEntry 1  }
   
   
   nodeManagerObjectName OBJECT-TYPE
      SYNTAX      DisplayString (SIZE (1..256))
      MAX-ACCESS  read-only
      STATUS      current
      DESCRIPTION "JMX-standard MBean name"
      ::= { nodeManagerEntry 5  }
   
   
   nodeManagerType OBJECT-TYPE
      SYNTAX      DisplayString (SIZE (1..64))
      MAX-ACCESS  read-only
      STATUS      current
      DESCRIPTION "Returns the type of the MBean. "
      ::= { nodeManagerEntry 10  }
   
   
   nodeManagerName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { nodeManagerEntry 15  }
   
   
   nodeManagerParent OBJECT-TYPE
      SYNTAX      DisplayString (SIZE (1..256))
      MAX-ACCESS  read-only
      STATUS      current
      DESCRIPTION "BEA-proprietary Parent object's identification, with syntax
      <type>:<name>"
      ::= { nodeManagerEntry 20  }
   
   
   nodeManagerListenAddress OBJECT-TYPE
      SYNTAX      DisplayString (SIZE (1..256))
      MAX-ACCESS  read-only
      STATUS      current
      DESCRIPTION "The host name or IP address of the NodeManager for the server or clients on the server to use when connecting to the NodeManager instance.  "
      ::= { nodeManagerEntry 35  }
   
   
   nodeManagerListenPort OBJECT-TYPE
      SYNTAX      INTEGER
      MAX-ACCESS  read-only
      STATUS      current
      DESCRIPTION "The port number of the NodeManager for the server or clients on the server to use when connecting to the NodeManager instance.  "
      ::= { nodeManagerEntry 40  }
   
   
   nodeManagerShellCommand OBJECT-TYPE
      SYNTAX      OCTET STRING
      MAX-ACCESS  read-only
      STATUS      current
      DESCRIPTION "Returns the local command line to use when invoking SSH or RSH node manager functions. "
      ::= { nodeManagerEntry 41  }
   
   
   nodeManagerNodeManagerHome OBJECT-TYPE
      SYNTAX      OCTET STRING
      MAX-ACCESS  read-only
      STATUS      current
      DESCRIPTION "Returns the node manager home directory that will be used to substitute for the shell command template "
      ::= { nodeManagerEntry 42  }
   
   
   nodeManagerDebugEnabled OBJECT-TYPE
      SYNTAX      OCTET STRING
      MAX-ACCESS  read-only
      STATUS      current
      DESCRIPTION "Specifies whether communication with this Node Manager needs to be debugged. When enabled, connections to the NodeManager from the server or clients on the server will result in more information sent to the server log. "
      ::= { nodeManagerEntry 43  }
   
   
   nodeManagerNMType OBJECT-TYPE
      SYNTAX      OCTET STRING
      MAX-ACCESS  read-only
      STATUS      current
      DESCRIPTION "Returns the node manager type for the server or clients on the server to use when connecting to the NodeManager instance. "
      ::= { nodeManagerEntry 44  }
   
   
   nodeManagerUserName OBJECT-TYPE
      SYNTAX      OCTET STRING
      MAX-ACCESS  read-only
      STATUS      current
      DESCRIPTION "The Node Manager client user name used to connect to the underlying service to which the client delegates operations.  "
      ::= { nodeManagerEntry 45  }
   
   
   nodeManagerInstalledVMMAdapters OBJECT-TYPE
      SYNTAX      OCTET STRING
      MAX-ACCESS  read-only
      STATUS      current
      DESCRIPTION "Gets a list of the names and versions of the installed Virtual Machine Manager (VMM) adapters "
      ::= { nodeManagerEntry 46  }
   
   
   nodeManagerAdapterVersion OBJECT-TYPE
      SYNTAX      OCTET STRING
      MAX-ACCESS  read-only
      STATUS      current
      DESCRIPTION "Gets the node manager client adapter version when using a VMM adapter to connect to OVM or other VMM adapters providers "
      ::= { nodeManagerEntry 47  }
   
   
   nodeManagerAdapterName OBJECT-TYPE
      SYNTAX      OCTET STRING
      MAX-ACCESS  read-only
      STATUS      current
      DESCRIPTION "Gets the node manager client adapter name when using a VMM adapter to connect to OVM or other VMM adapters providers "
      ::= { nodeManagerEntry 48  }
   
   
   nodeManagerAdapter OBJECT-TYPE
      SYNTAX      OCTET STRING
      MAX-ACCESS  read-only
      STATUS      current
      DESCRIPTION "Gets the node manager client adapter name_version when using a VMM adapter to connect to OVM or other VMM adapter providers "
      ::= { nodeManagerEntry 49  }
   
   
   nodeManagerTags OBJECT-TYPE
      SYNTAX      OCTET STRING
      MAX-ACCESS  read-only
      STATUS      current
      DESCRIPTION "Return all tags on this Configuration MBean "
      ::= { nodeManagerEntry 50  }
   
   
   nodeManagerNMSocketCreateTimeoutInMillis OBJECT-TYPE
      SYNTAX      INTEGER
      MAX-ACCESS  read-only
      STATUS      current
      DESCRIPTION "Returns the timeout value to be used by NodeManagerRuntime when creating a a socket connection to the agent. Default set high as SSH agent may require a high connection establishment time. "
      ::= { nodeManagerEntry 51  }
   
   
   rmcFactoryTable OBJECT-TYPE
      SYNTAX      SEQUENCE OF RmcFactoryEntry
      MAX-ACCESS  not-accessible
      STATUS      current
      DESCRIPTION "Represents a Java EE resource manager connection factory in a Java EE app. MBeans for resource manager connection factories extend this interface. For example, a MailSessionMBean. "
      ::= { wls 708  }
      
   
   rmcFactoryEntry OBJECT-TYPE
      SYNTAX      RmcFactoryEntry
      MAX-ACCESS  not-accessible
      STATUS      current
      DESCRIPTION "Entry of rmcFactoryTable"
      INDEX { rmcFactoryIndex}
      ::= { rmcFactoryTable 1 }
      
   RmcFactoryEntry ::=
      SEQUENCE
      {
         rmcFactoryIndex      DisplayString,
         rmcFactoryObjectName DisplayString,
         rmcFactoryType       DisplayString,
         rmcFactoryName       DisplayString,
         rmcFactoryParent     DisplayString,
         rmcFactoryJNDIName   DisplayString,
         rmcFactoryDeploymentOrder INTEGER,
         rmcFactoryTags       OCTET STRING
      }
      
   
   rmcFactoryIndex OBJECT-TYPE
      SYNTAX      DisplayString (SIZE (1..16))
      MAX-ACCESS  read-only
      STATUS      current
      DESCRIPTION "Unique value directed from ObjectName which is used as table index"
      ::= { rmcFactoryEntry 1  }
   
   
   rmcFactoryObjectName OBJECT-TYPE
      SYNTAX      DisplayString (SIZE (1..256))
      MAX-ACCESS  read-only
      STATUS      current
      DESCRIPTION "JMX-standard MBean name"
      ::= { rmcFactoryEntry 5  }
   
   
   rmcFactoryType OBJECT-TYPE
      SYNTAX      DisplayString (SIZE (1..64))
      MAX-ACCESS  read-only
      STATUS      current
      DESCRIPTION "Returns the type of the MBean. "
      ::= { rmcFactoryEntry 10  }
   
   
   rmcFactoryName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { rmcFactoryEntry 15  }
   
   
   rmcFactoryParent OBJECT-TYPE
      SYNTAX      DisplayString (SIZE (1..256))
      MAX-ACCESS  read-only
      STATUS      current
      DESCRIPTION "BEA-proprietary Parent object's identification, with syntax
      <type>:<name>"
      ::= { rmcFactoryEntry 20  }
   
   
   rmcFactoryJNDIName OBJECT-TYPE
      SYNTAX      DisplayString
      MAX-ACCESS  read-only
      STATUS      current
      DESCRIPTION "The JNDI Name associated with this resource. "
      ::= { rmcFactoryEntry 21  }
   
   
   rmcFactoryDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { rmcFactoryEntry 22  }
   
   
   rmcFactoryTags OBJECT-TYPE
      SYNTAX      OCTET STRING
      MAX-ACCESS  read-only
      STATUS      current
      DESCRIPTION "Return all tags on this Configuration MBean "
      ::= { rmcFactoryEntry 23  }
   
   
   securityTable OBJECT-TYPE
      SYNTAX      SEQUENCE OF SecurityEntry
      MAX-ACCESS  not-accessible
      STATUS      current
      DESCRIPTION "This table represents a security in the domain."
      ::= { wls 710  }
      
   
   securityEntry OBJECT-TYPE
      SYNTAX      SecurityEntry
      MAX-ACCESS  not-accessible
      STATUS      current
      DESCRIPTION "Entry of securityTable"
      INDEX { securityIndex}
      ::= { securityTable 1 }
      
   SecurityEntry ::=
      SEQUENCE
      {
         securityIndex        DisplayString,
         securityObjectName   DisplayString,
         securityType         DisplayString,
         securityName         DisplayString,
         securityParent       DisplayString,
         securityConnectionFilter DisplayString,
         securityConnectionFilterRules DisplayString,
         securityConnectionLoggerEnabled DisplayString
      }
      
   
   securityIndex OBJECT-TYPE
      SYNTAX      DisplayString (SIZE (1..16))
      MAX-ACCESS  read-only
      STATUS      current
      DESCRIPTION "Unique value directed from ObjectName which is used as table index"
      ::= { securityEntry 1  }
   
   
   securityObjectName OBJECT-TYPE
      SYNTAX      DisplayString (SIZE (1..256))
      MAX-ACCESS  read-only
      STATUS      current
      DESCRIPTION "JMX-standard MBean name"
      ::= { securityEntry 5  }
   
   
   securityType OBJECT-TYPE
      SYNTAX      DisplayString (SIZE (1..64))
      MAX-ACCESS  read-only
      STATUS      current
      DESCRIPTION "BEA-proprietary MBean type"
      ::= { securityEntry 10  }
   
   
   securityName OBJECT-TYPE
      SYNTAX      DisplayString (SIZE (1..64))
      MAX-ACCESS  read-only
      STATUS      current
      DESCRIPTION "BEA-proprietary MBean name"
      ::= { securityEntry 15  }
   
   
   securityParent OBJECT-TYPE
      SYNTAX      DisplayString (SIZE (1..256))
      MAX-ACCESS  read-only
      STATUS      current
      DESCRIPTION "BEA-proprietary Parent object's identification, with syntax
      <type>:<name>"
      ::= { securityEntry 20  }
   
   
   securityConnectionFilter OBJECT-TYPE
      SYNTAX      DisplayString (SIZE (1..256))
      MAX-ACCESS  read-only
      STATUS      current
      DESCRIPTION "The name of the Java class that implements a connection filter.
      * The connection filter must be an implementation of the 
      * <tt>weblogic.security.net.ConnectionFilter</tt> interface."
      ::= { securityEntry 30  }
   
   
   securityConnectionFilterRules OBJECT-TYPE
      SYNTAX      DisplayString (SIZE (1..256))
      MAX-ACCESS  read-only
      STATUS      current
      DESCRIPTION "The list of rules for the system connection filter.
      * If none are specified, all connections are accepted."
      ::= { securityEntry 35  }
   
   
   securityConnectionLoggerEnabled OBJECT-TYPE
      SYNTAX      DisplayString (SIZE (1..256))
      MAX-ACCESS  read-only
      STATUS      current
      DESCRIPTION "Enables the logging of accepted connections.  This attribute can be used by
      * a system administrator to dynamically check the incoming connections in the
      * log file to determine if filtering needs to be performed."
      ::= { securityEntry 40  }
   
   
   serverTable OBJECT-TYPE
      SYNTAX      SEQUENCE OF ServerEntry
      MAX-ACCESS  not-accessible
      STATUS      current
      DESCRIPTION "This class represents a individual WebLogic Server. A WebLogic Server is a Java process that is a container for Java EE applications. "
      ::= { wls 730  }
      
   
   serverEntry OBJECT-TYPE
      SYNTAX      ServerEntry
      MAX-ACCESS  not-accessible
      STATUS      current
      DESCRIPTION "Entry of serverTable"
      INDEX { serverIndex}
      ::= { serverTable 1 }
      
   ServerEntry ::=
      SEQUENCE
      {
         serverIndex          DisplayString,
         serverObjectName     DisplayString,
         serverType           DisplayString,
         serverName           DisplayString,
         serverParent         DisplayString,
         serverReverseDNSAllowed INTEGER,
         serverDefaultProtocol DisplayString,
         serverDefaultSecureProtocol DisplayString,
         serverNativeIOEnabled INTEGER,
         serverThreadPoolPercentSocketReaders INTEGER,
         serverMaxT3MessageSize INTEGER,
         serverMaxHTTPMessageSize INTEGER,
         serverMaxIIOPMessageSize INTEGER,
         serverCompleteT3MessageTimeout INTEGER,
         serverCompleteHTTPMessageTimeout INTEGER,
         serverCompleteIIOPMessageTimeout INTEGER,
         serverLogRemoteExceptionsEnabled INTEGER,
         serverInstrumentStackTraceEnabled INTEGER,
         serverListenPort     INTEGER,
         serverClusterWeight  INTEGER,
         serverReplicationGroup DisplayString,
         serverPreferredSecondaryGroup DisplayString,
         serverJDBCLoggingEnabled INTEGER,
         serverIIOPEnabled    INTEGER,
         serverDefaultIIOPUser DisplayString,
         serverHttpdEnabled   INTEGER,
         serverListenThreadStartDelaySecs INTEGER,
         serverListenAddress  DisplayString,
         serverLoginTimeoutMillis INTEGER,
         serverAdministrationPort INTEGER,
         serverJavaCompiler   DisplayString,
         serverJavaCompilerPreClassPath DisplayString,
         serverJavaCompilerPostClassPath DisplayString,
         serverExtraRmicOptions DisplayString,
         serverTransactionLogFilePrefix DisplayString,
         serverTunnelingEnabled INTEGER,
         serverTunnelingClientTimeoutSecs INTEGER,
         serverTunnelingClientPingSecs INTEGER,
         serverJMSDefaultConnectionFactoriesEnabled INTEGER,
         serverAcceptBacklog  INTEGER,
         serverListenPortEnabled OCTET STRING,
         serverUse81StyleExecuteQueues OCTET STRING,
         serverStagingMode    OCTET STRING,
         serverLowMemoryGCThreshold INTEGER,
         serverStagingDirectoryName OCTET STRING,
         serverGracefulShutdownTimeout INTEGER,
         serverManagedServerIndependenceEnabled OCTET STRING,
         serverStartupTimeout INTEGER,
         serverSocketBufferSizeAsChunkSize OCTET STRING,
         serverRestartMax     INTEGER,
         serverCompleteMessageTimeout INTEGER,
         serverServerLifeCycleTimeoutVal INTEGER,
         serverVerboseEJBDeploymentEnabled OCTET STRING,
         serverAdminReconnectIntervalSeconds INTEGER,
         serverClientCertProxyEnabled OCTET STRING,
         serverRestartDelaySeconds INTEGER,
         serverLowMemoryGranularityLevel INTEGER,
         serverSocketReaders  INTEGER,
         serverOutboundEnabled OCTET STRING,
         serverJDBCLLRTableName OCTET STRING,
         serverInterfaceAddress OCTET STRING,
         serverExtraEjbcOptions OCTET STRING,
         serverCOMEnabled     OCTET STRING,
         serverMessageIdPrefixEnabled OCTET STRING,
         serverAutoRestart    OCTET STRING,
         serverIgnoreSessionsDuringShutdown OCTET STRING,
         serverDefaultTGIOPUser OCTET STRING,
         serverMaxOpenSockCount INTEGER,
         serverLowMemorySampleSize INTEGER,
         serverAutoKillIfFailed OCTET STRING,
         serverCustomIdentityKeyStoreFileName OCTET STRING,
         serverTGIOPEnabled   OCTET STRING,
         serverHealthCheckStartDelaySeconds INTEGER,
         serverUploadDirectoryName OCTET STRING,
         serverWeblogicPluginEnabled OCTET STRING,
         serverJDBCLoginTimeoutSeconds INTEGER,
         serverClasspathServletDisabled OCTET STRING,
         serverIdleConnectionTimeout INTEGER,
         serverDefaultInternalServletsDisabled OCTET STRING,
         serverMaxMessageSize INTEGER,
         serverCustomTrustKeyStoreType OCTET STRING,
         serverListenersBindEarly OCTET STRING,
         serverLowMemoryTimeInterval INTEGER,
         serverTransactionLogFileWritePolicy OCTET STRING,
         serverHttpTraceSupportEnabled OCTET STRING,
         serverKeyStores      OCTET STRING,
         serverAutoMigrationEnabled OCTET STRING,
         serverPeriodLength   INTEGER,
         serverStuckThreadTimerInterval INTEGER,
         serverDGCIdlePeriodsUntilTimeout INTEGER,
         serverMuxerClass     OCTET STRING,
         serverHealthCheckIntervalSeconds INTEGER,
         serverRestartIntervalSeconds INTEGER,
         serverIdlePeriodsUntilTimeout INTEGER,
         serverCustomTrustKeyStoreFileName OCTET STRING,
         serverHostsMigratableServices OCTET STRING,
         serverExternalDNSName OCTET STRING,
         serverOutboundPrivateKeyEnabled OCTET STRING,
         serverAdministrationProtocol OCTET STRING,
         serverCustomIdentityKeyStoreType OCTET STRING,
         serverStartupMode    OCTET STRING,
         serverNMSocketCreateTimeoutInMillis INTEGER,
         serverListenDelaySecs INTEGER,
         serverIdleIIOPConnectionTimeout INTEGER,
         serverMaxCOMMessageSize INTEGER,
         serverMessagingBridgeThreadPoolSize INTEGER,
         serverServerVersion  OCTET STRING,
         serverIIOPTxMechanism OCTET STRING,
         serverMSIFileReplicationEnabled OCTET STRING,
         serverJNDITransportableObjectFactoryList OCTET STRING,
         serverHealthCheckTimeoutSeconds INTEGER,
         serverStuckThreadMaxTime INTEGER,
         serverCompleteCOMMessageTimeout INTEGER,
         serverConnectTimeout INTEGER,
         serverGatheredWritesEnabled OCTET STRING,
         serverScatteredReadsEnabled OCTET STRING,
         serverVirtualMachineName OCTET STRING,
         serverUseFusionForLLR OCTET STRING,
         serverAddWorkManagerThreadsByCpuCount OCTET STRING,
         serverUseDetailedThreadName OCTET STRING,
         serverCompleteWriteTimeout INTEGER,
         serverUseConcurrentQueueForRequestManager OCTET STRING,
         serverUseEnhancedPriorityQueueForRequestManager OCTET STRING,
         serverReplicationPorts OCTET STRING,
         serverPrintStackTraceInProduction OCTET STRING,
         serverResolveDNSName OCTET STRING,
         serverAllowShrinkingPriorityRequestQueue OCTET STRING,
         serverUseEnhancedIncrementAdvisor OCTET STRING,
         serverTags           OCTET STRING,
         serverBuzzPort       INTEGER,
         serverMaxConcurrentNewThreads INTEGER,
         serverEagerThreadLocalCleanup OCTET STRING,
         serverRetryIntervalBeforeMSIMode INTEGER,
         serverBuzzAddress    OCTET STRING,
         serverJMSConnectionFactoryUnmappedResRefMode OCTET STRING,
         serverBuzzEnabled    OCTET STRING,
         serverMaxConcurrentLongRunningRequests INTEGER,
         serverNumOfRetriesBeforeMSIMode INTEGER,
         serverIsolatePartitionThreadLocals OCTET STRING,
         serverClasspathServletSecureModeEnabled OCTET STRING,
         serverSitConfigPollingInterval INTEGER,
         serverTransactionPrimaryChannelName OCTET STRING,
         serverTransactionSecureChannelName OCTET STRING,
         serverTransactionPublicSecureChannelName OCTET STRING,
         serverTransactionPublicChannelName OCTET STRING,
         serverCleanupOrphanedSessionsEnabled OCTET STRING,
         serverSessionReplicationOnShutdownEnabled OCTET STRING,
         serverSitConfigRequired OCTET STRING
      }
      
   
   serverIndex OBJECT-TYPE
      SYNTAX      DisplayString (SIZE (1..16))
      MAX-ACCESS  read-only
      STATUS      current
      DESCRIPTION "Unique value directed from ObjectName which is used as table index"
      ::= { serverEntry 1  }
   
   
   serverObjectName OBJECT-TYPE
      SYNTAX      DisplayString (SIZE (1..256))
      MAX-ACCESS  read-only
      STATUS      current
      DESCRIPTION "JMX-standard MBean name"
      ::= { serverEntry 5  }
   
   
   serverType OBJECT-TYPE
      SYNTAX      DisplayString (SIZE (1..64))
      MAX-ACCESS  read-only
      STATUS      current
      DESCRIPTION "Returns the type of the MBean. "
      ::= { serverEntry 10  }
   
   
   serverName OBJECT-TYPE
      SYNTAX      DisplayString (SIZE (1..64))
      MAX-ACCESS  read-only
      STATUS      current
      DESCRIPTION "An alphanumeric name for this server instance. (Spaces are not valid.)  The name must be unique for all configuration objects in the domain. Within a domain, each server, machine, cluster, JDBC connection pool, virtual host, and any other resource type must be named uniquely and must not use the same name as the domain.  For more information on server naming conventions, see Domain and Server Name Restrictions in Understanding Domain Configuration for Oracle WebLogic Server.  The server name is not used as part of the URL for applications that are deployed on the server. It is for your identification purposes only. The server name displays in the Administration Console, and if you use WebLogic Server command-line utilities or APIs, you use this name to identify the server.  After you have created a server, you cannot change its name. Instead, clone the server and provide a new name for the clone. "
      ::= { serverEntry 15  }
   
   
   serverParent OBJECT-TYPE
      SYNTAX      DisplayString (SIZE (1..256))
      MAX-ACCESS  read-only
      STATUS      current
      DESCRIPTION "BEA-proprietary Parent object's identification, with syntax
      <type>:<name>"
      ::= { serverEntry 20  }
   
   
   serverReverseDNSAllowed OBJECT-TYPE
      SYNTAX      INTEGER
                  {
                     true(1),
                     false(2)
                  }
      
      MAX-ACCESS  read-only
      STATUS      current
      DESCRIPTION "Specifies whether the kernel is allowed to perform reverse DNS lookups. "
      ::= { serverEntry 30  }
   
   
   serverDefaultProtocol OBJECT-TYPE
      SYNTAX      DisplayString (SIZE (1..32))
      MAX-ACCESS  read-only
      STATUS      current
      DESCRIPTION "The protocol to use for connections when none is specified. "
      ::= { serverEntry 35  }
   
   
   serverDefaultSecureProtocol OBJECT-TYPE
      SYNTAX      DisplayString (SIZE (1..32))
      MAX-ACCESS  read-only
      STATUS      current
      DESCRIPTION "The protocol to use for secure connections when none is specified. "
      ::= { serverEntry 40  }
   
   
   serverNativeIOEnabled OBJECT-TYPE
      SYNTAX      INTEGER
                  {
                     true(1),
                     false(2)
                  }
      
      MAX-ACCESS  read-only
      STATUS      current
      DESCRIPTION "Specifies whether native I/O is enabled for the server. "
      ::= { serverEntry 50  }
   
   
   serverThreadPoolPercentSocketReaders OBJECT-TYPE
      SYNTAX      INTEGER
      MAX-ACCESS  read-only
      STATUS      current
      DESCRIPTION "The percentage of execute threads from the default queue that can be used as socket readers. "
      ::= { serverEntry 55  }
   
   
   serverMaxT3MessageSize OBJECT-TYPE
      SYNTAX      INTEGER
      MAX-ACCESS  read-only
      STATUS      current
      DESCRIPTION "The maximum number of bytes allowed in messages that are received over the T3 protocol. If you configure custom network channels for this server, each channel can override this maximum message size.  This maximum message size helps guard against a denial of service attack in which a caller attempts to force the server to allocate more memory than is available thereby keeping the server from responding quickly to other requests.  A value of -1 causes the T3 protocol to use the maximums that are specified elsewhere along the order of precedence. "
      ::= { serverEntry 60  }
   
   
   serverMaxHTTPMessageSize OBJECT-TYPE
      SYNTAX      INTEGER
      MAX-ACCESS  read-only
      STATUS      current
      DESCRIPTION "The maximum number of bytes allowed in messages that are received over the HTTP protocol. If you configure custom network channels for this server, each channel can override this maximum message size.  This maximum message size helps guard against a denial of service attack in which a caller attempts to force the server to allocate more memory than is available thereby keeping the server from responding quickly to other requests.  A value of -1 causes the HTTP protocol to use the maximums that are specified elsewhere along the order of precedence. "
      ::= { serverEntry 65  }
   
   
   serverMaxIIOPMessageSize OBJECT-TYPE
      SYNTAX      INTEGER
      MAX-ACCESS  read-only
      STATUS      current
      DESCRIPTION "The maximum number of bytes allowed in messages that are received over the IIOP protocol. If you configure custom network channels for this server, each channel can override this maximum message size.  This maximum message size helps guard against a denial of service attack in which a caller attempts to force the server to allocate more memory than is available thereby keeping the server from responding quickly to other requests.  A value of -1 causes the IIOP protocol to use the maximums that are specified elsewhere along the order of precedence. "
      ::= { serverEntry 70  }
   
   
   serverCompleteT3MessageTimeout OBJECT-TYPE
      SYNTAX      INTEGER
      MAX-ACCESS  read-only
      STATUS      current
      DESCRIPTION "The maximum number of seconds spent waiting for a complete T3 message to be received. If you configure network channels for this server, each channel can override this T3 message timeout.  This timeout helps guard against a denial of service attack in which a caller indicates that it will be sending a message of a certain size which it never finishes sending. "
      ::= { serverEntry 75  }
   
   
   serverCompleteHTTPMessageTimeout OBJECT-TYPE
      SYNTAX      INTEGER
      MAX-ACCESS  read-only
      STATUS      current
      DESCRIPTION "The maximum number of seconds spent waiting for a complete HTTP message to be received. If you configure network channels for this server, each channel can override this HTTP message timeout.  This timeout helps guard against a denial of service attack in which a caller indicates that it will be sending a message of a certain size which it never finishes sending.  A value of -1 indicates that this value should be obtained from network channels configured for this server. "
      ::= { serverEntry 80  }
   
   
   serverCompleteIIOPMessageTimeout OBJECT-TYPE
      SYNTAX      INTEGER
      MAX-ACCESS  read-only
      STATUS      current
      DESCRIPTION "The maximum number of seconds spent waiting for a complete IIOP message to be received. This timeout helps guard against denial of service attacks in which a caller indicates that they will be sending a message of a certain size which they never finish sending. "
      ::= { serverEntry 85  }
   
   
   serverLogRemoteExceptionsEnabled OBJECT-TYPE
      SYNTAX      INTEGER
                  {
                     true(1),
                     false(2)
                  }
      
      MAX-ACCESS  read-only
      STATUS      current
      DESCRIPTION "Specifies whether the server message log includes exceptions that are raised in remote systems. "
      ::= { serverEntry 100  }
   
   
   serverInstrumentStackTraceEnabled OBJECT-TYPE
      SYNTAX      INTEGER
                  {
                     true(1),
                     false(2)
                  }
      
      MAX-ACCESS  read-only
      STATUS      current
      DESCRIPTION "Specifies whether the server returns stack traces for RMI calls that generate exceptions.  With RMI stack tracking enabled, if a client issues an RMI call to a server subsystem or to a module running within the server, and if the subsystem or module generates an exception that includes a stack trace, the server will return the exception as well as the stack trace. With it disabled, the server will return the exception without the stack trace details. "
      ::= { serverEntry 105  }
   
   
   serverListenPort OBJECT-TYPE
      SYNTAX      INTEGER
      MAX-ACCESS  read-only
      STATUS      current
      DESCRIPTION "The default TCP port that this server uses to listen for regular (non-SSL) incoming connections.  Administrators must have the right privileges before binding to a port or else this operation will not be successful and it will render the console un-reachable.  If this port is disabled, the SSL port must be enabled. Additional ports can be configured using network channels. The cluster (multicast) port is configured separately. "
      ::= { serverEntry 120  }
   
   
   serverClusterWeight OBJECT-TYPE
      SYNTAX      INTEGER
      MAX-ACCESS  read-only
      STATUS      current
      DESCRIPTION "The proportion of the load that this server will bear, relative to other servers in a cluster.  If all servers have the default weight or the same weight, each bears an equal proportion of the load. If one server has weight 50 and all other servers have weight 100, the 50-weight server will bear half as much load as any other server. "
      ::= { serverEntry 135  }
   
   
   serverReplicationGroup OBJECT-TYPE
      SYNTAX      DisplayString (SIZE (1..64))
      MAX-ACCESS  read-only
      STATUS      current
      DESCRIPTION "Defines preferred clustered instances considered for hosting replicas of the primary HTTP session states created on the server. "
      ::= { serverEntry 140  }
   
   
   serverPreferredSecondaryGroup OBJECT-TYPE
      SYNTAX      DisplayString (SIZE (1..64))
      MAX-ACCESS  read-only
      STATUS      current
      DESCRIPTION "Defines secondary clustered instances considered for hosting replicas of the primary HTTP session states created on the server. "
      ::= { serverEntry 145  }
   
   
   serverJDBCLoggingEnabled OBJECT-TYPE
      SYNTAX      INTEGER
                  {
                     true(1),
                     false(2)
                  }
      
      MAX-ACCESS  read-only
      STATUS      current
      DESCRIPTION "Specifies whether this server maintains a JDBC log file. "
      ::= { serverEntry 165  }
   
   
   serverIIOPEnabled OBJECT-TYPE
      SYNTAX      INTEGER
                  {
                     true(1),
                     false(2)
                  }
      
      MAX-ACCESS  read-only
      STATUS      current
      DESCRIPTION "Specifies whether this server has IIOP support enabled for both the regular (non-SSL) and SSL ports. "
      ::= { serverEntry 185  }
   
   
   serverDefaultIIOPUser OBJECT-TYPE
      SYNTAX      DisplayString (SIZE (1..64))
      MAX-ACCESS  read-only
      STATUS      current
      DESCRIPTION "The user name of the default IIOP user. (Requires you to enable IIOP.) "
      ::= { serverEntry 190  }
   
   
   serverHttpdEnabled OBJECT-TYPE
      SYNTAX      INTEGER
                  {
                     true(1),
                     false(2)
                  }
      
      MAX-ACCESS  read-only
      STATUS      current
      DESCRIPTION "Whether or not HTTP support is enabled on the regular port or SSL port. "
      ::= { serverEntry 195  }
   
   
   serverListenThreadStartDelaySecs OBJECT-TYPE
      SYNTAX      INTEGER
      MAX-ACCESS  read-only
      STATUS      current
      DESCRIPTION "Returns the maximum time that the server will wait for server sockets to bind before starting a listen thread.  Properties to consider for removal "
      ::= { serverEntry 215  }
   
   
   serverListenAddress OBJECT-TYPE
      SYNTAX      DisplayString (SIZE (1..256))
      MAX-ACCESS  read-only
      STATUS      current
      DESCRIPTION "The IP address or DNS name this server uses to listen for incoming connections. For example, enter 12.34.5.67 or mymachine, respectively.  Note that the value you specify for the listen address is not the URL to the host machine and it does not include the communication protocol, listen port, or channel.  Servers can be reached through the following URL:  protocol://listen-address:listen-port  Any network channel that you configure for this server can override this listen address.  If a server's listen address is undefined, clients can reach the server through an IP address of the computer that hosts the server, a DNS name that resolves to the host, or the localhost string. The localhost string can be used only for requests from clients that are running on the same computer as the server.  If you want to limit the valid addresses for a server instance, specify one of the following:    IP address. If you provide an IP address, clients can specify either the IP address or a DNS name that maps to the IP address. Clients that specify an IP address and attempt to connect through an SSL port must disable hostname verification.    DNS name. If you provide a DNS name, clients can specify either the DNS name or the corresponding IP address.    Do not leave the listen address undefined on a computer that uses multiple IP address (a multihomed computer). On such a computer, the server will bind to all available IP addresses.  Note also that if you are using the demo certificates in a multi-server domain, Managed Server instances will fail to boot if you specify the fully-qualified DNS name. For information about this limitation and suggested workarounds, see 'Limitation on CertGen Usage' in Administering Security for Oracle WebLogic Server. "
      ::= { serverEntry 220  }
   
   
   serverLoginTimeoutMillis OBJECT-TYPE
      SYNTAX      INTEGER
      MAX-ACCESS  read-only
      STATUS      current
      DESCRIPTION "The login timeout for this server's default regular (non-SSL) listen port. This is the maximum amount of time allowed for a new connection to establish.  A value of 0 indicates there is no maximum. "
      ::= { serverEntry 225  }
   
   
   serverAdministrationPort OBJECT-TYPE
      SYNTAX      INTEGER
      MAX-ACCESS  read-only
      STATUS      current
      DESCRIPTION "The secure administration port for the server. This port requires that you enable the domain's administration port and that SSL is configured and enabled.  By default, the server uses the administration port that is specified at the domain level. To override the domain-level administration port for the current server instance, set this server's administration port. "
      ::= { serverEntry 230  }
   
   
   serverJavaCompiler OBJECT-TYPE
      SYNTAX      DisplayString (SIZE (1..32))
      MAX-ACCESS  read-only
      STATUS      current
      DESCRIPTION "The Java compiler to use for all applications hosted on this server that need to compile Java code. "
      ::= { serverEntry 235  }
   
   
   serverJavaCompilerPreClassPath OBJECT-TYPE
      SYNTAX      DisplayString (SIZE (1..256))
      MAX-ACCESS  read-only
      STATUS      current
      DESCRIPTION "The options to prepend to the Java compiler classpath when compiling Java code. "
      ::= { serverEntry 240  }
   
   
   serverJavaCompilerPostClassPath OBJECT-TYPE
      SYNTAX      DisplayString (SIZE (1..256))
      MAX-ACCESS  read-only
      STATUS      current
      DESCRIPTION "The options to append to the Java compiler classpath when compiling Java code. "
      ::= { serverEntry 245  }
   
   
   serverExtraRmicOptions OBJECT-TYPE
      SYNTAX      DisplayString (SIZE (1..256))
      MAX-ACCESS  read-only
      STATUS      current
      DESCRIPTION "The options passed to the RMIC compiler during server-side generation.  Each EJB component can override the compiler options that you specify here. "
      ::= { serverEntry 250  }
   
   
   serverTransactionLogFilePrefix OBJECT-TYPE
      SYNTAX      DisplayString (SIZE (1..32))
      MAX-ACCESS  read-only
      STATUS      current
      DESCRIPTION "The path prefix for the server's JTA transaction log files. If the pathname is not absolute, the path is assumed to be relative to the server's root directory.  For a clustered server, if you plan to be able to migrate the Transaction Recovery Service from this server if it fails to another server (backup server) in the same cluster, you must store transaction log files on persistent storage, such as a Storage Area Network (SAN) device or a dual-ported disk, available to both servers.  Do not use an NFS file system to store transaction log files. Because of the caching scheme in NFS, transaction log files on disk may not always be current. Using transaction log files stored on an NFS device for recovery may cause data corruption.  "
      ::= { serverEntry 255  }
   
   
   serverTunnelingEnabled OBJECT-TYPE
      SYNTAX      INTEGER
                  {
                     true(1),
                     false(2)
                  }
      
      MAX-ACCESS  read-only
      STATUS      current
      DESCRIPTION "Specifies whether tunneling for the T3, T3S, HTTP, HTTPS, IIOP, and IIOPS protocols should be enabled for this server.  If you create network channels for this server, each channel can override this setting. "
      ::= { serverEntry 265  }
   
   
   serverTunnelingClientTimeoutSecs OBJECT-TYPE
      SYNTAX      INTEGER
      MAX-ACCESS  read-only
      STATUS      current
      DESCRIPTION "The amount of time (in seconds) after which a missing tunneled client is considered dead.  If you create network channels for this server, each channel can override this setting. "
      ::= { serverEntry 270  }
   
   
   serverTunnelingClientPingSecs OBJECT-TYPE
      SYNTAX      INTEGER
      MAX-ACCESS  read-only
      STATUS      current
      DESCRIPTION "The interval (in seconds) at which to ping a tunneled client to see if it is still alive.  If you create network channels for this server, each channel can override this setting. "
      ::= { serverEntry 275  }
   
   
   serverJMSDefaultConnectionFactoriesEnabled OBJECT-TYPE
      SYNTAX      INTEGER
                  {
                     true(1),
                     false(2)
                  }
      
      MAX-ACCESS  read-only
      STATUS      current
      DESCRIPTION "Specifies whether this server uses JMS default connection factories.  WebLogic Server provides the following JMS default connection factories:    weblogic.jms.ConnectionFactory    weblogic.jms.XAConnectionFactory An XA factory is required for JMS applications to use JTA user-transactions, but is not required for transacted sessions. All other preconfigured attributes for the default connection factories are set to the same default values as a user-defined connection factory. If the preconfigured settings of the default factories are appropriate for your application, you do not need to configure any additional factories for your application.    Note: When using the default connection factories, you have no control over targeting the WebLogic Server instances where the connection factory may be deployed. However, you can disable the default connection factories on a per-server basis. To deploy a connection factory on independent servers, on specific servers within a cluster, or on an entire cluster, you need to configure a connection factory and specify the appropriate server targets. The default Java EE 7 JMS Connection Factory, java:comp/DefaultJMSConnectionFactory, will be available even when the WebLogic JMS default connection factories are disabled. "
      ::= { serverEntry 280  }
   
   
   serverAcceptBacklog OBJECT-TYPE
      SYNTAX      INTEGER
      MAX-ACCESS  read-only
      STATUS      current
      DESCRIPTION "The number of backlogged, new TCP connection requests that should be allowed for this server's regular and SSL ports.  Setting the backlog to 0 may prevent this server from accepting any incoming connection on some operating systems. "
      ::= { serverEntry 286  }
   
   
   serverListenPortEnabled OBJECT-TYPE
      SYNTAX      OCTET STRING
      MAX-ACCESS  read-only
      STATUS      current
      DESCRIPTION "Specifies whether this server can be reached through the default plain-text (non-SSL) listen port.  If you disable this listen port, you must enable the default SSL listen port.  You can define additional listen ports for this server by configuring network channels. "
      ::= { serverEntry 287  }
   
   
   serverUse81StyleExecuteQueues OBJECT-TYPE
      SYNTAX      OCTET STRING
      MAX-ACCESS  read-only
      STATUS      current
      DESCRIPTION "Backward compatibility mode to switch to 8.1 execute queues instead of WorkManagers. Each of the WorkManagers is converted to an individual execute queue. Setting this attribute requires a server restart.  "
      ::= { serverEntry 288  }
   
   
   serverStagingMode OBJECT-TYPE
      SYNTAX      OCTET STRING
      MAX-ACCESS  read-only
      STATUS      current
      DESCRIPTION "The mode that specifies whether an application's files are copied from a source on the Administration Server to the Managed Server's staging area during application preparation.  During application preparation, the application's files are copied from the source on the Administration Server to the Managed Server's staging area. If you specify nostage or external_stage, the copy will not occur. This is useful when the staging area is a shared directory, already containing the application files, or if this is a single server domain. The administrator must ensure that the Managed Server's staging directory is set appropriately. Deployment errors will result if the application is not available during the preparation or activation of the application. Each application can override the staging mode specified here. "
      ::= { serverEntry 289  }
   
   
   serverLowMemoryGCThreshold OBJECT-TYPE
      SYNTAX      INTEGER
      MAX-ACCESS  read-only
      STATUS      current
      DESCRIPTION "The threshold level (in percent) that this server uses for logging low memory conditions and changing the server health state to Warning.  For example, if you specify 5, the server logs a low memory warning in the log file and changes the server health state to Warning after the average free memory reaches 5% of the initial free memory measured at the server's boot time. "
      ::= { serverEntry 290  }
   
   
   serverStagingDirectoryName OBJECT-TYPE
      SYNTAX      OCTET STRING
      MAX-ACCESS  read-only
      STATUS      current
      DESCRIPTION "The directory path on the Managed Server where all staged (prepared) applications are placed.  If an absolute directory name is not specified, the path is relative to the root directory '/'. Once configured, you cannot change the staging directory name. Remove all applications from the server prior to changing this attribute. The default staging directory is 'stage', relative to the server root. "
      ::= { serverEntry 291  }
   
   
   serverGracefulShutdownTimeout OBJECT-TYPE
      SYNTAX      INTEGER
      MAX-ACCESS  read-only
      STATUS      current
      DESCRIPTION "Number of seconds a graceful shutdown operation waits before forcing a shut down. A graceful shutdown gives WebLogic Server subsystems time to complete certain application processing currently in progress. If subsystems are unable to complete processing within the number of seconds that you specify here, then the server will force shutdown automatically.  A value of 0 means that the server will wait indefinitely for graceful shutdown to complete.  The graceful shutdown timeout applies only to graceful shutdown operations. "
      ::= { serverEntry 292  }
   
   
   serverManagedServerIndependenceEnabled OBJECT-TYPE
      SYNTAX      OCTET STRING
      MAX-ACCESS  read-only
      STATUS      current
      DESCRIPTION "Specifies whether this Managed Server can be started when the Administration Server is unavailable.  In such a case, the Managed Server retrieves its configuration by reading a configuration file and other files directly. "
      ::= { serverEntry 293  }
   
   
   serverStartupTimeout OBJECT-TYPE
      SYNTAX      INTEGER
      MAX-ACCESS  read-only
      STATUS      current
      DESCRIPTION "Timeout value for server start and resume operations. If the server fails to start in the timeout period, it will force shutdown.  A value of 0 means that the server will wait indefinitely for the operation to complete. "
      ::= { serverEntry 294  }
   
   
   serverSocketBufferSizeAsChunkSize OBJECT-TYPE
      SYNTAX      OCTET STRING
      MAX-ACCESS  read-only
      STATUS      current
      DESCRIPTION "Specifies whether the server's buffer size for sending or receiving data through a raw socket should be set to 4KB.  Otherwise, the server does not impose a limit to the buffer size and defers to the operating system. This option is useful only on some operating systems for improving performance. It should be disabled in most environments. "
      ::= { serverEntry 295  }
   
   
   serverRestartMax OBJECT-TYPE
      SYNTAX      INTEGER
      MAX-ACCESS  read-only
      STATUS      current
      DESCRIPTION "The number of times that the Node Manager can restart this server within the interval specified in RestartIntervalSeconds. "
      ::= { serverEntry 296  }
   
   
   serverCompleteMessageTimeout OBJECT-TYPE
      SYNTAX      INTEGER
      MAX-ACCESS  read-only
      STATUS      current
      DESCRIPTION "The maximum number of seconds that this server waits for a complete message to be received. If you configure network channels for this server, each channel can override this message timeout.  This timeout helps guard against a denial of service attack in which a caller indicates that it will be sending a message of a certain size which it never finishes sending.  CompleteMessageTimeout affects the HTTP Response, such that if WebLogic Server discovers sockets inactive for longer than the CompleteMessageTimeout, the server will close these sockets. "
      ::= { serverEntry 297  }
   
   
   serverServerLifeCycleTimeoutVal OBJECT-TYPE
      SYNTAX      INTEGER
      MAX-ACCESS  read-only
      STATUS      current
      DESCRIPTION "Number of seconds a force shutdown operation waits before timing out and killing itself. If the operation does not complete within the configured timeout seconds, the server will shutdown automatically if the state of the server at that time was SHUTTING_DOWN.  A value of 0 means that the server will wait indefinitely for life cycle operation to complete. "
      ::= { serverEntry 298  }
   
   
   serverVerboseEJBDeploymentEnabled OBJECT-TYPE
      SYNTAX      OCTET STRING
      MAX-ACCESS  read-only
      STATUS      current
      DESCRIPTION "Whether or not verbose deployment of EJBs is enabled. "
      ::= { serverEntry 299  }
   
   
   serverAdminReconnectIntervalSeconds OBJECT-TYPE
      SYNTAX      INTEGER
      MAX-ACCESS  read-only
      STATUS      current
      DESCRIPTION "The number of seconds between reconnection attempts to the admin server. When the admin server fails the managed server will periodically try to connect back to it. "
      ::= { serverEntry 300  }
   
   
   serverClientCertProxyEnabled OBJECT-TYPE
      SYNTAX      OCTET STRING
      MAX-ACCESS  read-only
      STATUS      current
      DESCRIPTION "Specifies whether the HttpClusterServlet proxies the client certificate in a special header.  By default (or if you specify false), the weblogic.xml deployment descriptor for each web application that is deployed on this server determines whether the web application trusts certificates sent from the proxy server plugin. By default (or if the deployment descriptor specifies false), users cannot log in to the web application from a proxy server plugin.  A value of true causes proxy-server plugins to pass identity certifications from clients to all web applications that are deployed on this server instance. A proxy-server plugin encodes each identify certification in the WL-Proxy-Client-Cert header and passes the header to WebLogic Server instances. A WebLogic Server instance takes the certificate information from the header, trusting that it came from a secure source, and uses that information to authenticate the user.  If you specify true, use a weblogic.security.net.ConnectionFilter to ensure that this WebLogic Server instance accepts connections only from the machine on which the proxy-server plugin is running. Specifying true without using a connection filter creates a security vulnerability because the WL-Proxy-Client-Cert header can be spoofed.  A cluster can also specify whether the HttpClusterServlet proxies the client certificate in a special header. The cluster-level setting overrides the setting in individual servers that are part of the cluster. "
      ::= { serverEntry 301  }
   
   
   serverRestartDelaySeconds OBJECT-TYPE
      SYNTAX      INTEGER
      MAX-ACCESS  read-only
      STATUS      current
      DESCRIPTION "The number of seconds the Node Manager should wait before restarting this server.  After killing a server process, the system might need several seconds to release the TCP port(s) the server was using. If Node Manager attempts to restart the Managed Server while its ports are still active, the startup attempt fails.  If AutoMigration is enabled and RestartDelaySeconds is 0, the RestartDelaySeconds is automatically set to the lease time. This prevents the server from failing to restart after migration when the previous lease is still valid. "
      ::= { serverEntry 302  }
   
   
   serverLowMemoryGranularityLevel OBJECT-TYPE
      SYNTAX      INTEGER
      MAX-ACCESS  read-only
      STATUS      current
      DESCRIPTION "The granularity level (in percent) that this server uses for logging low memory conditions and changing the server health state to Warning.  For example, if you specify 5 and the average free memory drops by 5% or more over two measured intervals, the server logs a low memory warning in the log file and changes the server health state to Warning. "
      ::= { serverEntry 303  }
   
   
   serverSocketReaders OBJECT-TYPE
      SYNTAX      INTEGER
      MAX-ACCESS  read-only
      STATUS      current
      DESCRIPTION "The number of socket reader threads. "
      ::= { serverEntry 304  }
   
   
   serverOutboundEnabled OBJECT-TYPE
      SYNTAX      OCTET STRING
      MAX-ACCESS  read-only
      STATUS      current
      DESCRIPTION "Specifies whether new server-to-server connections may consider the default server channel when initiating a connection. This is only relevant if the connection needs to be bound to the default listen address. This will only work for binary protocols that support both outbound and inbound traffic.  When this feature is not enabled, connections are initiated using a local address selected by the underlying hardware. For the default channel this is usually what is wanted for IP-routing to be effective. Note that since the default is false, other outbound channels will be considered in preference to the default channel.  Default administration channels, created when the domain-wide administration port is turned on, are always considered and bound when initiating an administrative connection. To allow IP-routing for administration traffic create custom admin with {@link NetworkAccessPointMBean#isOutboundEnabled isOutboundEnabled} set to false instead of enabling the domain-wide ADMIN port. "
      ::= { serverEntry 305  }
   
   
   serverJDBCLLRTableName OBJECT-TYPE
      SYNTAX      OCTET STRING
      MAX-ACCESS  read-only
      STATUS      current
      DESCRIPTION "The table name for this server's Logging Last Resource (LLR) database table(s). WebLogic Server creates the table(s) and then uses them during transaction processing for the LLR transaction optimization. This setting must be unique for each server. The default table name is WL_LLR_SERVERNAME.  This setting only applies if this server hosts one or more LLR-enabled JDBC data sources.  The format for the tables that WebLogic Server creates is [[[catalog.]schema.]name.] Each '.' in the table name is significant, and schema generally corresponds to username in many databases.  IMPORTANT: If this value is changed but the LLR table already exists in the database, you must preserve the existing table's data. Consequently, when changing the table name, the existing database table must be renamed by a database administrator to match the new configured table name. Otherwise, transaction records may be lost, resulting in heuristic failures that aren't logged.  IMPORTANT: Each server's table name must be unique. Multiple LLR-enabled data sources within the same server may share the same table, but multiple servers must not share the same table. If multiple same-named servers share a table, the behavior is undefined and it is likely that transactions will not recover properly after a crash, creating heuristic hazards. "
      ::= { serverEntry 306  }
   
   
   serverInterfaceAddress OBJECT-TYPE
      SYNTAX      OCTET STRING
      MAX-ACCESS  read-only
      STATUS      current
      DESCRIPTION "The IP address of the NIC that this server should use for multicast traffic. "
      ::= { serverEntry 307  }
   
   
   serverExtraEjbcOptions OBJECT-TYPE
      SYNTAX      OCTET STRING
      MAX-ACCESS  read-only
      STATUS      current
      DESCRIPTION "The options passed to the EJB compiler during server-side generation.  Each EJB component can override the compiler options that you specify here. The following options are valid:   -forcegeneration Forces generation of wrapper classes. Without this flag the classes may not be regenerated if it is determined to be unnecessary.  -disableHotCodeGen Generate ejb stub and skel as part of ejbc. Avoid HotCodeGen to have better performance.   -keepgenerated Keep the generated .java files.   -compiler javac Java compiler to exec.  If not specified, the -compilerclass option will be used.  -compilerclass com.sun.tools.javac.Main Specifies the compiler class to invoke.  -g Compile debugging info into class file.  -normi Passed through to Symantec's sj.  -classpath path Classpath to use.  -source source Source version.  -Joption Flags passed through to java runtime.  "
      ::= { serverEntry 308  }
   
   
   serverCOMEnabled OBJECT-TYPE
      SYNTAX      OCTET STRING
      MAX-ACCESS  read-only
      STATUS      current
      DESCRIPTION "Specifies whether COM support is enabled on the regular (non-SSL) port. COM is not supported on the SSL port. (The remaining fields on this page are relevant only if you check this box.) "
      ::= { serverEntry 309  }
   
   
   serverMessageIdPrefixEnabled OBJECT-TYPE
      SYNTAX      OCTET STRING
      MAX-ACCESS  read-only
      STATUS      current
      DESCRIPTION "Indicates whether message IDs in logged messages will include a prefix. Message ids are 6 digit numeric strings that can be optionally presented in a log entry with a prefix. The prefix used by server messages is 'BEA-'. "
      ::= { serverEntry 310  }
   
   
   serverAutoRestart OBJECT-TYPE
      SYNTAX      OCTET STRING
      MAX-ACCESS  read-only
      STATUS      current
      DESCRIPTION "Specifies whether the Node Manager can automatically restart this server if it crashes or otherwise goes down unexpectedly. "
      ::= { serverEntry 311  }
   
   
   serverIgnoreSessionsDuringShutdown OBJECT-TYPE
      SYNTAX      OCTET STRING
      MAX-ACCESS  read-only
      STATUS      current
      DESCRIPTION "Indicates whether a graceful shutdown operation drops all HTTP sessions immediately. If this is set to false, a graceful shutdown operation waits for HTTP sessions to complete or timeout. "
      ::= { serverEntry 312  }
   
   
   serverDefaultTGIOPUser OBJECT-TYPE
      SYNTAX      OCTET STRING
      MAX-ACCESS  read-only
      STATUS      current
      DESCRIPTION "The default user associated with the Tuxedo GIOP (TGIOP) protocol. (Requires you to configure WebLogic Tuxedo Connector (WTC) for this server.) "
      ::= { serverEntry 313  }
   
   
   serverMaxOpenSockCount OBJECT-TYPE
      SYNTAX      INTEGER
      MAX-ACCESS  read-only
      STATUS      current
      DESCRIPTION "The maximum number of open sockets allowed in server at a given point of time.  When the maximum threshold is reached, the server stops accepting new requests until the number of sockets drops below the threshold.  A value less than 0 indicates an unlimited size. "
      ::= { serverEntry 314  }
   
   
   serverLowMemorySampleSize OBJECT-TYPE
      SYNTAX      INTEGER
      MAX-ACCESS  read-only
      STATUS      current
      DESCRIPTION "The number of times this server samples free memory during the time period specified by LowMemoryTimeInterval.  Increasing the sample size can improve the accuracy of the reading. "
      ::= { serverEntry 315  }
   
   
   serverAutoKillIfFailed OBJECT-TYPE
      SYNTAX      OCTET STRING
      MAX-ACCESS  read-only
      STATUS      current
      DESCRIPTION "This is the equivalent of setting the OverloadProtectionMBean failureAction to 'force-shutdown' and the panicAction to 'system-exit'. "
      ::= { serverEntry 316  }
   
   
   serverCustomIdentityKeyStoreFileName OBJECT-TYPE
      SYNTAX      OCTET STRING
      MAX-ACCESS  read-only
      STATUS      current
      DESCRIPTION "The source of the identity keystore. For a JKS keystore, the source is the path and file name. For an Oracle Key Store Service (KSS) keystore, the source is the KSS URI.  If using a JKS keystore, the keystore path name must either be absolute or relative to where the server was booted.  If using a KSS keystore, the keystore URI must be of the form:  kss://system/keystorename  where keystorename is the name of the keystore registered in KSS.   The value in this attribute is only used if KeyStores is CUSTOM_IDENTITY_AND_JAVA_STANDARD_TRUST, CUSTOM_IDENTITY_AND_CUSTOM_TRUST or CUSTOM_IDENTITY_AND_COMMAND_LINE_TRUST. "
      ::= { serverEntry 317  }
   
   
   serverTGIOPEnabled OBJECT-TYPE
      SYNTAX      OCTET STRING
      MAX-ACCESS  read-only
      STATUS      current
      DESCRIPTION "Specifies whether this server supports Tuxedo GIOP (TGIOP) requests. (Requires you to configure WebLogic Tuxedo Connector (WTC) for this server.) "
      ::= { serverEntry 318  }
   
   
   serverHealthCheckStartDelaySeconds OBJECT-TYPE
      SYNTAX      INTEGER
      MAX-ACCESS  read-only
      STATUS      current
      DESCRIPTION "The number of seconds the Node Manager should wait before starting to monitor the server. "
      ::= { serverEntry 319  }
   
   
   serverUploadDirectoryName OBJECT-TYPE
      SYNTAX      OCTET STRING
      MAX-ACCESS  read-only
      STATUS      current
      DESCRIPTION "The directory path on the Administration Server where all uploaded applications are placed.  If an absolute directory name is not specified, the path is relative to the root directory '/'. The default staging directory is 'stage', relative to the server root. On the Managed Server this returns null, and is not configurable. "
      ::= { serverEntry 320  }
   
   
   serverWeblogicPluginEnabled OBJECT-TYPE
      SYNTAX      OCTET STRING
      MAX-ACCESS  read-only
      STATUS      current
      DESCRIPTION "Specifies whether this server uses the proprietary WL-Proxy-Client-IP header.  Set this attribute to true to specify that this server instance uses the proprietary WL-Proxy-Client-IP header, which is recommended if the server instance will receive requests from a proxy plug-in. If the server instance is a member of a cluster that will receive proxied requests, enable the WebLogic plug-in at the cluster level. For servers that are members of a cluster, the setting at the cluster level overrides the server's setting. When the WebLogic plug-in is enabled at the cluster level, a call to getRemoteAddr will return the address of the browser client from the proprietary WL-Proxy-Client-IP header instead of the Web server.  Set this attrbute to false to disable the weblogic-plugin-enabled parameter, weblogic-plugin-enabled=false, in the config.xml file.  Note: If you are using Oracle HTTP Server, the WebLogic Proxy Plug-In, or Oracle Traffic Director to distribute client requests to a Managed Server or a cluster, Oracle recommends setting this attribute to true. "
      ::= { serverEntry 321  }
   
   
   serverJDBCLoginTimeoutSeconds OBJECT-TYPE
      SYNTAX      INTEGER
      MAX-ACCESS  read-only
      STATUS      current
      DESCRIPTION "The JDBC Login Timeout value. Specified value is passed into java.sql.DriverManager.setLoginTimeout(). Note that this DriverManager setting will impact *all* JDBC drivers loaded into this JVM. Feature is disabled by default. "
      ::= { serverEntry 322  }
   
   
   serverClasspathServletDisabled OBJECT-TYPE
      SYNTAX      OCTET STRING
      MAX-ACCESS  read-only
      STATUS      current
      DESCRIPTION "The ClasspathServlet will serve any class file in the classpath and is registered by default in every Web application (including management). It does not need to be turned on for many applications though, and represents a security hole if unchecked.  WLS components such as JDBC and JMS rely on the ClasspathServlet. If the servlet can not be disabled, then set the ClassPathServletSecureModeEnabled to true. "
      ::= { serverEntry 323  }
   
   
   serverIdleConnectionTimeout OBJECT-TYPE
      SYNTAX      INTEGER
      MAX-ACCESS  read-only
      STATUS      current
      DESCRIPTION "The maximum number of seconds that a connection is allowed to be idle before it is closed by the server. The T3 and T3S protocols ignore this attribute. If you configure network channels for this server, each channel can override this idle connection message timeout.  This timeout helps guard against server deadlock through too many open connections. "
      ::= { serverEntry 324  }
   
   
   serverDefaultInternalServletsDisabled OBJECT-TYPE
      SYNTAX      OCTET STRING
      MAX-ACCESS  read-only
      STATUS      current
      DESCRIPTION "Specifies whether all default servlets in the servlet engine are disabled.  This includes: weblogic.servlet.ClasspathServlet weblogic.servlet.utils.iiop.GetIORServlet weblogic.rjvm.http.TunnelSendServlet weblogic.rjvm.http.TunnelRecvServlet weblogic.rjvm.http.TunnelLoginServlet weblogic.rjvm.http.TunnelCloseServlet If set to true, this property overrides the ClasspathServletDisabled property. "
      ::= { serverEntry 325  }
   
   
   serverMaxMessageSize OBJECT-TYPE
      SYNTAX      INTEGER
      MAX-ACCESS  read-only
      STATUS      current
      DESCRIPTION "The maximum number of bytes allowed in messages that are received over all supported protocols, unless overridden by a protocol-specific setting or a custom channel setting.  The order of precedence for setting message size maximums is as follows:    A channel-wide maximum in a custom network channel.    A protocol-specific setting in the default network channel. See  {@link #getMaxCOMMessageSize() getMaxCOMMessageSize} {@link #getMaxHTTPMessageSize() getMaxHTTPMessageSize} {@link #getMaxIIOPMessageSize() getMaxIIOPessageSize} {@link #getMaxT3MessageSize() getMaxT3MessageSize}     The message maximum in this attribute.    This maximum message size helps guard against a denial of service attack in which a caller attempts to force the server to allocate more memory than is available thereby keeping the server from responding quickly to other requests. A client can set this value using the -Dweblogic.MaxMessageSize property. "
      ::= { serverEntry 326  }
   
   
   serverCustomTrustKeyStoreType OBJECT-TYPE
      SYNTAX      OCTET STRING
      MAX-ACCESS  read-only
      STATUS      current
      DESCRIPTION "The type of the keystore. Generally, this is JKS. If using the Oracle Key Store Service, this would be KSS  If empty or null, then the JDK's default keystore type (specified in java.security) is used. This keystore type is only used if KeyStores is CUSTOM_IDENTITY_AND_CUSTOM_TRUST. "
      ::= { serverEntry 327  }
   
   
   serverListenersBindEarly OBJECT-TYPE
      SYNTAX      OCTET STRING
      MAX-ACCESS  read-only
      STATUS      current
      DESCRIPTION "Determines whether the server should bind server sockets early.  Early binding detects port conflicts quickly and also gives user feedback on the default listen port as to the server state. "
      ::= { serverEntry 328  }
   
   
   serverLowMemoryTimeInterval OBJECT-TYPE
      SYNTAX      INTEGER
      MAX-ACCESS  read-only
      STATUS      current
      DESCRIPTION "The amount of time (in seconds) that defines the interval over which this server determines average free memory values.  By default, the server obtains an average free memory value every 3600 seconds. "
      ::= { serverEntry 329  }
   
   
   serverTransactionLogFileWritePolicy OBJECT-TYPE
      SYNTAX      OCTET STRING
      MAX-ACCESS  read-only
      STATUS      current
      DESCRIPTION "The policy that determines how transaction log file entries are written to disk. This policy can affect transaction performance. (Note: To be transactionally safe, the Direct-Write policy may require additional OS or environment changes on some Windows systems.)  WebLogic Server supports the following policies:    Cache-Flush. Flushes operating system and on-disk caches after each write.    Direct-Write. Tells the operating system to write directly to disk with each write. Direct-Write performs better than Cache-Flush.    If Direct-Write is not supported on the host platform, the policy becomes Cache-Flush and a log message is printed.  Note: On Windows, the 'Direct-Write' policy may leave transaction data in the on-disk cache without writing it to disk immediately. This is not transactionally safe because a power failure can cause loss of on-disk cache data. For transactionally safe writes using 'Direct-Write' on Windows, either disable all write caching for the disk (enabled by default), or use a disk with a battery-backed cache.  The on-disk cache for a hard-drive on Windows can be disabled through system administration: Control-Panel -&gt; System -&gt; Hardware-tab -&gt; Device-Manager-button -&gt; Disk-Drives -&gt; name-of-drive -&gt; Policies-tab -&gt; 'Enable write caching on the disk' check-box. Some file systems do not allow this value to be changed. For example, a RAID system that has a reliable cache. "
      ::= { serverEntry 330  }
   
   
   serverHttpTraceSupportEnabled OBJECT-TYPE
      SYNTAX      OCTET STRING
      MAX-ACCESS  read-only
      STATUS      current
      DESCRIPTION "Returns the HttpTraceSupportEnabled value "
      ::= { serverEntry 331  }
   
   
   serverKeyStores OBJECT-TYPE
      SYNTAX      OCTET STRING
      MAX-ACCESS  read-only
      STATUS      current
      DESCRIPTION "Which configuration rules should be used for finding the server's identity and trust keystores? "
      ::= { serverEntry 332  }
   
   
   serverAutoMigrationEnabled OBJECT-TYPE
      SYNTAX      OCTET STRING
      MAX-ACCESS  read-only
      STATUS      current
      DESCRIPTION "Specifies whether Node Manager can automatically restart this server and its services on another machine if the server fails. "
      ::= { serverEntry 333  }
   
   
   serverPeriodLength OBJECT-TYPE
      SYNTAX      INTEGER
      MAX-ACCESS  read-only
      STATUS      current
      DESCRIPTION "The time interval in milliseconds of the heartbeat period. A value of 0 indicates that heartbeats are turned off. "
      ::= { serverEntry 334  }
   
   
   serverStuckThreadTimerInterval OBJECT-TYPE
      SYNTAX      INTEGER
      MAX-ACCESS  read-only
      STATUS      current
      DESCRIPTION "The number of seconds after which WebLogic Server periodically scans threads to see if they have been continually working for the configured maximum length of time. "
      ::= { serverEntry 335  }
   
   
   serverDGCIdlePeriodsUntilTimeout OBJECT-TYPE
      SYNTAX      INTEGER
      MAX-ACCESS  read-only
      STATUS      current
      DESCRIPTION "The number of idle periods allowed before the object is collected. "
      ::= { serverEntry 336  }
   
   
   serverMuxerClass OBJECT-TYPE
      SYNTAX      OCTET STRING
      MAX-ACCESS  read-only
      STATUS      current
      DESCRIPTION "Non-blocking IO is enabled by default on the server side. The default value is weblogic.socket.NIOSocketMuxer.  The Certicom SSL implementation is not supported with NIOSocketMuxer. If you need to secure internet communication, Oracle recommends enabling JSSE (Java Secure Socket Extension). "
      ::= { serverEntry 337  }
   
   
   serverHealthCheckIntervalSeconds OBJECT-TYPE
      SYNTAX      INTEGER
      MAX-ACCESS  read-only
      STATUS      current
      DESCRIPTION "The number of seconds that defines the frequency of this server's self-health monitoring. The server monitors the health of it's subsystems every HealthCheckIntervalSeconds and changes the Server's overall state if required.  "
      ::= { serverEntry 338  }
   
   
   serverRestartIntervalSeconds OBJECT-TYPE
      SYNTAX      INTEGER
      MAX-ACCESS  read-only
      STATUS      current
      DESCRIPTION "The number of seconds during which this server can be restarted, up to the number of times specified in RestartMax. "
      ::= { serverEntry 339  }
   
   
   serverIdlePeriodsUntilTimeout OBJECT-TYPE
      SYNTAX      INTEGER
      MAX-ACCESS  read-only
      STATUS      current
      DESCRIPTION "The number of idle periods until peer is considered unreachable. "
      ::= { serverEntry 340  }
   
   
   serverCustomTrustKeyStoreFileName OBJECT-TYPE
      SYNTAX      OCTET STRING
      MAX-ACCESS  read-only
      STATUS      current
      DESCRIPTION "The source of the custom trust keystore. For a JKS keystore, the source is the path and file name. For an Oracle Key Store Service (KSS) keystore, the source is the KSS URI.  If using a JKS keystore, the keystore path name must either be absolute or relative to where the server was booted.  If using a KSS keystore, the keystore URI must be of the form:  kss://system/keystorename  where keystorename is the name of the keystore registered in KSS.   The value in this attribute is only used if KeyStores is  CUSTOM_IDENTITY_AND_CUSTOM_TRUST. "
      ::= { serverEntry 341  }
   
   
   serverHostsMigratableServices OBJECT-TYPE
      SYNTAX      OCTET STRING
      MAX-ACCESS  read-only
      STATUS      current
      DESCRIPTION "Gets the hostsMigratableServices attribute of the ServerMBean object "
      ::= { serverEntry 342  }
   
   
   serverExternalDNSName OBJECT-TYPE
      SYNTAX      OCTET STRING
      MAX-ACCESS  read-only
      STATUS      current
      DESCRIPTION "The external IP address or DNS name for this server.  This address will be sent with HTTP session cookies and with dynamic server lists to HTTP proxies. It will also be used by external application clients to enable the propagation of RMI traffic through network address translating (NAT) firewalls.  You must specify an external DNS name for configurations in which a firewall is performing network address translation, unless clients are accessing WebLogic Server using t3 and the default channel. For example, define the external DNS name for configurations in which a firewall is performing network address translation, and clients are accessing WebLogic Server using HTTP via a proxy plug-in. "
      ::= { serverEntry 343  }
   
   
   serverOutboundPrivateKeyEnabled OBJECT-TYPE
      SYNTAX      OCTET STRING
      MAX-ACCESS  read-only
      STATUS      current
      DESCRIPTION "Specifies whether the SSL identity specified by {@link SSLMBean#getServerPrivateKeyAlias() getSSLMBean#ServerPrivateKeyAlias} for this server should be used for outbound SSL connections on the default server channel. In normal circumstances the outbound identity is determined by the caller's environment. "
      ::= { serverEntry 344  }
   
   
   serverAdministrationProtocol OBJECT-TYPE
      SYNTAX      OCTET STRING
      MAX-ACCESS  read-only
      STATUS      current
      DESCRIPTION "Returns the protocol to be used for administrative connections when none is specified. "
      ::= { serverEntry 345  }
   
   
   serverCustomIdentityKeyStoreType OBJECT-TYPE
      SYNTAX      OCTET STRING
      MAX-ACCESS  read-only
      STATUS      current
      DESCRIPTION "The type of the keystore. Generally, this is JKS. If using the Oracle Key Store Service, this would be KSS  If empty or null, then the JDK's default keystore type (specified in java.security) is used. The custom identity key store type is only used if KeyStores is CUSTOM_IDENTITY_AND_JAVA_STANDARD_TRUST, CUSTOM_IDENTITY_AND_CUSTOM_TRUST or CUSTOM_IDENTITY_AND_COMMAND_LINE_TRUST. "
      ::= { serverEntry 346  }
   
   
   serverStartupMode OBJECT-TYPE
      SYNTAX      OCTET STRING
      MAX-ACCESS  read-only
      STATUS      current
      DESCRIPTION "The state in which this server should be started. If you specify STANDBY, you must also enable the domain-wide administration port.  In the RUNNING state, a server offers its services to clients and can operate as a full member of a cluster. In the ADMIN state, the server is up and running, but available only for administration operations, allowing you to perform server and application-level administration tasks without risk to running applications. In the STANDBY state, a server instance does not process any request; its regular Listen Port is closed. The Administration Port is open. It only accepts life cycle commands that transition the server instance to either the RUNNING or the SHUTDOWN state. Other Administration requests are not accepted. A STANDBY server's only purpose is to resume into the RUNNING state quickly; it saves server startup time. "
      ::= { serverEntry 347  }
   
   
   serverNMSocketCreateTimeoutInMillis OBJECT-TYPE
      SYNTAX      INTEGER
      MAX-ACCESS  read-only
      STATUS      current
      DESCRIPTION "Returns the timeout value to be used by NodeManagerRuntime when creating a a socket connection to the agent. Default set high as SSH agent may require a high connection establishment time. "
      ::= { serverEntry 348  }
   
   
   serverListenDelaySecs OBJECT-TYPE
      SYNTAX      INTEGER
      MAX-ACCESS  read-only
      STATUS      current
      DESCRIPTION "Perpetuated for compatibility with 6.1 only. "
      ::= { serverEntry 349  }
   
   
   serverIdleIIOPConnectionTimeout OBJECT-TYPE
      SYNTAX      INTEGER
      MAX-ACCESS  read-only
      STATUS      current
      DESCRIPTION "The maximum number of seconds an IIOP connection is allowed to be idle before it is closed by the server. This timeout helps guard against server deadlock through too many open connections. "
      ::= { serverEntry 350  }
   
   
   serverMaxCOMMessageSize OBJECT-TYPE
      SYNTAX      INTEGER
      MAX-ACCESS  read-only
      STATUS      current
      DESCRIPTION "The maximum number of bytes allowed in messages that are received over the COM protocol. If you configure custom network channels for this server, each channel can override this maximum message size.  This maximum message size helps guard against a denial of service attack in which a caller attempts to force the server to allocate more memory than is available thereby keeping the server from responding quickly to other requests.  A value of -1 causes the COM protocol to use the maximums that are specified elsewhere along the order of precedence. "
      ::= { serverEntry 351  }
   
   
   serverMessagingBridgeThreadPoolSize OBJECT-TYPE
      SYNTAX      INTEGER
      MAX-ACCESS  read-only
      STATUS      current
      DESCRIPTION "Returns the size of the messaging bridge execute thread pool. "
      ::= { serverEntry 352  }
   
   
   serverServerVersion OBJECT-TYPE
      SYNTAX      OCTET STRING
      MAX-ACCESS  read-only
      STATUS      current
      DESCRIPTION "The release identifier for the server. Since this is a configured attribute it is only as accurate as the configuration. The form of the version is major.minor.servicepack.rollingpatch. Not all parts of the version are required. i.e. '7' is acceptable. "
      ::= { serverEntry 353  }
   
   
   serverIIOPTxMechanism OBJECT-TYPE
      SYNTAX      OCTET STRING
      MAX-ACCESS  read-only
      STATUS      current
      DESCRIPTION "Configures IIOP propagate transactions using either WebLogic-specific JTA or the OMG-specified OTS.  It is not possible to use both because it affects the way transactions are negotiated. "
      ::= { serverEntry 354  }
   
   
   serverMSIFileReplicationEnabled OBJECT-TYPE
      SYNTAX      OCTET STRING
      MAX-ACCESS  read-only
      STATUS      current
      DESCRIPTION "Specifies whether the Administration Server replicates its configuration files to this Managed Server.  With file replication enabled, the Administration Server copies its configuration file and SerializedSystemIni.dat into the Managed Server's root directory every 5 minutes. This option does not replicate a boot identity file.  Regardless of the name of the configuration file that you used to start the Administration Server, the replicated file is always named msi-config.xml. For example, if you specified -Dweblogic.ConfigFile=MyConfig.xml when you started the Administration Server, if you have enabled file replication, the Administration Server copies MyConfig.xml and names the copy msi-config.xml.  Depending on your backup schemes and the frequency with which you update your domain's configuration, this option might not be worth the performance cost of copying potentially large files across a network. "
      ::= { serverEntry 355  }
   
   
   serverJNDITransportableObjectFactoryList OBJECT-TYPE
      SYNTAX      OCTET STRING
      MAX-ACCESS  read-only
      STATUS      current
      DESCRIPTION "List of factories that create transportable objects. "
      ::= { serverEntry 356  }
   
   
   serverHealthCheckTimeoutSeconds OBJECT-TYPE
      SYNTAX      INTEGER
      MAX-ACCESS  read-only
      STATUS      current
      DESCRIPTION "The number of seconds the Node Manager should wait before timing out its health query to this server.  If the timeout is reached, Node Managed assumes the Managed Server has failed. "
      ::= { serverEntry 357  }
   
   
   serverStuckThreadMaxTime OBJECT-TYPE
      SYNTAX      INTEGER
      MAX-ACCESS  read-only
      STATUS      current
      DESCRIPTION "The number of seconds that a thread must be continually working before this server considers the thread stuck.  For example, if you set this to 600 seconds, WebLogic Server considers a thread to be 'stuck' after 600 seconds of continuous use.  In WebLogic Server 9.x and later, it is recommended that you use the ServerFailureTriggerMBean in the OverloadProtectionMBean. The ServerFailureTriggerMBean transitions the server to a FAILED state after the specified number of stuck threads are detected. The OverloadProtectionMBean has options to suspend or shutdown a failed server.  "
      ::= { serverEntry 358  }
   
   
   serverCompleteCOMMessageTimeout OBJECT-TYPE
      SYNTAX      INTEGER
      MAX-ACCESS  read-only
      STATUS      current
      DESCRIPTION "The maximum number of seconds spent waiting for a complete COM message to be received. This setting does not apply to any network channels that you have configured for this server.  This timeout helps guard against a denial of service attack in which a caller indicates that they will be sending a message of a certain size which they never finish sending. "
      ::= { serverEntry 359  }
   
   
   serverConnectTimeout OBJECT-TYPE
      SYNTAX      INTEGER
      MAX-ACCESS  read-only
      STATUS      current
      DESCRIPTION "The amount of time that this server should wait to establish an outbound socket connection before timing out. A value of 0 disables server connect timeout. "
      ::= { serverEntry 360  }
   
   
   serverGatheredWritesEnabled OBJECT-TYPE
      SYNTAX      OCTET STRING
      MAX-ACCESS  read-only
      STATUS      current
      DESCRIPTION "Enables gathered writes over NIO socket channels. Enabling this attribute increases efficiency during I/O in environments with high network throughput and should be used only when configuring a WebLogic domain for Oracle Exalogic. "
      ::= { serverEntry 361  }
   
   
   serverScatteredReadsEnabled OBJECT-TYPE
      SYNTAX      OCTET STRING
      MAX-ACCESS  read-only
      STATUS      current
      DESCRIPTION "Enables scattered reads over NIO socket channels. Enabling this attribute increases efficiency during I/O in environments with high network throughput and should be used only when configuring a WebLogic domain for Oracle Exalogic. "
      ::= { serverEntry 362  }
   
   
   serverVirtualMachineName OBJECT-TYPE
      SYNTAX      OCTET STRING
      MAX-ACCESS  read-only
      STATUS      current
      DESCRIPTION "When WLS is running on JRVE, this specifies the name of the virtual machine running this server "
      ::= { serverEntry 363  }
   
   
   serverUseFusionForLLR OBJECT-TYPE
      SYNTAX      OCTET STRING
      MAX-ACCESS  read-only
      STATUS      current
      DESCRIPTION "Enables the use of the ADM_DDL  store procedure for LLR. The default value is false (not enabled).  When enabled, a  WLS_ prefix and _DYD suffix is is automatically added to the LLR table name at runtime so the LLR table name in server configuration is not consistent with the actual table name in database. "
      ::= { serverEntry 364  }
   
   
   serverAddWorkManagerThreadsByCpuCount OBJECT-TYPE
      SYNTAX      OCTET STRING
      MAX-ACCESS  read-only
      STATUS      current
      DESCRIPTION "Enables increased efficiency of the self-tuning thread pool by aligning it with the Exalogic processor architecture threading capabilities. Use only when configuring a WebLogic domain for Oracle Exalogic.  Enabling this attribute increases efficiency during I/O in environments with high network throughput. Disabling this attribute allows the thread pool to self-tune to match the demand of the workload at the expense of longer ramp up time.  "
      ::= { serverEntry 365  }
   
   
   serverUseDetailedThreadName OBJECT-TYPE
      SYNTAX      OCTET STRING
      MAX-ACCESS  read-only
      STATUS      current
      DESCRIPTION "Specifies whether to includes detailed information in self-tuning thread pool thread names. Setting this flag as true would include additional information, such as the name of the Work Manager for which the execute thread is executing the task, but at the expense of overhead in keeping the thread name updated with such information. "
      ::= { serverEntry 366  }
   
   
   serverCompleteWriteTimeout OBJECT-TYPE
      SYNTAX      INTEGER
      MAX-ACCESS  read-only
      STATUS      current
      DESCRIPTION "The maximum number of seconds that this server waits for a complete HTTP response to be sent.  A value of 0 disables the complete write timeout. The default value is derived from the CompleteHTTPMessageTimeout. If it is -1, then the CompleteMessageTimeout value is used for the default value. "
      ::= { serverEntry 367  }
   
   
   serverUseConcurrentQueueForRequestManager OBJECT-TYPE
      SYNTAX      OCTET STRING
      MAX-ACCESS  read-only
      STATUS      current
      DESCRIPTION "Reduces lock contention by using concurrent buffer queue to park incoming requests. Enabling this attribute increases throughput as requests are scheduled without acquiring any locks.  "
      ::= { serverEntry 368  }
   
   
   serverUseEnhancedPriorityQueueForRequestManager OBJECT-TYPE
      SYNTAX      OCTET STRING
      MAX-ACCESS  read-only
      STATUS      current
      DESCRIPTION "Reduces lock contention by using the enhanced ConcurrentCalendarQueue as the priority based queue for pending requests that are waiting for a thread.  This attribute should be enabled only in an Oracle Exalogic environment. "
      ::= { serverEntry 369  }
   
   
   serverReplicationPorts OBJECT-TYPE
      SYNTAX      OCTET STRING
      MAX-ACCESS  read-only
      STATUS      current
      DESCRIPTION "When WLS is running on Exalogic machines, cluster replication traffic could go over multiple replication channels. However multiple replication channels need not be configured on each clustered server instance. Only one replication channel with explicit IP-Address needs to be configured for each server and replicationPorts range can be specified for each server. For eg. range 7001-7010 will create 10 replication channels with ports 7001 to 7010 for the given server. These channels inherits all the properties of the configured replication channel except the listen port.Names of these channels will be derived from the configured replication channel with suffic {x} added where x could be 1,2.. as per the number of ports specified. Public ports are same as the listen port for these additional channels. "
      ::= { serverEntry 370  }
   
   
   serverPrintStackTraceInProduction OBJECT-TYPE
      SYNTAX      OCTET STRING
      MAX-ACCESS  read-only
      STATUS      current
      DESCRIPTION "Specifies whether the server message log includes exception stack trace that are raised in remote systems. "
      ::= { serverEntry 371  }
   
   
   serverResolveDNSName OBJECT-TYPE
      SYNTAX      OCTET STRING
      MAX-ACCESS  read-only
      STATUS      current
      DESCRIPTION "Resolve the listen address to use for all T3 communication "
      ::= { serverEntry 372  }
   
   
   serverAllowShrinkingPriorityRequestQueue OBJECT-TYPE
      SYNTAX      OCTET STRING
      MAX-ACCESS  read-only
      STATUS      current
      DESCRIPTION "Specifies whether self-tuning should allow shrinking of its priority based queue for pending requests after it has grown in size due to busy workload, and whether it should try to purge work requests that have already been picked up for processing due to minimum threads constraints before growing the queue. Setting this to true would help reduce memory footprint after the busy work period has ended, at the expense of the overhead of growing the request queue again at the next period of busy workload. It would also help to reduce the amount of memory allocated for the request queue, at the expense of the overhead required in purging already processed work requests from the queue. "
      ::= { serverEntry 373  }
   
   
   serverUseEnhancedIncrementAdvisor OBJECT-TYPE
      SYNTAX      OCTET STRING
      MAX-ACCESS  read-only
      STATUS      current
      DESCRIPTION "Specifies whether self-tuning should use the enhanced IncrementAdvisor implementation that uses a different algorithm to adjust the size of the self-tuning thread pool. "
      ::= { serverEntry 374  }
   
   
   serverTags OBJECT-TYPE
      SYNTAX      OCTET STRING
      MAX-ACCESS  read-only
      STATUS      current
      DESCRIPTION "Return all tags on this Configuration MBean "
      ::= { serverEntry 375  }
   
   
   serverBuzzPort OBJECT-TYPE
      SYNTAX      INTEGER
      MAX-ACCESS  read-only
      STATUS      current
      DESCRIPTION "Buzz endpoint port.  A value of 0 means system-allocated (dynamic) port. "
      ::= { serverEntry 376  }
   
   
   serverMaxConcurrentNewThreads OBJECT-TYPE
      SYNTAX      INTEGER
      MAX-ACCESS  read-only
      STATUS      current
      DESCRIPTION "The maximum number of running threads that can be created by all the Managed Thread Factories in the server. "
      ::= { serverEntry 377  }
   
   
   serverEagerThreadLocalCleanup OBJECT-TYPE
      SYNTAX      OCTET STRING
      MAX-ACCESS  read-only
      STATUS      current
      DESCRIPTION "Specifies whether to clean up all ThreadLocals storage from self-tuning thread pool threads after they have finished processing each work request. By default, the self-tuning thread pool only cleans up ThreadLocal storage in its threads after an application is undeployed to avoid ClassLoader memory leak. "
      ::= { serverEntry 378  }
   
   
   serverRetryIntervalBeforeMSIMode OBJECT-TYPE
      SYNTAX      INTEGER
      MAX-ACCESS  read-only
      STATUS      current
      DESCRIPTION "Get the number of seconds between the retries to contact admin server, before starting in Managed Server Independence Mode "
      ::= { serverEntry 379  }
   
   
   serverBuzzAddress OBJECT-TYPE
      SYNTAX      OCTET STRING
      MAX-ACCESS  read-only
      STATUS      current
      DESCRIPTION "Buzz endpoint address. "
      ::= { serverEntry 380  }
   
   
   serverJMSConnectionFactoryUnmappedResRefMode OBJECT-TYPE
      SYNTAX      OCTET STRING
      MAX-ACCESS  read-only
      STATUS      current
      DESCRIPTION " Use this unmapped resource reference mode to specify the behavior of any resource reference to a Connection Factory when the resource reference does not directly specify a JNDI name by a lookup attribute, or by a mappedName attribute, or by a jndi-name in a descriptor file. If a JNDI name is specified, the resource reference either resolves to the specified object in the JNDI tree or generates a javax.naming.NameNotFoundException.    Following are the available unmapped resource reference modes:    FailSafe : In this mode, an application JMS connection factory resource reference that does not specify a JNDI name resolves to an object bound to the JNDI tree with the same name as the resource reference name if one can be found in JNDI tree. Otherwise, it throws a javax.naming.NameNotFoundException. A resource reference without a JNDI name never returns a Java EE 7 Default Connection Factory in this mode.  This mode yields pre-12.2.1 WebLogic Server behavior. This mode is Java EE compliant, but the Java EE 7 specification disallows it from being the default mode.        ReturnDefault : This policy is a Java EE compliant mode and it is the default mode. It complies with Java EE 7 while doing a best effort to try delivering FailSafe behavior when it is expected.  (a) If the resource reference name matches the local JNDI name of a configured foreign JMS provider mapping, then WebLogic Server returns the remote JNDI entry from the mapping if it can be resolved, or it throws a javax.naming.NameNotFoundException.   (b) If the resource reference does not match with a foreign JMS provider mapping, and if the resource reference name matches the name of an object that is already bound to the JNDI tree, WebLogic Server returns the JNDI tree object.   (c) If neither (a) nor (b) apply, then WebLogic Server returns 'java:comp/DefaultJMSConnectionFactory'. In addition, it adds an 'Info' message in the server log indicating that a special behavior has occurred. This log message will occur at most once per application per server boot.    "
      ::= { serverEntry 381  }
   
   
   serverBuzzEnabled OBJECT-TYPE
      SYNTAX      OCTET STRING
      MAX-ACCESS  read-only
      STATUS      current
      DESCRIPTION "Enables Buzz for sending/receiving messages with peers. Enabling this attribute increases efficiency during I/O in environments with high network throughput and should be used only when configuring a WebLogic domain for Oracle Exalogic. "
      ::= { serverEntry 382  }
   
   
   serverMaxConcurrentLongRunningRequests OBJECT-TYPE
      SYNTAX      INTEGER
      MAX-ACCESS  read-only
      STATUS      current
      DESCRIPTION "The maximum number of running long-running requests that can be submitted to all the Managed Executor Services or Managed Scheduled Executor Services in the server. "
      ::= { serverEntry 383  }
   
   
   serverNumOfRetriesBeforeMSIMode OBJECT-TYPE
      SYNTAX      INTEGER
      MAX-ACCESS  read-only
      STATUS      current
      DESCRIPTION "Get the number of retries to contact admin server, before starting in Managed Server Independence Mode "
      ::= { serverEntry 384  }
   
   
   serverIsolatePartitionThreadLocals OBJECT-TYPE
      SYNTAX      OCTET STRING
      MAX-ACCESS  read-only
      STATUS      current
      DESCRIPTION "Specified whether the server needs to ensure that threadlocals storage from self-tuning thread pool threads must be cleaned up before the threads are used for processing work requests from a different partition. This helps ensure that no threadlocals from a different partition can be retrieved from work requests while being processed by a self-tuning thread pool thread.  The different between this attribute and the eagerThreadLocalCleanup attribute is that threadlocals storage will not be cleared if the previous work request processed by the self-tuning thread pool thread was for the same partition, whereas with eagerThreadLocalCleanup set, the threadlocals storage will also be cleared in this case. "
      ::= { serverEntry 385  }
   
   
   serverClasspathServletSecureModeEnabled OBJECT-TYPE
      SYNTAX      OCTET STRING
      MAX-ACCESS  read-only
      STATUS      current
      DESCRIPTION "If secure mode is enabled, the ClasspathServlet will serve only class files from wellknown packages required for JDBC and JMS functionality. If secure mode is disabled, it represents a security hole if unchecked as the ClassPatchServlet will serve any class in the classpath and is registered by default in every Web application (including management).   If set to true, the ClasspathServlet will not be disabled by the DefaultInternalServletsDisabled value of true.  "
      ::= { serverEntry 386  }
   
   
   serverSitConfigPollingInterval OBJECT-TYPE
      SYNTAX      INTEGER
      MAX-ACCESS  read-only
      STATUS      current
      DESCRIPTION "Returns the current polling interval for finding the situational config file in the filesystem "
      ::= { serverEntry 387  }
   
   
   serverTransactionPrimaryChannelName OBJECT-TYPE
      SYNTAX      OCTET STRING
      MAX-ACCESS  read-only
      STATUS      current
      DESCRIPTION "Returns the name of the server network channel to derive the default URL used for internal JTA communication with this server. "
      ::= { serverEntry 388  }
   
   
   serverTransactionSecureChannelName OBJECT-TYPE
      SYNTAX      OCTET STRING
      MAX-ACCESS  read-only
      STATUS      current
      DESCRIPTION "Returns the name of the server network channel to derive the secure URL used for internal JTA communication with this server. "
      ::= { serverEntry 389  }
   
   
   serverTransactionPublicSecureChannelName OBJECT-TYPE
      SYNTAX      OCTET STRING
      MAX-ACCESS  read-only
      STATUS      current
      DESCRIPTION "Returns the name of the server network channel to derive the public secure URL used for internal JTA communication with this server. "
      ::= { serverEntry 390  }
   
   
   serverTransactionPublicChannelName OBJECT-TYPE
      SYNTAX      OCTET STRING
      MAX-ACCESS  read-only
      STATUS      current
      DESCRIPTION "Returns the name of the server network channel to derive the public URL used for internal JTA communication with this server. "
      ::= { serverEntry 391  }
   
   
   serverCleanupOrphanedSessionsEnabled OBJECT-TYPE
      SYNTAX      OCTET STRING
      MAX-ACCESS  read-only
      STATUS      current
      DESCRIPTION "Indicates if replication service should cleanup orphaned http and ejb sessions. Orphaned sessions are http and ejb session instances that are not referenced by the replication service. "
      ::= { serverEntry 392  }
   
   
   serverSessionReplicationOnShutdownEnabled OBJECT-TYPE
      SYNTAX      OCTET STRING
      MAX-ACCESS  read-only
      STATUS      current
      DESCRIPTION "Indicates if session replication on server shutdown is enabled. During server shutdown, any active http and ejb stateful session states will be replicated to a secondary server (if available) in the cluster. "
      ::= { serverEntry 393  }
   
   
   serverSitConfigRequired OBJECT-TYPE
      SYNTAX      OCTET STRING
      MAX-ACCESS  read-only
      STATUS      current
      DESCRIPTION "Returns whether situational config files are required and WebLogic Server should fail to boot if situational config files are not present. "
      ::= { serverEntry 394  }
   
   
   serverStartTable OBJECT-TYPE
      SYNTAX      SEQUENCE OF ServerStartEntry
      MAX-ACCESS  not-accessible
      STATUS      current
      DESCRIPTION "This bean is used to configure the attributes necessary to start up a server on a remote machine. "
      ::= { wls 735  }
      
   
   serverStartEntry OBJECT-TYPE
      SYNTAX      ServerStartEntry
      MAX-ACCESS  not-accessible
      STATUS      current
      DESCRIPTION "Entry of serverStartTable"
      INDEX { serverStartIndex}
      ::= { serverStartTable 1 }
      
   ServerStartEntry ::=
      SEQUENCE
      {
         serverStartIndex     DisplayString,
         serverStartObjectName DisplayString,
         serverStartType      DisplayString,
         serverStartName      DisplayString,
         serverStartParent    DisplayString,
         serverStartArguments DisplayString,
         serverStartBeaHome   DisplayString,
         serverStartClassPath DisplayString,
         serverStartJavaHome  DisplayString,
         serverStartRootDirectory DisplayString,
         serverStartSecurityPolicyFile DisplayString,
         serverStartUsername  DisplayString,
         serverStartJavaVendor OCTET STRING,
         serverStartMWHome    OCTET STRING,
         serverStartTags      OCTET STRING
      }
      
   
   serverStartIndex OBJECT-TYPE
      SYNTAX      DisplayString (SIZE (1..16))
      MAX-ACCESS  read-only
      STATUS      current
      DESCRIPTION "Unique value directed from ObjectName which is used as table index"
      ::= { serverStartEntry 1  }
   
   
   serverStartObjectName OBJECT-TYPE
      SYNTAX      DisplayString (SIZE (1..256))
      MAX-ACCESS  read-only
      STATUS      current
      DESCRIPTION "JMX-standard MBean name"
      ::= { serverStartEntry 5  }
   
   
   serverStartType OBJECT-TYPE
      SYNTAX      DisplayString (SIZE (1..64))
      MAX-ACCESS  read-only
      STATUS      current
      DESCRIPTION "Returns the type of the MBean. "
      ::= { serverStartEntry 10  }
   
   
   serverStartName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { serverStartEntry 15  }
   
   
   serverStartParent OBJECT-TYPE
      SYNTAX      DisplayString (SIZE (1..256))
      MAX-ACCESS  read-only
      STATUS      current
      DESCRIPTION "BEA-proprietary Parent object's identification, with syntax
      <type>:<name>"
      ::= { serverStartEntry 20  }
   
   
   serverStartArguments OBJECT-TYPE
      SYNTAX      DisplayString (SIZE (1..256))
      MAX-ACCESS  read-only
      STATUS      current
      DESCRIPTION "The arguments to use when starting this server.  These are the first arguments appended immediately after java portion of the startup command. For example, you can set Java heap memory or specify any weblogic.Server option.  This property should not be used to specify weblogic.management.username or weblogic.management.password as these values will be ignored during server startup.  Instead the username and password properties should be set. This will also enable Node Manager to properly encrypt these values on the Managed Server's machine.  Separate arguments with a space.  This value can also be specified conveniently in the nodemanager .properties file using the weblogic.startup.Arguments property. Node Manager will pass this value to a start script using the JAVA_OPTIONS environment variable.  When issuing a Java command line to start the server, Node Manager will pass the arguments as options. "
      ::= { serverStartEntry 25  }
   
   
   serverStartBeaHome OBJECT-TYPE
      SYNTAX      DisplayString (SIZE (1..256))
      MAX-ACCESS  read-only
      STATUS      current
      DESCRIPTION " The BEA home directory (path on the machine running Node Manager) to use when starting this server.  Specify the directory on the Node Manager machine under which all of Oracle's BEA products were installed. For example, c:&#92;bea. "
      ::= { serverStartEntry 30  }
   
   
   serverStartClassPath OBJECT-TYPE
      SYNTAX      DisplayString (SIZE (1..256))
      MAX-ACCESS  read-only
      STATUS      current
      DESCRIPTION "The classpath (path on the machine running Node Manager) to use when starting this server.  At a minimum you will need to specify the following values for the class path option: WL_HOME/server/lib/weblogic_sp.jar;WL_HOME/server/lib/weblogic.jar  where WL_HOME is the directory in which you installed WebLogic Server on the Node Manager machine.  The shell environment determines which character you use to separate path elements. On Windows, you typically use a semicolon (;). In a BASH shell, you typically use a colon (:).  This value can also be specified conveniently in the nodemanager .properties file using the weblogic.startup.ClassPath property. Node Manager will pass this value to a start script using the CLASSPATH environment variable.  When issuing a Java command line to start the server, Node Manager will pass -Djava.class.path. "
      ::= { serverStartEntry 35  }
   
   
   serverStartJavaHome OBJECT-TYPE
      SYNTAX      DisplayString (SIZE (1..256))
      MAX-ACCESS  read-only
      STATUS      current
      DESCRIPTION "The Java home directory (path on the machine running Node Manager) to use when starting this server.  Specify the parent directory of the JDK's bin directory. For example, c:&#92;bea&#92;jdk141.  This value can also be specified conveniently in the nodemanager .properties file using the weblogic.startup.JavaHome or property. Node Manager will pass this value to a start script using the JAVA_HOME environment variable.  When issuing a Java command line to start the server, Node Manager will use the Java executable from the specified location.  "
      ::= { serverStartEntry 40  }
   
   
   serverStartRootDirectory OBJECT-TYPE
      SYNTAX      DisplayString (SIZE (1..256))
      MAX-ACCESS  read-only
      STATUS      current
      DESCRIPTION "The directory that this server uses as its root directory. This directory must be on the computer that hosts Node Manager. If you do not specify a Root Directory value, the domain directory is used by default.  "
      ::= { serverStartEntry 45  }
   
   
   serverStartSecurityPolicyFile OBJECT-TYPE
      SYNTAX      DisplayString (SIZE (1..256))
      MAX-ACCESS  read-only
      STATUS      current
      DESCRIPTION "The security policy file (directory and filename on the machine running Node Manager) to use when starting this server.  This value can also be specified conveniently in the nodemanager .properties file using the weblogic.startup.SecurityPolicyFile property .  When Node Manager is using a start script, the security policy file will be defined in an environment variable, SECURITY_POLICY.  Additionally, when Node Manager is launching the process directly using a Java command, the security policy file will be defined with -Djava.security.policy=  "
      ::= { serverStartEntry 50  }
   
   
   serverStartUsername OBJECT-TYPE
      SYNTAX      DisplayString (SIZE (1..256))
      MAX-ACCESS  read-only
      STATUS      current
      DESCRIPTION "The user name to use when booting this server.  The Administration Console inserts the user name that you supplied when you logged in to the console. The Domain Configuration Wizard inserts the user name that you defined when you created the domain. "
      ::= { serverStartEntry 55  }
   
   
   serverStartJavaVendor OBJECT-TYPE
      SYNTAX      OCTET STRING
      MAX-ACCESS  read-only
      STATUS      current
      DESCRIPTION "The Java Vendor value to use when starting this server.   If the server is part of a cluster and configured for automatic migration across possibly different platforms with different vendors providing the JDKs, then, both JavaVendor and JavaHome should be set in the generated configuration file instead.  This value can also be specified conveniently in the nodemanager .properties file using the weblogic.startup.JavaVendor property.  Node Manager does not pass this value invoking a Java command line to start the server.  It does pass this value in the environment variable JAVA_VENDOR to the start script.  "
      ::= { serverStartEntry 56  }
   
   
   serverStartMWHome OBJECT-TYPE
      SYNTAX      OCTET STRING
      MAX-ACCESS  read-only
      STATUS      current
      DESCRIPTION " The MWHome directory (path on the machine running Node Manager) to use when starting this server.  Specify the directory on the Node Manager machine under which all of Oracle's Middleware products were installed. For example, c:&#92;bea.  This value can also be specified conveniently in the nodemanager .properties file using the weblogic.startup.MWHome property.  Node Manager does not pass this value to start scripts. It does specify -Dbea.home when invoking a Java command line to start the server. "
      ::= { serverStartEntry 57  }
   
   
   serverStartTags OBJECT-TYPE
      SYNTAX      OCTET STRING
      MAX-ACCESS  read-only
      STATUS      current
      DESCRIPTION "Return all tags on this Configuration MBean "
      ::= { serverStartEntry 58  }
   
   
   snmpAgentTable OBJECT-TYPE
      SYNTAX      SEQUENCE OF SnmpAgentEntry
      MAX-ACCESS  not-accessible
      STATUS      current
      DESCRIPTION "This singleton MBean represents an SNMP agent that is scoped to a WebLogic Server domain. This MBean is provided to support domains that were created with WebLogic Server release 9.2 and earlier. For new domains, create an instance of {@link SNMPAgentDeploymentMBean} and target it to the domain's Administration Server. "
      ::= { wls 740  }
      
   
   snmpAgentEntry OBJECT-TYPE
      SYNTAX      SnmpAgentEntry
      MAX-ACCESS  not-accessible
      STATUS      current
      DESCRIPTION "Entry of snmpAgentTable"
      INDEX { snmpAgentIndex}
      ::= { snmpAgentTable 1 }
      
   SnmpAgentEntry ::=
      SEQUENCE
      {
         snmpAgentIndex       DisplayString,
         snmpAgentObjectName  DisplayString,
         snmpAgentType        DisplayString,
         snmpAgentName        DisplayString,
         snmpAgentParent      DisplayString,
         snmpAgentCommunityPrefix DisplayString,
         snmpAgentDebugLevel  INTEGER,
         snmpAgentMibDataRefreshInterval INTEGER,
         snmpAgentServerStatusCheckIntervalFactor INTEGER,
         snmpAgentSNMPPort    INTEGER,
         snmpAgentSNMPTrapVersion INTEGER,
         snmpAgentEnabled     INTEGER,
         snmpAgentSendAutomaticTrapsEnabled INTEGER,
         snmpAgentMaxInformRetryCount INTEGER,
         snmpAgentInformRetryInterval INTEGER,
         snmpAgentMasterAgentXPort INTEGER,
         snmpAgentCommunityBasedAccessEnabled OCTET STRING,
         snmpAgentSNMPAccessForUserMBeansEnabled OCTET STRING,
         snmpAgentInformEnabled OCTET STRING,
         snmpAgentPrivacyProtocol OCTET STRING,
         snmpAgentSNMPEngineId OCTET STRING,
         snmpAgentAuthenticationProtocol OCTET STRING,
         snmpAgentLocalizedKeyCacheInvalidationInterval Counter64,
         snmpAgentTags        OCTET STRING,
         snmpAgentListenAddress OCTET STRING
      }
      
   
   snmpAgentIndex OBJECT-TYPE
      SYNTAX      DisplayString (SIZE (1..16))
      MAX-ACCESS  read-only
      STATUS      current
      DESCRIPTION "Unique value directed from ObjectName which is used as table index"
      ::= { snmpAgentEntry 1  }
   
   
   snmpAgentObjectName OBJECT-TYPE
      SYNTAX      DisplayString (SIZE (1..256))
      MAX-ACCESS  read-only
      STATUS      current
      DESCRIPTION "JMX-standard MBean name"
      ::= { snmpAgentEntry 5  }
   
   
   snmpAgentType OBJECT-TYPE
      SYNTAX      DisplayString (SIZE (1..64))
      MAX-ACCESS  read-only
      STATUS      current
      DESCRIPTION "Returns the type of the MBean. "
      ::= { snmpAgentEntry 10  }
   
   
   snmpAgentName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { snmpAgentEntry 15  }
   
   
   snmpAgentParent OBJECT-TYPE
      SYNTAX      DisplayString (SIZE (1..256))
      MAX-ACCESS  read-only
      STATUS      current
      DESCRIPTION "BEA-proprietary Parent object's identification, with syntax
      <type>:<name>"
      ::= { snmpAgentEntry 20  }
   
   
   snmpAgentCommunityPrefix OBJECT-TYPE
      SYNTAX      DisplayString
      MAX-ACCESS  read-only
      STATUS      current
      DESCRIPTION "The password (community name) that you want this SNMP agent to use to secure SNMPv1 or v2 communication with SNMP managers. Requires you to enable community based access for this agent.  SNMPv3 does not use community names. Instead, it encrypts user names and passwords in its PDUs.   When you use SNMPv1 or v2, there are two community names that are needed when the WebLogic SNMP agent and SNMP managers interact:    The name that you specify in this community prefix. All SNMP managers must send this name when connecting to this SNMP agent.    The community name that the SNMP manager defines. The SNMP agent must send this name when connecting to the manager. (You supply this community name when you configure a trap destination.)    In addition to using the community prefix as a password, an SNMP agent on an Administration Server uses the prefix to qualify requests from SNMP managers. Because the Administration Server can access data for all WebLogic Server instances in a domain, a request that specifies only an attribute name is potentially ambiguous. For example, the attribute serverUptime exists for each WebLogic Server instance in a domain. To clarify requests that you send to SNMP agents on Administration Servers, use the community prefix as follows:    To request the value of an attribute on a specific Managed Server, when you send a request from an SNMP manager, append the name of the server instance to the community prefix: community_prefix@server_name.    To request the value of an attribute for all server instances in a domain, send a community name with the following form: community_prefix    To secure access to the values of the WebLogic attributes when using the SNMPv1 or v2 protocols, it is recommended that you set community prefix to a value other than public or private.  You cannot specify a null (empty) value for the community prefix when SNMP agent is enabled. If you do not want this agent to receive SNMPv1 or v2 requests, disable community based access. "
      ::= { snmpAgentEntry 21  }
   
   
   snmpAgentDebugLevel OBJECT-TYPE
      SYNTAX      INTEGER
      MAX-ACCESS  read-only
      STATUS      current
      DESCRIPTION "The minimum severity of debug messages that this SNMP agent generates.  The SNMP agent writes all debug messages to standard out; they are not written to the WebLogic Server log files. Debug messages provide a detailed description of the SNMP agent's actions. For example, the agent outputs a noncritical message each time it generates a notification.  Valid values are:   0  No debug messages.   1  Fatal messages only.   2  Critical and fatal messages.   3  Non-critical, critical, and, fatal messages.   "
      ::= { snmpAgentEntry 22  }
   
   
   snmpAgentMibDataRefreshInterval OBJECT-TYPE
      SYNTAX      INTEGER
      MAX-ACCESS  read-only
      STATUS      current
      DESCRIPTION "The minimum number of seconds that this SNMP agent caches OIDs before checking if new ones have been added to the Management Information Base (MIB).  A MIB is a database of all objects that can be managed through SNMP. When you create a new WebLogic Server resource, the SNMP agent assigns a unique OID to the resource and adds it to the MIB. For example, when you create a new server, the SNMP agent adds an OID to the MIB.  This attribute is not used by the SNMP Agent anymore. The SNMP Agent retrieves internal notifications about MBean registrations in the WLS MBeanServers. "
      ::= { snmpAgentEntry 23  }
   
   
   snmpAgentServerStatusCheckIntervalFactor OBJECT-TYPE
      SYNTAX      INTEGER
      MAX-ACCESS  read-only
      STATUS      current
      DESCRIPTION "The multiplier used to calculate the interval at which this SNMP agent checks for newly started or shut down server instances.  You can enable the SNMP agent to automatically generate serverStartup and serverShutdown notifications when servers start or shut down. See {@link SNMPAgentMBean#isSendAutomaticTrapsEnabled}.  This status check value is multiplied by the MIB Data Refresh Interval to determine the interval:  interval = n * MibDataRefreshInterval  The SNMP Agent uses internal notifications to update itself when a server is restarted so there is no need to poll the server for their status.  For the most frequent interval, specify 1 as the multiplier value. "
      ::= { snmpAgentEntry 24  }
   
   
   snmpAgentSNMPPort OBJECT-TYPE
      SYNTAX      INTEGER
      MAX-ACCESS  read-only
      STATUS      current
      DESCRIPTION "The port on which you want this SNMP agent to listen for incoming requests from SNMP managers that use the UDP protocol.  SNMP managers can use this port to ping the SNMP agent and request the status of specific attributes.  If you target this SNMP agent to multiple server instances, and if two or more servers are running on the same computer, WebLogic Server will automatically increment this UDP port value by 1 for each agent. WebLogic Server never assigns port 162 because it is the default port that an agent uses to send notifications. In addition, if any port is already in use, WebLogic Server skips the port and assigns the next available port. For example, if you use the default value of this attribute and then target this agent to ManagedServer1 and ManagedServer2, and if both servers are running on the same computer, then the agent on ManagedServer1 will listen on UDP port 161 and the agent on ManagedServer2 will listen on UDP port 163. The incremented port number is not persisted in the domain's configuration; when WebLogic Server increments port numbers, it does so in the order in which servers are started on the same computer. If WebLogic Server re-assigns the UDP port for an SNMP agent, look in the agent's SNMPAgentRuntimeMBean to see the agent's runtime UDP port. SNMP agents can also communicate through the host server's TCP listen port (7001 by default) or through a TCP port that is configured by a custom network channel. "
      ::= { snmpAgentEntry 25  }
   
   
   snmpAgentSNMPTrapVersion OBJECT-TYPE
      SYNTAX      INTEGER
      MAX-ACCESS  read-only
      STATUS      current
      DESCRIPTION "The SNMP notification version that this SNMP agent generates. "
      ::= { snmpAgentEntry 26  }
   
   
   snmpAgentEnabled OBJECT-TYPE
      SYNTAX      INTEGER
      MAX-ACCESS  read-only
      STATUS      current
      DESCRIPTION "Specifies whether this SNMP agent is enabled. "
      ::= { snmpAgentEntry 27  }
   
   
   snmpAgentSendAutomaticTrapsEnabled OBJECT-TYPE
      SYNTAX      INTEGER
      MAX-ACCESS  read-only
      STATUS      current
      DESCRIPTION "Specifies whether this SNMP agent sends automatically generated notifications to SNMP managers.  The SNMP agent generates automatic notifications when any of the following events occur:   The WebLogic Server instance that is hosting the SNMP agent starts. This type of notification (coldStart) has no variable bindings.  A server instance starts or stops. An SNMP agent on a Managed Server generates these notifications only when its host Managed Server starts or stops. An SNMP agent on an Administration Server generates these notifications when any server in the domain starts or stops. These notification types (serverStart and serverShutdown) contain variable bindings to identify the server that started or stopped and the time at which the notification was generated.   "
      ::= { snmpAgentEntry 28  }
   
   
   snmpAgentMaxInformRetryCount OBJECT-TYPE
      SYNTAX      INTEGER
      MAX-ACCESS  read-only
      STATUS      current
      DESCRIPTION "The maximum number of times that this SNMP agent will resend INFORM notifications for which it has not received a response. "
      ::= { snmpAgentEntry 29  }
   
   
   snmpAgentInformRetryInterval OBJECT-TYPE
      SYNTAX      INTEGER
      MAX-ACCESS  read-only
      STATUS      current
      DESCRIPTION "The number of milliseconds that this SNMP agent will wait for a response to an INFORM notification. If the agent does not receive a response within the specified interval, it will resend the notification. "
      ::= { snmpAgentEntry 30  }
   
   
   snmpAgentMasterAgentXPort OBJECT-TYPE
      SYNTAX      INTEGER
      MAX-ACCESS  read-only
      STATUS      current
      DESCRIPTION "The port that this SNMP agent uses to communicate with its subagents. The agent uses subagents to provide access to custom MBeans (MBeans that you create and register) and to other software components. WebLogic Server SNMP agents do not enable users to register their own subagents. "
      ::= { snmpAgentEntry 31  }
   
   
   snmpAgentCommunityBasedAccessEnabled OBJECT-TYPE
      SYNTAX      OCTET STRING
      MAX-ACCESS  read-only
      STATUS      current
      DESCRIPTION "Specifies whether this SNMP agent supports SNMPv1 and v2. SNMPv1 and v2 use community strings for authentication. If you disable community strings for this SNMP agent, the agent will process only SNMPv3 requests. If an SNMP manager sends a v1 or v2 message, the agent discards the message and returns an error code to the manager. "
      ::= { snmpAgentEntry 32  }
   
   
   snmpAgentSNMPAccessForUserMBeansEnabled OBJECT-TYPE
      SYNTAX      OCTET STRING
      MAX-ACCESS  read-only
      STATUS      current
      DESCRIPTION "Configures this SNMP agent to provide read-only access to MBean types that you have created and registered (custom MBeans). If you enable this access, when you register a custom MBean in a WebLogic Server MBeanServer, this SNMP agent dynamically updates a runtime MIB module that WebLogic Server maintains for custom MBeans.  For each custom MBean type, WebLogic Server adds a table to the MIB module. For each instance of the custom MBean, it adds a table row. While WebLogic Server does not persist the MIB as a file or other data structure, the OIDs in the MIB remain constant across server sessions. The MIB module for custom MBeans is managed by a subAgent. Its master agent is this WebLogic Server SNMP agent and it communicates with the master agent through the AgentX port. "
      ::= { snmpAgentEntry 33  }
   
   
   snmpAgentInformEnabled OBJECT-TYPE
      SYNTAX      OCTET STRING
      MAX-ACCESS  read-only
      STATUS      current
      DESCRIPTION "Configures this SNMP agent to send notifications as an INFORM instead of a TRAP. Requires you to specify the agent's SNMPTrapVersion as SNMPv2 or SNMPv3. When an agent sends an INFORM notification, it waits for a confirmation response from the SNMP manager. If it does not receive a response, it resends the INFORM notification. "
      ::= { snmpAgentEntry 34  }
   
   
   snmpAgentPrivacyProtocol OBJECT-TYPE
      SYNTAX      OCTET STRING
      MAX-ACCESS  read-only
      STATUS      current
      DESCRIPTION "The protocol that this SNMP agent uses to encrypt and unencrypt messages. Applicable only with SNMPv3. Requires you to also use an authentication protocol. To use this protocol when sending responses or notifications, you must also configure the security level of your trap destinations. If you do not choose a privacy protocol, then communication between this agent and managers can be viewed (but not altered) by unauthorized users. "
      ::= { snmpAgentEntry 35  }
   
   
   snmpAgentSNMPEngineId OBJECT-TYPE
      SYNTAX      OCTET STRING
      MAX-ACCESS  read-only
      STATUS      current
      DESCRIPTION "An identifier for this SNMP agent that is unique amongst all other SNMP agents in the current WebLogic Server domain. If you use SNMPv3 to send messages to this SNMP agent, you must specify the SNMP engine ID when you configure the SNMP manager. For an SNMP agent on an Administration Server, the default value is the name of the WebLogic Server domain. For an agent on a Managed Server, the default is the name of the server. "
      ::= { snmpAgentEntry 36  }
   
   
   snmpAgentAuthenticationProtocol OBJECT-TYPE
      SYNTAX      OCTET STRING
      MAX-ACCESS  read-only
      STATUS      current
      DESCRIPTION "The protocol that this SNMP agent uses to ensure that only authorized users can request or receive information about your WebLogic Server domain. Applicable only with SNMPv3. The protocol also ensures message integrity and prevents masquerading and reordered, delayed, or replayed messages. To use this protocol when receiving requests from SNMP managers, you must configure credential mapping in the WebLogic Server security realm. To use this protocol when sending responses or notifications, you must configure the security level of your trap destinations. If you do not choose an authentication protocol, then the SNMP agent does not authenticate incoming SNMPv3 requests; anyone can use SNMPv3 to retrieve information about your WebLogic Server domain. "
      ::= { snmpAgentEntry 37  }
   
   
   snmpAgentLocalizedKeyCacheInvalidationInterval OBJECT-TYPE
      SYNTAX      Counter64
      MAX-ACCESS  read-only
      STATUS      current
      DESCRIPTION "The number of milliseconds after which WebLogic Server invalidates its cache of SNMP security keys. Setting a high value creates a risk that users whose credentials have been removed can still access SNMP data. An SNMP security key is an encrypted version of an SNMP agent's engine ID and an authentication password or privacy password. WebLogic Server generates one security key for each entry that you create in the SNMP credential map. When a WebLogic Server SNMP agent receives an SNMPv3 request, it compares the key that is in the request with its WebLogic Server keys. If it finds a match, it processes the request. The SNMP agent also encodes these keys in its responses and notifications. (You configure which keys are encoded when you create a trap destination.) Instead of regenerating the keys for each SNMPv3 communication, WebLogic Server caches the keys. To make sure that the cache contains the latest set of SNMP credentials, WebLogic Server periodically invalidates the cache. After the cache is invalidated, the next time an SNMP agent requests credentials, WebLogic Server regenerates the cache. Note that making a change to the credential map does not automatically update the cache. Instead, the cache is updated only after it has been invalidated. For example, if you update a privacy password in an existing entry in the SNMP credential map, the SNMP agent is not aware of the new password until the key cache is invalidated and regenerated. An SNMP user with the old security password can still access WebLogic Server data until the cache is invalidated. You can invalidate a key immediately instead of waiting for this invalidation interval to expire.  "
      ::= { snmpAgentEntry 38  }
   
   
   snmpAgentTags OBJECT-TYPE
      SYNTAX      OCTET STRING
      MAX-ACCESS  read-only
      STATUS      current
      DESCRIPTION "Return all tags on this Configuration MBean "
      ::= { snmpAgentEntry 39  }
   
   
   snmpAgentListenAddress OBJECT-TYPE
      SYNTAX      OCTET STRING
      MAX-ACCESS  read-only
      STATUS      current
      DESCRIPTION "The listen address on which you want this SNMP agent to listen for incoming requests from SNMP managers that use the UDP protocol.  If not specified the Server's ListenAddress is used as the ListenAddress for the SNMPAgent. "
      ::= { snmpAgentEntry 40  }
   
   
   sslTable OBJECT-TYPE
      SYNTAX      SEQUENCE OF SslEntry
      MAX-ACCESS  not-accessible
      STATUS      current
      DESCRIPTION "This MBean represents the configuration of the SSL protocol. "
      ::= { wls 745  }
      
   
   sslEntry OBJECT-TYPE
      SYNTAX      SslEntry
      MAX-ACCESS  not-accessible
      STATUS      current
      DESCRIPTION "Entry of sslTable"
      INDEX { sslIndex}
      ::= { sslTable 1 }
      
   SslEntry ::=
      SEQUENCE
      {
         sslIndex             DisplayString,
         sslObjectName        DisplayString,
         sslType              DisplayString,
         sslName              DisplayString,
         sslParent            DisplayString,
         sslExportKeyLifespan INTEGER,
         sslHostnameVerifier  DisplayString,
         sslIdentityAndTrustLocations DisplayString,
         sslListenPort        INTEGER,
         sslLoginTimeoutMillis INTEGER,
         sslServerCertificateChainFileName DisplayString,
         sslServerCertificateFileName DisplayString,
         sslServerPrivateKeyAlias DisplayString,
         sslClientCertificateEnforced INTEGER,
         sslEnabled           INTEGER,
         sslHostnameVerificationIgnored INTEGER,
         sslSSLRejectionLoggingEnabled INTEGER,
         sslTwoWaySSLEnabled  INTEGER,
         sslOutboundCertificateValidation OCTET STRING,
         sslInboundCertificateValidation OCTET STRING,
         sslUseServerCerts    OCTET STRING,
         sslAllowUnencryptedNullCipher OCTET STRING,
         sslTrustedCAFileName OCTET STRING,
         sslServerKeyFileName OCTET STRING,
         sslCiphersuites      OCTET STRING,
         sslJSSEEnabled       OCTET STRING,
         sslOutboundPrivateKeyAlias OCTET STRING,
         sslUseClientCertForOutbound OCTET STRING,
         sslClientCertAlias   OCTET STRING,
         sslAcceptKSSDemoCertsEnabled OCTET STRING,
         sslTags              OCTET STRING,
         sslSSLv2HelloEnabled OCTET STRING,
         sslMinimumTLSProtocolVersion OCTET STRING,
         sslClientInitSecureRenegotiationAccepted OCTET STRING
      }
      
   
   sslIndex OBJECT-TYPE
      SYNTAX      DisplayString (SIZE (1..16))
      MAX-ACCESS  read-only
      STATUS      current
      DESCRIPTION "Unique value directed from ObjectName which is used as table index"
      ::= { sslEntry 1  }
   
   
   sslObjectName OBJECT-TYPE
      SYNTAX      DisplayString (SIZE (1..256))
      MAX-ACCESS  read-only
      STATUS      current
      DESCRIPTION "JMX-standard MBean name"
      ::= { sslEntry 5  }
   
   
   sslType OBJECT-TYPE
      SYNTAX      DisplayString (SIZE (1..64))
      MAX-ACCESS  read-only
      STATUS      current
      DESCRIPTION "Returns the type of the MBean. "
      ::= { sslEntry 10  }
   
   
   sslName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { sslEntry 15  }
   
   
   sslParent OBJECT-TYPE
      SYNTAX      DisplayString (SIZE (1..256))
      MAX-ACCESS  read-only
      STATUS      current
      DESCRIPTION "BEA-proprietary Parent object's identification, with syntax
      <type>:<name>"
      ::= { sslEntry 20  }
   
   
   sslExportKeyLifespan OBJECT-TYPE
      SYNTAX      INTEGER
      MAX-ACCESS  read-only
      STATUS      current
      DESCRIPTION "Indicates the number of times WebLogic Server can use an exportable key between a domestic server and an exportable client before generating a new key. The more secure you want WebLogic Server to be, the fewer times the key should be used before generating a new key. "
      ::= { sslEntry 23  }
   
   
   sslHostnameVerifier OBJECT-TYPE
      SYNTAX      DisplayString
      MAX-ACCESS  read-only
      STATUS      current
      DESCRIPTION "The name of the class that implements the weblogic.security.SSL.HostnameVerifier interface.  This class verifies whether the connection to the host with the hostname from URL should be allowed. The class is used to prevent man-in-the-middle attacks. The weblogic.security.SSL.HostnameVerifier has a verify() method that WebLogic Server calls on the client during the SSL handshake. "
      ::= { sslEntry 24  }
   
   
   sslIdentityAndTrustLocations OBJECT-TYPE
      SYNTAX      DisplayString
      MAX-ACCESS  read-only
      STATUS      current
      DESCRIPTION "Indicates where SSL should find the server's identity (certificate and private key) as well as the server's trust (trusted CAs).    If set to KEYSTORES, then SSL retrieves the identity and trust from the server's keystores (that are configured on the Server).    If set to FILES_OR_KEYSTORE_PROVIDERS, then SSL first looks in the deprecated KeyStore providers for the identity and trust. If not found, then it looks in the flat files indicated by the SSL Trusted CA File Name, Server Certificate File Name, and Server Key File Name attributes.    Domains created in WebLogic Server version 8.1 or later, default to KEYSTORES. Domains created before WebLogic Server version 8.1, default to FILES_OR_KEYSTORE_PROVIDERS. "
      ::= { sslEntry 25  }
   
   
   sslListenPort OBJECT-TYPE
      SYNTAX      INTEGER
      MAX-ACCESS  read-only
      STATUS      current
      DESCRIPTION "The TCP/IP port at which this server listens for SSL connection requests. "
      ::= { sslEntry 26  }
   
   
   sslLoginTimeoutMillis OBJECT-TYPE
      SYNTAX      INTEGER
      MAX-ACCESS  read-only
      STATUS      current
      DESCRIPTION "Specifies the number of milliseconds that WebLogic Server waits for an SSL connection before timing out. SSL connections take longer to negotiate than regular connections.  If clients are connecting over the Internet, raise the default number to accommodate additional network latency. "
      ::= { sslEntry 27  }
   
   
   sslServerCertificateChainFileName OBJECT-TYPE
      SYNTAX      DisplayString
      MAX-ACCESS  read-only
      STATUS      current
      DESCRIPTION "The full directory location and name of the file containing an ordered list of certificate authorities trusted by WebLogic Server.  The .pem file extension indicates that method that should be used to read the file. Note that as of WebLogic Server version 7.0, the digital certificate for WebLogic Server should not be stored in a file. "
      ::= { sslEntry 28  }
   
   
   sslServerCertificateFileName OBJECT-TYPE
      SYNTAX      DisplayString
      MAX-ACCESS  read-only
      STATUS      current
      DESCRIPTION "The full directory location of the digital certificate file (.der or .pem) for the server.  The pathname should either be absolute or relative to the directory from which the server is booted. This field provides backward compatibility for security configurations that stored digital certificates in files.  The file extension ( .der or .pem) tells WebLogic Server how to read the contents of the file. "
      ::= { sslEntry 29  }
   
   
   sslServerPrivateKeyAlias OBJECT-TYPE
      SYNTAX      DisplayString
      MAX-ACCESS  read-only
      STATUS      current
      DESCRIPTION "The string alias used to store and retrieve the server's private key in the keystore. This private key is associated with the server's digital certificate. "
      ::= { sslEntry 30  }
   
   
   sslClientCertificateEnforced OBJECT-TYPE
      SYNTAX      INTEGER
      MAX-ACCESS  read-only
      STATUS      current
      DESCRIPTION "Indicates whether or not clients must present digital certificates from a trusted certificate authority to WebLogic Server. "
      ::= { sslEntry 31  }
   
   
   sslEnabled OBJECT-TYPE
      SYNTAX      INTEGER
      MAX-ACCESS  read-only
      STATUS      current
      DESCRIPTION "Indicates whether the server can be reached through the default SSL listen port.  If the administration port is enabled for the WebLogic Server domain, then administrative traffic travels over the administration port and application traffic travels over the Listen Port and SSL Listen Port. If the administration port is disabled, then all traffic travels over the Listen Port and SSL Listen Port. "
      ::= { sslEntry 32  }
   
   
   sslHostnameVerificationIgnored OBJECT-TYPE
      SYNTAX      INTEGER
      MAX-ACCESS  read-only
      STATUS      current
      DESCRIPTION "Specifies whether to ignore the installed implementation of the weblogic.security.SSL.HostnameVerifier interface (when this server is acting as a client to another application server). "
      ::= { sslEntry 33  }
   
   
   sslSSLRejectionLoggingEnabled OBJECT-TYPE
      SYNTAX      INTEGER
      MAX-ACCESS  read-only
      STATUS      current
      DESCRIPTION "Indicates whether warning messages are logged in the server log when SSL connections are rejected. "
      ::= { sslEntry 35  }
   
   
   sslTwoWaySSLEnabled OBJECT-TYPE
      SYNTAX      INTEGER
      MAX-ACCESS  read-only
      STATUS      current
      DESCRIPTION "The form of SSL that should be used.  By default, WebLogic Server is configured to use one-way SSL (implied by the Client Certs Not Requested value). Selecting Client Certs Requested But Not Enforced enables two-way SSL. With this option, the server requests a certificate from the client, but the connection continues if the client does not present a certificate. Selecting Client Certs Requested And Enforced also enables two-way SSL and requires a client to present a certificate. However, if a certificate is not presented, the SSL connection is terminated. "
      ::= { sslEntry 36  }
   
   
   sslOutboundCertificateValidation OBJECT-TYPE
      SYNTAX      OCTET STRING
      MAX-ACCESS  read-only
      STATUS      current
      DESCRIPTION "Indicates the server certificate validation rules for outbound SSL.  This attribute always applies to outbound SSL that is part of WebLogic Server (that is, an Administration Server talking to the Node Manager). It does not apply to application code in the server that is using outbound SSL unless the application code uses a weblogic.security.SSL.ServerTrustManager that is configured to use outbound SSL validation. "
      ::= { sslEntry 37  }
   
   
   sslInboundCertificateValidation OBJECT-TYPE
      SYNTAX      OCTET STRING
      MAX-ACCESS  read-only
      STATUS      current
      DESCRIPTION "Indicates the client certificate validation rules for inbound SSL.  This attribute only applies to ports and network channels using 2-way SSL. "
      ::= { sslEntry 38  }
   
   
   sslUseServerCerts OBJECT-TYPE
      SYNTAX      OCTET STRING
      MAX-ACCESS  read-only
      STATUS      current
      DESCRIPTION "Sets whether the client should use the server certificates/key as the client identity when initiating an outbound connection over https. "
      ::= { sslEntry 40  }
   
   
   sslAllowUnencryptedNullCipher OBJECT-TYPE
      SYNTAX      OCTET STRING
      MAX-ACCESS  read-only
      STATUS      current
      DESCRIPTION "Test if the AllowUnEncryptedNullCipher is enabled see setAllowUnencryptedNullCipher(boolean enable) for the NullCipher feature. "
      ::= { sslEntry 41  }
   
   
   sslTrustedCAFileName OBJECT-TYPE
      SYNTAX      OCTET STRING
      MAX-ACCESS  read-only
      STATUS      current
      DESCRIPTION "The full directory location of the file that specifies the certificate authorities trusted by the server.  The pathname should either be absolute or relative to the directory from which the server is booted. This field provides backward compatibility for security configurations that store trusted certificate authorities in files.  The file specified in this attribute can contain a single digital certificate or multiple digital certificates. The file extension ( .der or .pem) tells WebLogic Server how to read the contents of the file. "
      ::= { sslEntry 42  }
   
   
   sslServerKeyFileName OBJECT-TYPE
      SYNTAX      OCTET STRING
      MAX-ACCESS  read-only
      STATUS      current
      DESCRIPTION "The full directory location of the private key file (.der or .pem) for the server.  The pathname should either be absolute or relative to the directory from which the server is booted. This field provides backward compatibility for security configurations that store private keys in files. For a more secure deployment, Oracle recommends saving private keys in keystores.  The file extension (.der or .pem) indicates the method that should be used to read the file. "
      ::= { sslEntry 44  }
   
   
   sslCiphersuites OBJECT-TYPE
      SYNTAX      OCTET STRING
      MAX-ACCESS  read-only
      STATUS      current
      DESCRIPTION "Indicates the cipher suites being used on a particular WebLogic Server.  The strongest negotiated cipher suite is chosen during the SSL handshake. The set of cipher suites used by default by JSEE depends on the specific JDK version with which WebLogic Server is configured.  For a list of possible values, see Cipher Suites. "
      ::= { sslEntry 45  }
   
   
   sslJSSEEnabled OBJECT-TYPE
      SYNTAX      OCTET STRING
      MAX-ACCESS  read-only
      STATUS      current
      DESCRIPTION "Determines whether the SSL implementation in Weblogic Server is JSSE based. "
      ::= { sslEntry 46  }
   
   
   sslOutboundPrivateKeyAlias OBJECT-TYPE
      SYNTAX      OCTET STRING
      MAX-ACCESS  read-only
      STATUS      current
      DESCRIPTION "The string alias used to store and retrieve the outbound private key in the keystore. This private key is associated with either a server or a client digital certificate. This attribute value is derived from other settings and cannot be physically set.  The returned value is determined as follows:  If the {@link #isUseClientCertForOutbound} returns true, the value from {@link #getClientCertAlias} is returned.  Otherwise, the value from {@link #getServerPrivateKeyAlias} is returned.  "
      ::= { sslEntry 48  }
   
   
   sslUseClientCertForOutbound OBJECT-TYPE
      SYNTAX      OCTET STRING
      MAX-ACCESS  read-only
      STATUS      current
      DESCRIPTION "Determines whether to use the configured client SSL certificate as identity for outbound SSL connections.  Note that to use a client SSL certificate, one must be specified in {@link #setClientCertAlias}. "
      ::= { sslEntry 49  }
   
   
   sslClientCertAlias OBJECT-TYPE
      SYNTAX      OCTET STRING
      MAX-ACCESS  read-only
      STATUS      current
      DESCRIPTION "Determines the alias of the client SSL certificate to be used as identity for outbound SSL connections. The certificate is assumed to be stored in the server configured keystore.  Note that to use the client SSL certificate, {@link #setUseClientCertForOutbound} must be enabled. "
      ::= { sslEntry 50  }
   
   
   sslAcceptKSSDemoCertsEnabled OBJECT-TYPE
      SYNTAX      OCTET STRING
      MAX-ACCESS  read-only
      STATUS      current
      DESCRIPTION " "
      ::= { sslEntry 51  }
   
   
   sslTags OBJECT-TYPE
      SYNTAX      OCTET STRING
      MAX-ACCESS  read-only
      STATUS      current
      DESCRIPTION "Return all tags on this Configuration MBean "
      ::= { sslEntry 52  }
   
   
   sslSSLv2HelloEnabled OBJECT-TYPE
      SYNTAX      OCTET STRING
      MAX-ACCESS  read-only
      STATUS      current
      DESCRIPTION "Indicate whether SSLv2Hello is enabled "
      ::= { sslEntry 53  }
   
   
   sslMinimumTLSProtocolVersion OBJECT-TYPE
      SYNTAX      OCTET STRING
      MAX-ACCESS  read-only
      STATUS      current
      DESCRIPTION "Get the minimum SSL/TLS protocol version currently configured. "
      ::= { sslEntry 54  }
   
   
   sslClientInitSecureRenegotiationAccepted OBJECT-TYPE
      SYNTAX      OCTET STRING
      MAX-ACCESS  read-only
      STATUS      current
      DESCRIPTION "Indicate whether TLS client initiated secure renegotiation is accepted. "
      ::= { sslEntry 55  }
   
   
   startupClassTable OBJECT-TYPE
      SYNTAX      SEQUENCE OF StartupClassEntry
      MAX-ACCESS  not-accessible
      STATUS      current
      DESCRIPTION "Provides methods that configure startup classes. A startup class is a Java program that is automatically loaded and executed when a WebLogic Server instance is started or restarted.  By default, startup classes are loaded and executed after all other server subsystems have initialized and after the server deploys modules. For any startup class, you can override the default and specify that the server loads and executes it and before it deploys JDBC connection pools and before it deploys Web applications and EJBs. "
      ::= { wls 750  }
      
   
   startupClassEntry OBJECT-TYPE
      SYNTAX      StartupClassEntry
      MAX-ACCESS  not-accessible
      STATUS      current
      DESCRIPTION "Entry of startupClassTable"
      INDEX { startupClassIndex}
      ::= { startupClassTable 1 }
      
   StartupClassEntry ::=
      SEQUENCE
      {
         startupClassIndex    DisplayString,
         startupClassObjectName DisplayString,
         startupClassType     DisplayString,
         startupClassName     DisplayString,
         startupClassParent   DisplayString,
         startupClassFailureIsFatal INTEGER,
         startupClassDeploymentOrder INTEGER,
         startupClassLoadBeforeAppDeployments OCTET STRING,
         startupClassArguments OCTET STRING,
         startupClassClassName OCTET STRING,
         startupClassLoadBeforeAppActivation OCTET STRING,
         startupClassLoadAfterAppsRunning OCTET STRING,
         startupClassTags     OCTET STRING
      }
      
   
   startupClassIndex OBJECT-TYPE
      SYNTAX      DisplayString (SIZE (1..16))
      MAX-ACCESS  read-only
      STATUS      current
      DESCRIPTION "Unique value directed from ObjectName which is used as table index"
      ::= { startupClassEntry 1  }
   
   
   startupClassObjectName OBJECT-TYPE
      SYNTAX      DisplayString (SIZE (1..256))
      MAX-ACCESS  read-only
      STATUS      current
      DESCRIPTION "JMX-standard MBean name"
      ::= { startupClassEntry 5  }
   
   
   startupClassType OBJECT-TYPE
      SYNTAX      DisplayString (SIZE (1..64))
      MAX-ACCESS  read-only
      STATUS      current
      DESCRIPTION "Returns the type of the MBean. "
      ::= { startupClassEntry 10  }
   
   
   startupClassName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { startupClassEntry 15  }
   
   
   startupClassParent OBJECT-TYPE
      SYNTAX      DisplayString (SIZE (1..256))
      MAX-ACCESS  read-only
      STATUS      current
      DESCRIPTION "BEA-proprietary Parent object's identification, with syntax
      <type>:<name>"
      ::= { startupClassEntry 20  }
   
   
   startupClassFailureIsFatal OBJECT-TYPE
      SYNTAX      INTEGER
                  {
                     true(1),
                     false(2)
                  }
      
      MAX-ACCESS  read-only
      STATUS      current
      DESCRIPTION "Specifies whether a failure in this startup class prevents the targeted server(s) from starting.  If you specify that failure is not fatal, if the startup class fails, the server continues its startup process. "
      ::= { startupClassEntry 25  }
   
   
   startupClassDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { startupClassEntry 26  }
   
   
   startupClassLoadBeforeAppDeployments OBJECT-TYPE
      SYNTAX      OCTET STRING
      MAX-ACCESS  read-only
      STATUS      current
      DESCRIPTION "Specifies whether the targeted servers load and run this startup class before activating JMS and JDBC services and before starting deployment for applications and EJBs.  If you enable this feature for a startup class, a server loads and runs the startup class before the deployment prepare phase. At this point, JMS and JDBC services are not yet available. (Deployment for applications and EJBs consists of three phases: prepare, admin and activate.)  If you do not enable this feature, LoadBeforeAppActivation or LoadAfterAppsRunning, a server instance loads startup classes when applications go to the admin state. "
      ::= { startupClassEntry 27  }
   
   
   startupClassArguments OBJECT-TYPE
      SYNTAX      OCTET STRING
      MAX-ACCESS  read-only
      STATUS      current
      DESCRIPTION "Arguments that a server uses to initialize a class.  Separate multiple arguments with a comma. For example:  first=MyFirstName,last=MyLastName "
      ::= { startupClassEntry 28  }
   
   
   startupClassClassName OBJECT-TYPE
      SYNTAX      OCTET STRING
      MAX-ACCESS  read-only
      STATUS      current
      DESCRIPTION "The fully qualified name of a class to load and run. The class must be on the server's classpath.  For example, mycompany.mypackage.myclass "
      ::= { startupClassEntry 29  }
   
   
   startupClassLoadBeforeAppActivation OBJECT-TYPE
      SYNTAX      OCTET STRING
      MAX-ACCESS  read-only
      STATUS      current
      DESCRIPTION "Specifies whether the targeted servers load and run this startup class after activating JMS and JDBC services and before activating applications and EJBs.  If you enable this feature for a startup class, a server loads and runs the startup class before the activate phase. At this point, JMS and JDBC services are available. (Deployment for applications and EJBs consists of three phases: prepare, admin and activate.)  Enable this feature if the startup class needs to be invoked after JDBC connection pools are available but before the applications are activated and ready to service client requests.  If you do not enable this feature, LoadBeforeAppDeployments or LoadAfterAppsRunning, a server instance loads startup classes when applications go to the admin state. "
      ::= { startupClassEntry 30  }
   
   
   startupClassLoadAfterAppsRunning OBJECT-TYPE
      SYNTAX      OCTET STRING
      MAX-ACCESS  read-only
      STATUS      current
      DESCRIPTION "Specifies whether the targeted servers load and run this startup class after applications and EJBs are running.  If you enable this feature for a startup class, a server loads and runs the startup class after the activate phase. At this point, JMS and JDBC services are available. (Deployment for applications and EJBs consists of three phases: prepare, admin and activate.)  Enable this feature if the startup class needs to be invoked after applications are running and ready to service client requests.  If you do not enable this feature, LoadBeforeAppDeployments or LoadBeforeAppActivation, a server instance loads startup classes when applications go to the admin state. "
      ::= { startupClassEntry 31  }
   
   
   startupClassTags OBJECT-TYPE
      SYNTAX      OCTET STRING
      MAX-ACCESS  read-only
      STATUS      current
      DESCRIPTION "Return all tags on this Configuration MBean "
      ::= { startupClassEntry 32  }
   
   
   webAppComponentTable OBJECT-TYPE
      SYNTAX      SEQUENCE OF WebAppComponentEntry
      MAX-ACCESS  not-accessible
      STATUS      current
      DESCRIPTION "This table describes web module of an application."
      ::= { wls 760  }
      
   
   webAppComponentEntry OBJECT-TYPE
      SYNTAX      WebAppComponentEntry
      MAX-ACCESS  not-accessible
      STATUS      current
      DESCRIPTION "Entry of webAppComponentTable"
      INDEX { webAppComponentIndex}
      ::= { webAppComponentTable 1 }
      
   WebAppComponentEntry ::=
      SEQUENCE
      {
         webAppComponentIndex DisplayString,
         webAppComponentObjectName DisplayString,
         webAppComponentType  DisplayString,
         webAppComponentName  DisplayString,
         webAppComponentParent DisplayString,
         webAppComponentApplication DisplayString,
         webAppComponentURI   DisplayString,
         webAppComponentWebServers DisplayString,
         webAppComponentIndexDirectoryEnabled INTEGER,
         webAppComponentServletExtensionCaseSensitive INTEGER,
         webAppComponentServletReloadCheckSecs INTEGER,
         webAppComponentSingleThreadedServletPoolSize INTEGER,
         webAppComponentAuthRealmName DisplayString
      }
      
   
   webAppComponentIndex OBJECT-TYPE
      SYNTAX      DisplayString (SIZE (1..16))
      MAX-ACCESS  read-only
      STATUS      current
      DESCRIPTION "Unique value directed from ObjectName which is used as table index"
      ::= { webAppComponentEntry 1  }
   
   
   webAppComponentObjectName OBJECT-TYPE
      SYNTAX      DisplayString (SIZE (1..256))
      MAX-ACCESS  read-only
      STATUS      current
      DESCRIPTION "JMX-standard MBean name"
      ::= { webAppComponentEntry 5  }
   
   
   webAppComponentType OBJECT-TYPE
      SYNTAX      DisplayString (SIZE (1..64))
      MAX-ACCESS  read-only
      STATUS      current
      DESCRIPTION "BEA-proprietary MBean type"
      ::= { webAppComponentEntry 10  }
   
   
   webAppComponentName OBJECT-TYPE
      SYNTAX      DisplayString (SIZE (1..64))
      MAX-ACCESS  read-only
      STATUS      current
      DESCRIPTION "BEA-proprietary MBean name"
      ::= { webAppComponentEntry 15  }
   
   
   webAppComponentParent OBJECT-TYPE
      SYNTAX      DisplayString (SIZE (1..256))
      MAX-ACCESS  read-only
      STATUS      current
      DESCRIPTION "BEA-proprietary Parent object's identification, with syntax
      <type>:<name>"
      ::= { webAppComponentEntry 20  }
   
   
   webAppComponentApplication OBJECT-TYPE
      SYNTAX      DisplayString (SIZE (1..256))
      MAX-ACCESS  read-only
      STATUS      current
      DESCRIPTION "The application this component is a part of. 
      This is guaranteed to never be null."
      ::= { webAppComponentEntry 25  }
   
   
   webAppComponentURI OBJECT-TYPE
      SYNTAX      DisplayString (SIZE (1..256))
      MAX-ACCESS  read-only
      STATUS      current
      DESCRIPTION "A URI pointing to the application component, usually on the Admin Server."
      ::= { webAppComponentEntry 30  }
   
   
   webAppComponentWebServers OBJECT-TYPE
      SYNTAX      DisplayString (SIZE (1..256))
      MAX-ACCESS  read-only
      STATUS      current
      DESCRIPTION "targets on which this deployment is deployed."
      ::= { webAppComponentEntry 35  }
   
   
   webAppComponentIndexDirectoryEnabled OBJECT-TYPE
      SYNTAX      INTEGER
                  {
                     true(1),
                     false(2)
                  }
      
      MAX-ACCESS  read-only
      STATUS      current
      DESCRIPTION "boolean value (true Or false). Return whether or not to automatically generate an HTML
      directory listing if false suitable index file is found"
      ::= { webAppComponentEntry 40  }
   
   
   webAppComponentServletExtensionCaseSensitive OBJECT-TYPE
      SYNTAX      INTEGER
                  {
                     true(1),
                     false(2)
                  }
      
      MAX-ACCESS  read-only
      STATUS      current
      DESCRIPTION "boolean value (true Or false)."
      ::= { webAppComponentEntry 45  }
   
   
   webAppComponentServletReloadCheckSecs OBJECT-TYPE
      SYNTAX      INTEGER
      MAX-ACCESS  read-only
      STATUS      current
      DESCRIPTION "How often WebLogic checks whether a servlet has been
      modified, and if so reloads it. -1                                is never reload, 0 is 
      always reload"
      ::= { webAppComponentEntry 50  }
   
   
   webAppComponentSingleThreadedServletPoolSize OBJECT-TYPE
      SYNTAX      INTEGER
      MAX-ACCESS  read-only
      STATUS      current
      DESCRIPTION "The size of the pool used for SingleThreadModle instance
      pools."
      ::= { webAppComponentEntry 55  }
   
   
   webAppComponentAuthRealmName OBJECT-TYPE
      SYNTAX      DisplayString (SIZE (1..64))
      MAX-ACCESS  read-only
      STATUS      current
      DESCRIPTION "The Realm in the Basic Authentication 
      HTTP dialog box which pops up on the browsers"
      ::= { webAppComponentEntry 60  }
   
   
   webServerTable OBJECT-TYPE
      SYNTAX      SEQUENCE OF WebServerEntry
      MAX-ACCESS  not-accessible
      STATUS      current
      DESCRIPTION "This bean represents the configuration of virtual web server within a weblogic server. Note that a server may define multiple web servers to support virtual hosts.  This MBean represents a virtual host. "
      ::= { wls 770  }
      
   
   webServerEntry OBJECT-TYPE
      SYNTAX      WebServerEntry
      MAX-ACCESS  not-accessible
      STATUS      current
      DESCRIPTION "Entry of webServerTable"
      INDEX { webServerIndex}
      ::= { webServerTable 1 }
      
   WebServerEntry ::=
      SEQUENCE
      {
         webServerIndex       DisplayString,
         webServerObjectName  DisplayString,
         webServerType        DisplayString,
         webServerName        DisplayString,
         webServerParent      DisplayString,
         webServerKeepAliveEnabled INTEGER,
         webServerKeepAliveSecs INTEGER,
         webServerHttpsKeepAliveSecs INTEGER,
         webServerPostTimeoutSecs INTEGER,
         webServerMaxPostTimeSecs INTEGER,
         webServerMaxPostSize INTEGER,
         webServerWAPEnabled  INTEGER,
         webServerSingleSignonDisabled OCTET STRING,
         webServerSendServerHeaderEnabled OCTET STRING,
         webServerOverloadResponseCode INTEGER,
         webServerClientIpHeader OCTET STRING,
         webServerFrontendHTTPSPort INTEGER,
         webServerFrontendHost OCTET STRING,
         webServerAuthCookieEnabled OCTET STRING,
         webServerFrontendHTTPPort INTEGER,
         webServerChunkedTransferDisabled OCTET STRING,
         webServerUseHighestCompatibleHTTPVersion OCTET STRING,
         webServerWriteChunkBytes INTEGER,
         webServerAcceptContextPathInGetRealPath OCTET STRING,
         webServerUseHeaderEncoding OCTET STRING,
         webServerDefaultWebAppContextRoot OCTET STRING,
         webServerDeploymentOrder INTEGER,
         webServerMaxRequestParameterCount INTEGER,
         webServerTags        OCTET STRING
      }
      
   
   webServerIndex OBJECT-TYPE
      SYNTAX      DisplayString (SIZE (1..16))
      MAX-ACCESS  read-only
      STATUS      current
      DESCRIPTION "Unique value directed from ObjectName which is used as table index"
      ::= { webServerEntry 1  }
   
   
   webServerObjectName OBJECT-TYPE
      SYNTAX      DisplayString (SIZE (1..256))
      MAX-ACCESS  read-only
      STATUS      current
      DESCRIPTION "JMX-standard MBean name"
      ::= { webServerEntry 5  }
   
   
   webServerType OBJECT-TYPE
      SYNTAX      DisplayString (SIZE (1..64))
      MAX-ACCESS  read-only
      STATUS      current
      DESCRIPTION "Returns the type of the MBean. "
      ::= { webServerEntry 10  }
   
   
   webServerName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { webServerEntry 15  }
   
   
   webServerParent OBJECT-TYPE
      SYNTAX      DisplayString (SIZE (1..256))
      MAX-ACCESS  read-only
      STATUS      current
      DESCRIPTION "BEA-proprietary Parent object's identification, with syntax
      <type>:<name>"
      ::= { webServerEntry 20  }
   
   
   webServerKeepAliveEnabled OBJECT-TYPE
      SYNTAX      INTEGER
                  {
                     true(1),
                     false(2)
                  }
      
      MAX-ACCESS  read-only
      STATUS      current
      DESCRIPTION "Indicates whether there should be a persistent connection to this server. (This may improve the performance of your Web applications.)  Gets the keepAliveEnabled attribute of the WebServerMBean object "
      ::= { webServerEntry 75  }
   
   
   webServerKeepAliveSecs OBJECT-TYPE
      SYNTAX      INTEGER
      MAX-ACCESS  read-only
      STATUS      current
      DESCRIPTION "The amount of time this server waits before closing an inactive HTTP connection.  Number of seconds to maintain HTTP keep-alive before timing out the request. "
      ::= { webServerEntry 80  }
   
   
   webServerHttpsKeepAliveSecs OBJECT-TYPE
      SYNTAX      INTEGER
      MAX-ACCESS  read-only
      STATUS      current
      DESCRIPTION "The amount of time this server waits before closing an inactive HTTPS connection.  Number of seconds to maintain HTTPS keep-alive before timing out the request. "
      ::= { webServerEntry 85  }
   
   
   webServerPostTimeoutSecs OBJECT-TYPE
      SYNTAX      INTEGER
      MAX-ACCESS  read-only
      STATUS      current
      DESCRIPTION "Timeout (in seconds) for reading HTTP POST data in a servlet request. If the POST data is chunked, the amount of time the server waits between the end of receiving the last chunk of data and the end of receiving the next chunk of data in an HTTP POST before it times out. (This is used to prevent denial-of-service attacks that attempt to overload the server with POST data.)  Gets the postTimeoutSecs attribute of the WebServerMBean object "
      ::= { webServerEntry 90  }
   
   
   webServerMaxPostTimeSecs OBJECT-TYPE
      SYNTAX      INTEGER
      MAX-ACCESS  read-only
      STATUS      current
      DESCRIPTION "Max Post Time (in seconds) for reading HTTP POST data in a servlet request. MaxPostTime &lt; 0 means unlimited  Gets the maxPostTimeSecs attribute of the WebServerMBean object "
      ::= { webServerEntry 95  }
   
   
   webServerMaxPostSize OBJECT-TYPE
      SYNTAX      INTEGER
      MAX-ACCESS  read-only
      STATUS      current
      DESCRIPTION "The maximum post size this server allows for reading HTTP POST and PUT data in a servlet request.  A value less than 0 indicates an unlimited size.  Gets the maxPostSize attribute of the WebServerMBean object "
      ::= { webServerEntry 100  }
   
   
   webServerWAPEnabled OBJECT-TYPE
      SYNTAX      INTEGER
                  {
                     true(1),
                     false(2)
                  }
      
      MAX-ACCESS  read-only
      STATUS      current
      DESCRIPTION "Indicates whether the session ID should include JVM information. (Checking this box may be necessary when using URL rewriting with WAP devices that limit the size of the URL to 128 characters, and may also affect the use of replicated sessions in a cluster.) When this box is selected, the default size of the URL will be set at 52 characters, and it will not contain any special characters.  Gets the WAPEnabled attribute of the WebServerMBean object "
      ::= { webServerEntry 115  }
   
   
   webServerSingleSignonDisabled OBJECT-TYPE
      SYNTAX      OCTET STRING
      MAX-ACCESS  read-only
      STATUS      current
      DESCRIPTION "Indicates whether the singleSignonDisabled attribute is enabled "
      ::= { webServerEntry 126  }
   
   
   webServerSendServerHeaderEnabled OBJECT-TYPE
      SYNTAX      OCTET STRING
      MAX-ACCESS  read-only
      STATUS      current
      DESCRIPTION "Indicates whether this server name is sent with the HTTP response. (This is useful for wireless applications where there is limited space for headers.)  Indicates whether this server instance includes its name and WebLogic Server version number in HTTP response headers. "
      ::= { webServerEntry 127  }
   
   
   webServerOverloadResponseCode OBJECT-TYPE
      SYNTAX      INTEGER
      MAX-ACCESS  read-only
      STATUS      current
      DESCRIPTION "Get the response code to be used when an application is overloaded. An application can get overloaded when the number of pending requests has reached the max capacity specified in the WorkManager or when the server is low on memory. The low memory condition is determined using {@link OverloadProtectionMBean#getFreeMemoryPercentLowThreshold()}. "
      ::= { webServerEntry 128  }
   
   
   webServerClientIpHeader OBJECT-TYPE
      SYNTAX      OCTET STRING
      MAX-ACCESS  read-only
      STATUS      current
      DESCRIPTION "Get the Client IP Header from WebSerevrMBean. "
      ::= { webServerEntry 129  }
   
   
   webServerFrontendHTTPSPort OBJECT-TYPE
      SYNTAX      INTEGER
      MAX-ACCESS  read-only
      STATUS      current
      DESCRIPTION "The name of the secure HTTP port to which all redirected URLs will be sent. If specified, WebLogic Server will use this value rather than the one in the HOST header.  Sets the frontendHTTPSPort Provides a method to ensure that the webapp will always have the correct PORT information, even when the request is coming through a firewall or a proxy. If this parameter is configured, the HOST header will be ignored and the information in this parameter will be used in its place. "
      ::= { webServerEntry 130  }
   
   
   webServerFrontendHost OBJECT-TYPE
      SYNTAX      OCTET STRING
      MAX-ACCESS  read-only
      STATUS      current
      DESCRIPTION "The name of the host to which all redirected URLs will be sent. If specified, WebLogic Server will use this value rather than the one in the HOST header.  Sets the HTTP frontendHost Provides a method to ensure that the webapp will always have the correct HOST information, even when the request is coming through a firewall or a proxy. If this parameter is configured, the HOST header will be ignored and the information in this parameter will be used in its place. "
      ::= { webServerEntry 131  }
   
   
   webServerAuthCookieEnabled OBJECT-TYPE
      SYNTAX      OCTET STRING
      MAX-ACCESS  read-only
      STATUS      current
      DESCRIPTION "Whether authcookie feature is enabled or not. "
      ::= { webServerEntry 132  }
   
   
   webServerFrontendHTTPPort OBJECT-TYPE
      SYNTAX      INTEGER
      MAX-ACCESS  read-only
      STATUS      current
      DESCRIPTION "The name of the HTTP port to which all redirected URLs will be sent. If specified, WebLogic Server will use this value rather than the one in the HOST header.  Sets the frontendHTTPPort Provides a method to ensure that the webapp will always have the correct PORT information, even when the request is coming through a firewall or a proxy. If this parameter is configured, the HOST header will be ignored and the information in this parameter will be used in its place. "
      ::= { webServerEntry 133  }
   
   
   webServerChunkedTransferDisabled OBJECT-TYPE
      SYNTAX      OCTET STRING
      MAX-ACCESS  read-only
      STATUS      current
      DESCRIPTION "Indicates whether the use of Chunk Transfer-Encoding in HTTP/1.1 is enabled. "
      ::= { webServerEntry 134  }
   
   
   webServerUseHighestCompatibleHTTPVersion OBJECT-TYPE
      SYNTAX      OCTET STRING
      MAX-ACCESS  read-only
      STATUS      current
      DESCRIPTION "Enables use of the highest compatible HTTP protocol version-string in the response. E.g. HTTP spec suggests that HTTP/1.1 version-string should be used in response to a request using HTTP/1.0. This does not necessarily affect the response format. "
      ::= { webServerEntry 135  }
   
   
   webServerWriteChunkBytes OBJECT-TYPE
      SYNTAX      INTEGER
      MAX-ACCESS  read-only
      STATUS      current
      DESCRIPTION "The default size of the blocks to be written to the network layer.  Gets the writeChunkBytes attribute of the WebServerMBean object "
      ::= { webServerEntry 136  }
   
   
   webServerAcceptContextPathInGetRealPath OBJECT-TYPE
      SYNTAX      OCTET STRING
      MAX-ACCESS  read-only
      STATUS      current
      DESCRIPTION "Indicates whether this server allows the inclusion of the context path in the virtual path to context.getRealPath(). (If checked, you cannot use sub directories with the same name as contextPath). This is a compatibility switch that will be deprecated 9.0.0.0 in future releases.  Gets the acceptContextPathInGetRealPath attribute of the WebServerMBean object "
      ::= { webServerEntry 137  }
   
   
   webServerUseHeaderEncoding OBJECT-TYPE
      SYNTAX      OCTET STRING
      MAX-ACCESS  read-only
      STATUS      current
      DESCRIPTION " "
      ::= { webServerEntry 138  }
   
   
   webServerDefaultWebAppContextRoot OBJECT-TYPE
      SYNTAX      OCTET STRING
      MAX-ACCESS  read-only
      STATUS      current
      DESCRIPTION "Returns the original context-root for the default Web application for this Web server. Alternatively, you can use the context-root attributes in application.xml or weblogic.xml to set a default Web application. The context-root for a default Web application is /. If '' (empty string) is specified, the Web server defaults to /. "
      ::= { webServerEntry 139  }
   
   
   webServerDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { webServerEntry 140  }
   
   
   webServerMaxRequestParameterCount OBJECT-TYPE
      SYNTAX      INTEGER
      MAX-ACCESS  read-only
      STATUS      current
      DESCRIPTION "Max Request Parameter Count this server allows for reading maximum HTTP POST Parameters count in a servlet request.  Gets the maxRequestParameterCount attribute of the WebServerMBean object "
      ::= { webServerEntry 141  }
   
   
   webServerTags OBJECT-TYPE
      SYNTAX      OCTET STRING
      MAX-ACCESS  read-only
      STATUS      current
      DESCRIPTION "Return all tags on this Configuration MBean "
      ::= { webServerEntry 142  }
   
   
   wlecConnectionPoolTable OBJECT-TYPE
      SYNTAX      SEQUENCE OF WlecConnectionPoolEntry
      MAX-ACCESS  not-accessible
      STATUS      current
      DESCRIPTION "This table defines a WLEC connection pool."
      ::= { wls 780  }
      
   
   wlecConnectionPoolEntry OBJECT-TYPE
      SYNTAX      WlecConnectionPoolEntry
      MAX-ACCESS  not-accessible
      STATUS      current
      DESCRIPTION "Entry of wlecConnectionPoolTable"
      INDEX { wlecConnectionPoolIndex}
      ::= { wlecConnectionPoolTable 1 }
      
   WlecConnectionPoolEntry ::=
      SEQUENCE
      {
         wlecConnectionPoolIndex DisplayString,
         wlecConnectionPoolObjectName DisplayString,
         wlecConnectionPoolType DisplayString,
         wlecConnectionPoolName DisplayString,
         wlecConnectionPoolParent DisplayString,
         wlecConnectionPoolDeploymentOrder INTEGER
      }
      
   
   wlecConnectionPoolIndex OBJECT-TYPE
      SYNTAX      DisplayString (SIZE (1..16))
      MAX-ACCESS  read-only
      STATUS      current
      DESCRIPTION "Unique value directed from ObjectName which is used as table index"
      ::= { wlecConnectionPoolEntry 1  }
   
   
   wlecConnectionPoolObjectName OBJECT-TYPE
      SYNTAX      DisplayString (SIZE (1..256))
      MAX-ACCESS  read-only
      STATUS      current
      DESCRIPTION "JMX-standard MBean name"
      ::= { wlecConnectionPoolEntry 5  }
   
   
   wlecConnectionPoolType OBJECT-TYPE
      SYNTAX      DisplayString (SIZE (1..64))
      MAX-ACCESS  read-only
      STATUS      current
      DESCRIPTION "BEA-proprietary MBean type"
      ::= { wlecConnectionPoolEntry 10  }
   
   
   wlecConnectionPoolName OBJECT-TYPE
      SYNTAX      DisplayString (SIZE (1..64))
      MAX-ACCESS  read-only
      STATUS      current
      DESCRIPTION "BEA-proprietary MBean name"
      ::= { wlecConnectionPoolEntry 15  }
   
   
   wlecConnectionPoolParent OBJECT-TYPE
      SYNTAX      DisplayString (SIZE (1..256))
      MAX-ACCESS  read-only
      STATUS      current
      DESCRIPTION "BEA-proprietary Parent object's identification, with syntax
      <type>:<name>"
      ::= { wlecConnectionPoolEntry 20  }
   
   
   wlecConnectionPoolDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { wlecConnectionPoolEntry 81  }
   
   
   bridgeDestinationTable OBJECT-TYPE
      SYNTAX      SEQUENCE OF BridgeDestinationEntry
      MAX-ACCESS  not-accessible
      STATUS      current
      DESCRIPTION "This table defines a Bridge destination."
      ::= { wls 782  }
      
   
   bridgeDestinationEntry OBJECT-TYPE
      SYNTAX      BridgeDestinationEntry
      MAX-ACCESS  not-accessible
      STATUS      current
      DESCRIPTION "Entry of BridgeDestinationTable"
      INDEX { bridgeDestinationIndex}
      ::= { bridgeDestinationTable 1 }
      
   BridgeDestinationEntry ::=
      SEQUENCE
      {
         bridgeDestinationIndex DisplayString,
         bridgeDestinationObjectName DisplayString,
         bridgeDestinationType DisplayString,
         bridgeDestinationName DisplayString,
         bridgeDestinationParent DisplayString,
         bridgeDestinationAdapterJNDIName DisplayString,
         bridgeDestinationClasspath OCTET STRING,
         bridgeDestinationUserName OCTET STRING
      }
      
   
   bridgeDestinationIndex OBJECT-TYPE
      SYNTAX      DisplayString (SIZE (1..16))
      MAX-ACCESS  read-only
      STATUS      current
      DESCRIPTION "Unique value directed from ObjectName which is used as table index"
      ::= { bridgeDestinationEntry 1  }
   
   
   bridgeDestinationObjectName OBJECT-TYPE
      SYNTAX      DisplayString (SIZE (1..256))
      MAX-ACCESS  read-only
      STATUS      current
      DESCRIPTION "JMX-standard MBean name"
      ::= { bridgeDestinationEntry 5  }
   
   
   bridgeDestinationType OBJECT-TYPE
      SYNTAX      DisplayString (SIZE (1..64))
      MAX-ACCESS  read-only
      STATUS      current
      DESCRIPTION "BEA-proprietary MBean type"
      ::= { bridgeDestinationEntry 10  }
   
   
   bridgeDestinationName OBJECT-TYPE
      SYNTAX      DisplayString (SIZE (1..64))
      MAX-ACCESS  read-only
      STATUS      current
      DESCRIPTION "BEA-proprietary MBean name"
      ::= { bridgeDestinationEntry 15  }
   
   
   bridgeDestinationParent OBJECT-TYPE
      SYNTAX      DisplayString (SIZE (1..256))
      MAX-ACCESS  read-only
      STATUS      current
      DESCRIPTION "BEA-proprietary Parent object's identification, with syntax
      <type>:<name>"
      ::= { bridgeDestinationEntry 20  }
   
   
   bridgeDestinationAdapterJNDIName OBJECT-TYPE
      SYNTAX      DisplayString (SIZE (1..256))
      MAX-ACCESS  read-only
      STATUS      current
      DESCRIPTION "Get the JNDI name of the adapter."
      ::= { bridgeDestinationEntry 30  }
   
   
   bridgeDestinationClasspath OBJECT-TYPE
      SYNTAX      OCTET STRING
      MAX-ACCESS  read-only
      STATUS      current
      DESCRIPTION "The CLASSPATH of the bridge destination.    Used mainly to connect to another release of WebLogic Server.    When connecting to a destination that is running on WebLogic Server 6.0 or earlier, the bridge destination must supply a CLASSPATH that indicates the locations of the classes for the earlier WebLogic Server implementation.    When connecting to a third-party JMS product, the bridge destination must supply the product's CLASSPATH in the WebLogic Server CLASSPATH."
      ::= { bridgeDestinationEntry 31  }
   
   
   bridgeDestinationUserName OBJECT-TYPE
      SYNTAX      OCTET STRING
      MAX-ACCESS  read-only
      STATUS      current
      DESCRIPTION "The optional user name the adapter uses to access the bridge destination.  All operations on the specified destination are done using this user name and the corresponding password. Therefore, the User Name/Password for the source and target destinations must have permission to the access the underlying destinations in order for the messaging bridge to work."
      ::= { bridgeDestinationEntry 32  }
   
   
   messagingBridgeTable OBJECT-TYPE
      SYNTAX      SEQUENCE OF MessagingBridgeEntry
      MAX-ACCESS  not-accessible
      STATUS      current
      DESCRIPTION "This MBean represents a WebLogic messaging bridge. A messaging bridge instance interoperates between separate implementations of WebLogic JMS or between WebLogic JMS and another messaging product.  For WebLogic JMS and third-party JMS products, a messaging bridge communicates with a configured source and target destinations using the resource adapters provided with WebLogic Server. "
      ::= { wls 786  }
      
   
   messagingBridgeEntry OBJECT-TYPE
      SYNTAX      MessagingBridgeEntry
      MAX-ACCESS  not-accessible
      STATUS      current
      DESCRIPTION "Entry of MessagingBridgeTable"
      INDEX { messagingBridgeIndex}
      ::= { messagingBridgeTable 1 }
      
   MessagingBridgeEntry ::=
      SEQUENCE
      {
         messagingBridgeIndex DisplayString,
         messagingBridgeObjectName DisplayString,
         messagingBridgeType  DisplayString,
         messagingBridgeName  DisplayString,
         messagingBridgeParent DisplayString,
         messagingBridgeSelector DisplayString,
         messagingBridgeQualityOfService DisplayString,
         messagingBridgeIdleTimeMaximum INTEGER,
         messagingBridgeTransactionTimeout INTEGER,
         messagingBridgeQOSDegradationAllowed INTEGER,
         messagingBridgeDurabilityEnabled OCTET STRING,
         messagingBridgeReconnectDelayMinimum INTEGER,
         messagingBridgePreserveMsgProperty OCTET STRING,
         messagingBridgeBatchSize INTEGER,
         messagingBridgeReconnectDelayMaximum INTEGER,
         messagingBridgeDeploymentOrder INTEGER,
         messagingBridgeAsyncEnabled OCTET STRING,
         messagingBridgeBatchInterval Counter64,
         messagingBridgeStarted OCTET STRING,
         messagingBridgeReconnectDelayIncrease INTEGER,
         messagingBridgePartialClusterStabilityDelaySeconds Counter64,
         messagingBridgeRestartInPlace OCTET STRING,
         messagingBridgeNumberOfRestartAttempts INTEGER,
         messagingBridgeSecondsBetweenRestarts INTEGER,
         messagingBridgeDistributionPolicy OCTET STRING,
         messagingBridgeTags  OCTET STRING,
         messagingBridgeMigrationPolicy OCTET STRING,
         messagingBridgeFailbackDelaySeconds Counter64,
         messagingBridgeInitialBootDelaySeconds Counter64,
         messagingBridgeFailOverLimit INTEGER
      }
      
   
   messagingBridgeIndex OBJECT-TYPE
      SYNTAX      DisplayString (SIZE (1..16))
      MAX-ACCESS  read-only
      STATUS      current
      DESCRIPTION "Unique value directed from ObjectName which is used as table index"
      ::= { messagingBridgeEntry 1  }
   
   
   messagingBridgeObjectName OBJECT-TYPE
      SYNTAX      DisplayString (SIZE (1..256))
      MAX-ACCESS  read-only
      STATUS      current
      DESCRIPTION "JMX-standard MBean name"
      ::= { messagingBridgeEntry 5  }
   
   
   messagingBridgeType OBJECT-TYPE
      SYNTAX      DisplayString (SIZE (1..64))
      MAX-ACCESS  read-only
      STATUS      current
      DESCRIPTION "Returns the type of the MBean. "
      ::= { messagingBridgeEntry 10  }
   
   
   messagingBridgeName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { messagingBridgeEntry 15  }
   
   
   messagingBridgeParent OBJECT-TYPE
      SYNTAX      DisplayString (SIZE (1..256))
      MAX-ACCESS  read-only
      STATUS      current
      DESCRIPTION "BEA-proprietary Parent object's identification, with syntax
      <type>:<name>"
      ::= { messagingBridgeEntry 20  }
   
   
   messagingBridgeSelector OBJECT-TYPE
      SYNTAX      DisplayString (SIZE (1..256))
      MAX-ACCESS  read-only
      STATUS      current
      DESCRIPTION "The filter for messages that are sent across the messaging bridge instance.  Only messages that match the selection criteria are sent across the messaging bridge:    For queues, messages that do not match the selection criteria are left behind and accumulate in the queue.    For topics, messages that do not match the connection criteria are dropped.   "
      ::= { messagingBridgeEntry 50  }
   
   
   messagingBridgeQualityOfService OBJECT-TYPE
      SYNTAX      DisplayString (SIZE (1..256))
      MAX-ACCESS  read-only
      STATUS      current
      DESCRIPTION "The QOS (quality of service) for this messaging bridge instance.   Exactly-once: Each message in the source destination is transferred to the target exactly once. This is the highest QOS a messaging bridge instance can offer.   Atmost-once: Each message in the source is transferred to the target only once with the possibility of being lost during the forwarding.   Duplicate-okay: Messages in the source destination are transferred to the target (none are lost) but some may appear in the target more than once.   "
      ::= { messagingBridgeEntry 70  }
   
   
   messagingBridgeIdleTimeMaximum OBJECT-TYPE
      SYNTAX      INTEGER
      MAX-ACCESS  read-only
      STATUS      current
      DESCRIPTION "The maximum amount of time, in seconds, that a messaging bridge instance remains idle.    In asynchronous mode, this is the longest amount of time a messaging bridge instance stays idle before it checks the sanity of its connection to the source.    In synchronous mode, this is the amount of time the messaging bridge can block on a receive call if no transaction is involved.   "
      ::= { messagingBridgeEntry 85  }
   
   
   messagingBridgeTransactionTimeout OBJECT-TYPE
      SYNTAX      INTEGER
      MAX-ACCESS  read-only
      STATUS      current
      DESCRIPTION "The amount of time, in seconds, that the transaction manager waits for each transaction before timing it out.    Transaction timeouts are used when the QOS (quality of service) for a messaging bridge instance requires transactions.    If a bridge is configured with Exactly-once QOS, the receiving and sending is completed in one transaction.   "
      ::= { messagingBridgeEntry 90  }
   
   
   messagingBridgeQOSDegradationAllowed OBJECT-TYPE
      SYNTAX      INTEGER
                  {
                     true(1),
                     false(2)
                  }
      
      MAX-ACCESS  read-only
      STATUS      current
      DESCRIPTION "Specifies if this messaging bridge instance allows the degradation of its QOS (quality of service) when the configured QOS is not available.    When enabled, the messaging bridge instance degrades the QOS when the configured QOS is not available. If the QOS is degraded, a log message is delivered to the WebLogic startup window or log file.    When not enabled, if messaging bridge instance cannot satisfy the quality of service requested, an error results and the messaging bridge instance does not start.   "
      ::= { messagingBridgeEntry 100  }
   
   
   messagingBridgeDurabilityEnabled OBJECT-TYPE
      SYNTAX      OCTET STRING
      MAX-ACCESS  read-only
      STATUS      current
      DESCRIPTION "Specifies whether or not the messaging bridge allows durable messages.  When enabled and the source destination is a JMS topic, a messaging bridge instance uses a durable subscription to ensure that no messages are lost in the event of a failure. DurabilityEnabled ignored if the source destination is a JMS queue.    When enabled and the source destination uses durable subscriptions, the source JMS implementation saves messages that are sent when a messaging bridge instance is not running. When the bridge instance is restarted, these messages are forwarded to the target destination. The administrator can choose not to be durable.    When not enabled, messages that are sent to the source JMS implementation while the bridge instance is down cannot be forwarded to the target destination.   "
      ::= { messagingBridgeEntry 101  }
   
   
   messagingBridgeReconnectDelayMinimum OBJECT-TYPE
      SYNTAX      INTEGER
      MAX-ACCESS  read-only
      STATUS      current
      DESCRIPTION "The minimum amount of time, in seconds, that a messaging bridge instance waits before it tries to reconnect to the source or target destination after a failure.  Use with ReconnectDelayMaximum and ReconnectDelayIncrease. After the first failure to connect to a destination, the bridge instance waits for the number of seconds defined by ReconnectDelayMinimum. Each time a reconnect attempt fails, the bridge instance increases its waiting time by the number of seconds defined by ReconnectDelayIncrease. The maximum delay time is defined by ReconnectDelayMaximum. Once the waiting time is increased to the maximum value, the bridge instance stops increase its waiting time. Once the bridge instance successfully connects to the destination, the bridge instance resets its waiting time to the initial value defined by ReconnectDelayMinimum.> "
      ::= { messagingBridgeEntry 102  }
   
   
   messagingBridgePreserveMsgProperty OBJECT-TYPE
      SYNTAX      OCTET STRING
      MAX-ACCESS  read-only
      STATUS      current
      DESCRIPTION "Specifies if message properties are preserved when messages are forwarded by a bridge instance.  The following message properties are preserved:    message ID    message timestamp    user ID    delivery mode    priority    expiration time    redelivery limit    unit of order name    If the target bridge destination is on a foreign JMS server, the following message properties are preserved:    delivery mode    priority    expiration time   "
      ::= { messagingBridgeEntry 103  }
   
   
   messagingBridgeBatchSize OBJECT-TYPE
      SYNTAX      INTEGER
      MAX-ACCESS  read-only
      STATUS      current
      DESCRIPTION "The number of messages that are processed within one transaction.  Batch Size only applies to a messaging bridge instance forwarding messages in synchronous mode and has a QOS (quality of service) that requires two-phase transactions. "
      ::= { messagingBridgeEntry 104  }
   
   
   messagingBridgeReconnectDelayMaximum OBJECT-TYPE
      SYNTAX      INTEGER
      MAX-ACCESS  read-only
      STATUS      current
      DESCRIPTION "The longest amount of time, in seconds, that a messaging bridge instance waits between one failed attempt to connect to the source or target, and the next retry.  Use with ReconnectDelayMinimum and ReconnectDelayIncrease. After the first failure to connect to a destination, a bridge instance waits for the number of seconds defined by ReconnectDelayMinimum. Each time a reconnect attempt fails, the bridge instance increases its waiting time by the number of seconds defined by ReconnectDelayIncrease. The maximum delay time is defined by ReconnectDelayMaximum. Once the waiting time is increased to the maximum value, the bridge instance stops increase its waiting time. Once the bridge instance successfully connects to the destination, the bridge instance resets its waiting time to the initial value defined by ReconnectDelayMinimum. "
      ::= { messagingBridgeEntry 105  }
   
   
   messagingBridgeDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { messagingBridgeEntry 106  }
   
   
   messagingBridgeAsyncEnabled OBJECT-TYPE
      SYNTAX      OCTET STRING
      MAX-ACCESS  read-only
      STATUS      current
      DESCRIPTION "Specifies if a messaging bridge instance forwards in asynchronous messaging mode.  AsyncEnabled only applies to messaging bridge instances whose source destination supports asynchronous receiving. Messaging bridges instances that forward in asynchronous mode are driven by the source destination. A messaging bridge instance listens for messages and forwards them as they arrive. When AsyncEnabled is not selected, a bridge instance is forced to work in synchronous mode, even if the source supports asynchronous receiving.  Note: For a messaging bridge instance with a QOS of Exactly-once to work in asynchronous mode, the source destination has to support the MDBTransaction interface. Otherwise, the bridge automatically switches to synchronous mode if it detects that MDBTransaction is not supported by the source destination. "
      ::= { messagingBridgeEntry 107  }
   
   
   messagingBridgeBatchInterval OBJECT-TYPE
      SYNTAX      Counter64
      MAX-ACCESS  read-only
      STATUS      current
      DESCRIPTION "The maximum amount of time, in milliseconds, that a messaging bridge instance waits before sending a batch of messages in one transaction, regardless of whether the Batch Size has been reached or not.    Only applies to a messaging bridge instance forwarding messages in synchronous mode and has a QOS (quality of service) that requires two-phase transactions.    The default value of -1 indicates that the bridge instance waits until the number of messages reaches the Batch Size before it completes a transaction.   "
      ::= { messagingBridgeEntry 108  }
   
   
   messagingBridgeStarted OBJECT-TYPE
      SYNTAX      OCTET STRING
      MAX-ACCESS  read-only
      STATUS      current
      DESCRIPTION "Specifies the initial operating state of a targeted messaging bridge instance.    If enabled, the messaging bridge instance forwards messages (running).    If not enabled, the messaging bridge instance does not forward messages (temporarily stopped).    After a messaging bridge has started forwarding messages (running), use Started to temporarily suspend an active messaging bridge instance or restart an stopped messaging bridge instance.    Select the Started checkbox to start a messaging bridge instance that has been temporarily stopped.    Clear the Started checkbox to temporarily stop a messaging bridge instance that was running.    This value does not indicate the run-time state of a messaging bridge instance.   "
      ::= { messagingBridgeEntry 109  }
   
   
   messagingBridgeReconnectDelayIncrease OBJECT-TYPE
      SYNTAX      INTEGER
      MAX-ACCESS  read-only
      STATUS      current
      DESCRIPTION "The incremental delay time, in seconds, that a messaging bridge instance increases its waiting time between one failed reconnection attempt and the next retry.  Use with ReconnectDelayMinimum and ReconnectDelayMaximum. After the first failure to connect to a destination, the bridge instance waits for the number of seconds defined by ReconnectDelayMinimum. Each time a reconnect attempt fails, the bridge instance increases its waiting time by the number of seconds defined by ReconnectDelayIncrease. The maximum delay time is defined by ReconnectDelayMaximum. Once the waiting time is increased to the maximum value, the bridge instance stops increase its waiting time. Once the bridge instance successfully connects to the destination, the bridge instance resets its waiting time to the initial value defined by ReconnectDelayMinimum. "
      ::= { messagingBridgeEntry 110  }
   
   
   messagingBridgePartialClusterStabilityDelaySeconds OBJECT-TYPE
      SYNTAX      Counter64
      MAX-ACCESS  read-only
      STATUS      current
      DESCRIPTION "Specifies the amount of time, in seconds, to delay before a partially started cluster starts all cluster-targeted JMS artifact instances that are configured with a Migration Policy of Always or On-Failure.   Before this timeout expires or all servers are running, a cluster starts a subset of such instances based on the total number of servers running and the configured cluster size. Once the timeout expires or all servers have started, the system considers the cluster stable and starts any remaining services.  This delay ensures that services are balanced across a cluster even if the servers are started sequentially. It is ignored after a cluster is fully started (stable) or when individual servers are started.   A value > 0 specifies the time, in seconds, to delay before a partially started cluster starts dynamically configured services. A value of 0 specifies no delay.  "
      ::= { messagingBridgeEntry 111  }
   
   
   messagingBridgeRestartInPlace OBJECT-TYPE
      SYNTAX      OCTET STRING
      MAX-ACCESS  read-only
      STATUS      current
      DESCRIPTION " Enables a periodic automatic in-place restart of failed cluster-targeted or standalone-server-targeted JMS artifact instance(s) running on healthy WebLogic Server instances. See the migratable target settings for in-place restarts of migratable-targeted JMS artifacts. When the Restart In Place setting is configured on a store, it applies to all JMS artifacts that reference the store.    If the Migration Policy of the JMS artifact is set to Off, Restart In Place is disabled by default.  If the Migration Policy of the JMS artifact is set to On-Failure or Always, Restart In Place is enabled by default.  This attribute is not used by WebLogic messaging bridges which automatically restart internal connections as needed.  For a JMS artifact that is cluster-targeted and the Migration Policy is set to On-Failure or Always, if restart fails after the configured maximum retry attempts, it will migrate to a different server within the cluster.    "
      ::= { messagingBridgeEntry 112  }
   
   
   messagingBridgeNumberOfRestartAttempts OBJECT-TYPE
      SYNTAX      INTEGER
      MAX-ACCESS  read-only
      STATUS      current
      DESCRIPTION "Specifies the maximum number of restart attempts.   A value > 0 specifies the maximum number of restart attempts. A value of 0 specifies the same behavior as setting {@link #getRestartInPlace} to false. A value of -1 means infinite retry restart until it either starts or the server instance shuts down.  "
      ::= { messagingBridgeEntry 113  }
   
   
   messagingBridgeSecondsBetweenRestarts OBJECT-TYPE
      SYNTAX      INTEGER
      MAX-ACCESS  read-only
      STATUS      current
      DESCRIPTION "Specifies the amount of time, in seconds, to wait in between attempts to restart a failed service instance. "
      ::= { messagingBridgeEntry 114  }
   
   
   messagingBridgeDistributionPolicy OBJECT-TYPE
      SYNTAX      OCTET STRING
      MAX-ACCESS  read-only
      STATUS      current
      DESCRIPTION "Specifies how the instances of a configured JMS artifact are named and distributed when cluster-targeted.  A JMS artifact is cluster-targeted when its target is directly set to a cluster, or when it is scoped to a resource group and the resource group is in turn targeted to a cluster.  When this setting is configured on a store, it applies to all JMS artifacts that reference the store.  Valid options:   Distributed Creates an instance on each server JVM in a cluster. Required for all SAF agents and for cluster-targeted or resource-group-scoped JMS servers that host distributed destinations.    Singleton Creates a single instance on a single server JVM within a cluster. Required for cluster-targeted or resource-group-scoped JMS servers that host standalone (non-distributed) destinations and for cluster-targeted or resource-group-scoped path services.  The Migration Policy must be On-Failure or Always when using this option with a JMS server, On-Failure when using this option with a messaging bridge, and Always when using this option with a path service.    Instance Naming Note:   The DistributionPolicy determines the instance name suffix for cluster-targeted JMS artifacts.  The suffix for a cluster-targeted Singleton is -01 and for a cluster-targeted Distributed is @ClusterMemberName.    Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   If you cannot cluster-target a bridge and still need singleton behavior in a configured cluster, you can target the bridge to a migratable target and configure the Migration Policy on the migratable target to Exactly-Once.   "
      ::= { messagingBridgeEntry 115  }
   
   
   messagingBridgeTags OBJECT-TYPE
      SYNTAX      OCTET STRING
      MAX-ACCESS  read-only
      STATUS      current
      DESCRIPTION "Return all tags on this Configuration MBean "
      ::= { messagingBridgeEntry 116  }
   
   
   messagingBridgeMigrationPolicy OBJECT-TYPE
      SYNTAX      OCTET STRING
      MAX-ACCESS  read-only
      STATUS      current
      DESCRIPTION "Controls migration and restart behavior of cluster-targeted JMS service artifact instances. When this setting is configured on a cluster-targeted store, it applies to all JMS artifacts that reference the store. See the migratable target settings for enabling migration and restart on migratable-targeted JMS artifacts.  Off Disables migration support for cluster-targeted JMS service objects, and changes the default for Restart In Place to false. If you want a restart to be enabled when the Migration Policy is Off, then Restart In Place must be explicitly configured to true. This policy cannot be combined with the Singleton Migration Policy.  On-Failure Enables automatic migration and restart of instances on the failure of a subsystem Service or WebLogic Server instance, including automatic fail-back and load balancing of instances.   Always Provides the same behavior as On-Failure and automatically migrates instances even in the event of a graceful shutdown or a partial cluster start.   Note: Cluster leasing must be configured for On-Failure and Always.  Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   A Migration Policy of Always is not recommended for bridges.   If you cannot cluster-target a bridge and still need singleton behavior in a configured cluster, you can target the bridge to a migratable target and configure the Migration Policy on the migratable target to Exactly-Once.   "
      ::= { messagingBridgeEntry 117  }
   
   
   messagingBridgeFailbackDelaySeconds OBJECT-TYPE
      SYNTAX      Counter64
      MAX-ACCESS  read-only
      STATUS      current
      DESCRIPTION "Specifies the amount of time, in seconds, to delay before failing a cluster-targeted JMS artifact instance back to its preferred server after the preferred server failed and was restarted.  This delay allows time for the system to stabilize and dependent services to be restarted, preventing a system failure during a reboot.   A value > 0 specifies the time, in seconds, to delay before failing a JMS artifact back to its user preferred server. A value of 0 indicates that the instance would never failback. A value of -1 indicates that there is no delay and the instance would failback immediately.   Note: This setting only applies when the JMS artifact is cluster-targeted and the Migration Policy is set to On-Failure or Always. "
      ::= { messagingBridgeEntry 118  }
   
   
   messagingBridgeInitialBootDelaySeconds OBJECT-TYPE
      SYNTAX      Counter64
      MAX-ACCESS  read-only
      STATUS      current
      DESCRIPTION "Specifies the amount of time, in seconds, to delay before starting a cluster-targeted JMS instance on a newly booted WebLogic Server instance. When this setting is configured on a store, it applies to all JMS artifacts that reference the store.  This allows time for the system to stabilize and dependent services to be restarted, preventing a system failure during a reboot.   A value > 0 is the time, in seconds, to delay before before loading resources after a failure and restart. A value of 0 specifies no delay.  Note: This setting only applies when the JMS artifact is cluster-targeted and the Migration Policy is set to On-Failure or Always. "
      ::= { messagingBridgeEntry 119  }
   
   
   messagingBridgeFailOverLimit OBJECT-TYPE
      SYNTAX      INTEGER
      MAX-ACCESS  read-only
      STATUS      current
      DESCRIPTION "Specify a limit for the number of cluster-targeted JMS artifact instances that can fail over to a particular JVM.  This can be used to prevent too many instances from starting on a server, avoiding a system failure when starting too few servers of a formerly large cluster.  A typical limit value should allow all instances to run in the smallest desired cluster size, which means (smallest-cluster-size * (limit + 1)) should equal or exceed the total number of instances.    A value of -1 means there is no fail over limit (unlimited). A value of 0 prevents any fail overs of cluster-targeted JMS artifact instances, so no more than 1 instance will run per server (this is an instance that has not failed over). A value of 1 allows one fail-over instance on each server, so no more than two instances will run per server (one failed over instance plus an instance that has not failed over).   Note: This setting only applies when the JMS artifact is cluster-targeted and the Migration Policy is set to On-Failure or Always. "
      ::= { messagingBridgeEntry 120  }
   
   
   virtualHostTable OBJECT-TYPE
      SYNTAX      SEQUENCE OF VirtualHostEntry
      MAX-ACCESS  not-accessible
      STATUS      current
      DESCRIPTION "This bean represents the configuration of virtual web server within a WebLogic Server instance. Note that a server may define multiple web servers to support virtual hosts.  This MBean represents a virtual host. "
      ::= { wls 790  }
      
   
   virtualHostEntry OBJECT-TYPE
      SYNTAX      VirtualHostEntry
      MAX-ACCESS  not-accessible
      STATUS      current
      DESCRIPTION "Entry of virtualHostTable"
      INDEX { virtualHostIndex}
      ::= { virtualHostTable 1 }
      
   VirtualHostEntry ::=
      SEQUENCE
      {
         virtualHostIndex     DisplayString,
         virtualHostObjectName DisplayString,
         virtualHostType      DisplayString,
         virtualHostName      DisplayString,
         virtualHostParent    DisplayString,
         virtualHostKeepAliveEnabled INTEGER,
         virtualHostKeepAliveSecs INTEGER,
         virtualHostHttpsKeepAliveSecs INTEGER,
         virtualHostPostTimeoutSecs INTEGER,
         virtualHostMaxPostTimeSecs INTEGER,
         virtualHostMaxPostSize INTEGER,
         virtualHostWAPEnabled INTEGER,
         virtualHostVirtualHostNames DisplayString,
         virtualHostFrontendHTTPPort INTEGER,
         virtualHostAuthCookieEnabled OCTET STRING,
         virtualHostSingleSignonDisabled OCTET STRING,
         virtualHostChunkedTransferDisabled OCTET STRING,
         virtualHostAcceptContextPathInGetRealPath OCTET STRING,
         virtualHostOverloadResponseCode INTEGER,
         virtualHostDeploymentOrder INTEGER,
         virtualHostNetworkAccessPoint OCTET STRING,
         virtualHostSendServerHeaderEnabled OCTET STRING,
         virtualHostFrontendHost OCTET STRING,
         virtualHostWriteChunkBytes INTEGER,
         virtualHostFrontendHTTPSPort INTEGER,
         virtualHostUseHeaderEncoding OCTET STRING,
         virtualHostUseHighestCompatibleHTTPVersion OCTET STRING,
         virtualHostDefaultWebAppContextRoot OCTET STRING,
         virtualHostClientIpHeader OCTET STRING,
         virtualHostMaxRequestParameterCount INTEGER,
         virtualHostTags      OCTET STRING
      }
      
   
   virtualHostIndex OBJECT-TYPE
      SYNTAX      DisplayString (SIZE (1..16))
      MAX-ACCESS  read-only
      STATUS      current
      DESCRIPTION "Unique value directed from ObjectName which is used as table index"
      ::= { virtualHostEntry 1  }
   
   
   virtualHostObjectName OBJECT-TYPE
      SYNTAX      DisplayString (SIZE (1..256))
      MAX-ACCESS  read-only
      STATUS      current
      DESCRIPTION "JMX-standard MBean name"
      ::= { virtualHostEntry 5  }
   
   
   virtualHostType OBJECT-TYPE
      SYNTAX      DisplayString (SIZE (1..64))
      MAX-ACCESS  read-only
      STATUS      current
      DESCRIPTION "Returns the type of the MBean. "
      ::= { virtualHostEntry 10  }
   
   
   virtualHostName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { virtualHostEntry 15  }
   
   
   virtualHostParent OBJECT-TYPE
      SYNTAX      DisplayString (SIZE (1..256))
      MAX-ACCESS  read-only
      STATUS      current
      DESCRIPTION "BEA-proprietary Parent object's identification, with syntax
      <type>:<name>"
      ::= { virtualHostEntry 20  }
   
   
   virtualHostKeepAliveEnabled OBJECT-TYPE
      SYNTAX      INTEGER
                  {
                     true(1),
                     false(2)
                  }
      
      MAX-ACCESS  read-only
      STATUS      current
      DESCRIPTION "Indicates whether there should be a persistent connection to this server. (This may improve the performance of your Web applications.)  Gets the keepAliveEnabled attribute of the WebServerMBean object "
      ::= { virtualHostEntry 75  }
   
   
   virtualHostKeepAliveSecs OBJECT-TYPE
      SYNTAX      INTEGER
      MAX-ACCESS  read-only
      STATUS      current
      DESCRIPTION "The amount of time this server waits before closing an inactive HTTP connection.  Number of seconds to maintain HTTP keep-alive before timing out the request. "
      ::= { virtualHostEntry 80  }
   
   
   virtualHostHttpsKeepAliveSecs OBJECT-TYPE
      SYNTAX      INTEGER
      MAX-ACCESS  read-only
      STATUS      current
      DESCRIPTION "The amount of time this server waits before closing an inactive HTTPS connection.  Number of seconds to maintain HTTPS keep-alive before timing out the request. "
      ::= { virtualHostEntry 85  }
   
   
   virtualHostPostTimeoutSecs OBJECT-TYPE
      SYNTAX      INTEGER
      MAX-ACCESS  read-only
      STATUS      current
      DESCRIPTION "Timeout (in seconds) for reading HTTP POST data in a servlet request. If the POST data is chunked, the amount of time the server waits between the end of receiving the last chunk of data and the end of receiving the next chunk of data in an HTTP POST before it times out. (This is used to prevent denial-of-service attacks that attempt to overload the server with POST data.)  Gets the postTimeoutSecs attribute of the WebServerMBean object "
      ::= { virtualHostEntry 90  }
   
   
   virtualHostMaxPostTimeSecs OBJECT-TYPE
      SYNTAX      INTEGER
      MAX-ACCESS  read-only
      STATUS      current
      DESCRIPTION "Max Post Time (in seconds) for reading HTTP POST data in a servlet request. MaxPostTime &lt; 0 means unlimited  Gets the maxPostTimeSecs attribute of the WebServerMBean object "
      ::= { virtualHostEntry 95  }
   
   
   virtualHostMaxPostSize OBJECT-TYPE
      SYNTAX      INTEGER
      MAX-ACCESS  read-only
      STATUS      current
      DESCRIPTION "The maximum post size this server allows for reading HTTP POST and PUT data in a servlet request.  A value less than 0 indicates an unlimited size.  Gets the maxPostSize attribute of the WebServerMBean object "
      ::= { virtualHostEntry 100  }
   
   
   virtualHostWAPEnabled OBJECT-TYPE
      SYNTAX      INTEGER
                  {
                     true(1),
                     false(2)
                  }
      
      MAX-ACCESS  read-only
      STATUS      current
      DESCRIPTION "Indicates whether the session ID should include JVM information. (Checking this box may be necessary when using URL rewriting with WAP devices that limit the size of the URL to 128 characters, and may also affect the use of replicated sessions in a cluster.) When this box is selected, the default size of the URL will be set at 52 characters, and it will not contain any special characters.  Gets the WAPEnabled attribute of the WebServerMBean object "
      ::= { virtualHostEntry 115  }
   
   
   virtualHostVirtualHostNames OBJECT-TYPE
      SYNTAX      DisplayString (SIZE (1..256))
      MAX-ACCESS  read-only
      STATUS      current
      DESCRIPTION "The list of host names, separated by line breaks, for which this virtual host will serve requests. "
      ::= { virtualHostEntry 130  }
   
   
   virtualHostFrontendHTTPPort OBJECT-TYPE
      SYNTAX      INTEGER
      MAX-ACCESS  read-only
      STATUS      current
      DESCRIPTION "The name of the HTTP port to which all redirected URLs will be sent. If specified, WebLogic Server will use this value rather than the one in the HOST header.  Sets the frontendHTTPPort Provides a method to ensure that the webapp will always have the correct PORT information, even when the request is coming through a firewall or a proxy. If this parameter is configured, the HOST header will be ignored and the information in this parameter will be used in its place. "
      ::= { virtualHostEntry 131  }
   
   
   virtualHostAuthCookieEnabled OBJECT-TYPE
      SYNTAX      OCTET STRING
      MAX-ACCESS  read-only
      STATUS      current
      DESCRIPTION "Whether authcookie feature is enabled or not. "
      ::= { virtualHostEntry 132  }
   
   
   virtualHostSingleSignonDisabled OBJECT-TYPE
      SYNTAX      OCTET STRING
      MAX-ACCESS  read-only
      STATUS      current
      DESCRIPTION "Indicates whether the singleSignonDisabled attribute is enabled "
      ::= { virtualHostEntry 133  }
   
   
   virtualHostChunkedTransferDisabled OBJECT-TYPE
      SYNTAX      OCTET STRING
      MAX-ACCESS  read-only
      STATUS      current
      DESCRIPTION "Indicates whether the use of Chunk Transfer-Encoding in HTTP/1.1 is enabled. "
      ::= { virtualHostEntry 134  }
   
   
   virtualHostAcceptContextPathInGetRealPath OBJECT-TYPE
      SYNTAX      OCTET STRING
      MAX-ACCESS  read-only
      STATUS      current
      DESCRIPTION "Indicates whether this server allows the inclusion of the context path in the virtual path to context.getRealPath(). (If checked, you cannot use sub directories with the same name as contextPath). This is a compatibility switch that will be deprecated 9.0.0.0 in future releases.  Gets the acceptContextPathInGetRealPath attribute of the WebServerMBean object "
      ::= { virtualHostEntry 135  }
   
   
   virtualHostOverloadResponseCode OBJECT-TYPE
      SYNTAX      INTEGER
      MAX-ACCESS  read-only
      STATUS      current
      DESCRIPTION "Get the response code to be used when an application is overloaded. An application can get overloaded when the number of pending requests has reached the max capacity specified in the WorkManager or when the server is low on memory. The low memory condition is determined using {@link OverloadProtectionMBean#getFreeMemoryPercentLowThreshold()}. "
      ::= { virtualHostEntry 136  }
   
   
   virtualHostDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { virtualHostEntry 137  }
   
   
   virtualHostNetworkAccessPoint OBJECT-TYPE
      SYNTAX      OCTET STRING
      MAX-ACCESS  read-only
      STATUS      current
      DESCRIPTION "The dedicated server channel name (NetworkAccessPoint) for which this virtual host will serve http request. If the NetworkAccessPoint for a given http request doesn't match any virtual host's NetworkAccessPoint, incoming HOST header will be matched with the VirtualHostNames in order to resolve the right virtual host.  "
      ::= { virtualHostEntry 138  }
   
   
   virtualHostSendServerHeaderEnabled OBJECT-TYPE
      SYNTAX      OCTET STRING
      MAX-ACCESS  read-only
      STATUS      current
      DESCRIPTION "Indicates whether this server name is sent with the HTTP response. (This is useful for wireless applications where there is limited space for headers.)  Indicates whether this server instance includes its name and WebLogic Server version number in HTTP response headers. "
      ::= { virtualHostEntry 139  }
   
   
   virtualHostFrontendHost OBJECT-TYPE
      SYNTAX      OCTET STRING
      MAX-ACCESS  read-only
      STATUS      current
      DESCRIPTION "The name of the host to which all redirected URLs will be sent. If specified, WebLogic Server will use this value rather than the one in the HOST header.  Sets the HTTP frontendHost Provides a method to ensure that the webapp will always have the correct HOST information, even when the request is coming through a firewall or a proxy. If this parameter is configured, the HOST header will be ignored and the information in this parameter will be used in its place. "
      ::= { virtualHostEntry 140  }
   
   
   virtualHostWriteChunkBytes OBJECT-TYPE
      SYNTAX      INTEGER
      MAX-ACCESS  read-only
      STATUS      current
      DESCRIPTION "The default size of the blocks to be written to the network layer.  Gets the writeChunkBytes attribute of the WebServerMBean object "
      ::= { virtualHostEntry 141  }
   
   
   virtualHostFrontendHTTPSPort OBJECT-TYPE
      SYNTAX      INTEGER
      MAX-ACCESS  read-only
      STATUS      current
      DESCRIPTION "The name of the secure HTTP port to which all redirected URLs will be sent. If specified, WebLogic Server will use this value rather than the one in the HOST header.  Sets the frontendHTTPSPort Provides a method to ensure that the webapp will always have the correct PORT information, even when the request is coming through a firewall or a proxy. If this parameter is configured, the HOST header will be ignored and the information in this parameter will be used in its place. "
      ::= { virtualHostEntry 142  }
   
   
   virtualHostUseHeaderEncoding OBJECT-TYPE
      SYNTAX      OCTET STRING
      MAX-ACCESS  read-only
      STATUS      current
      DESCRIPTION " "
      ::= { virtualHostEntry 143  }
   
   
   virtualHostUseHighestCompatibleHTTPVersion OBJECT-TYPE
      SYNTAX      OCTET STRING
      MAX-ACCESS  read-only
      STATUS      current
      DESCRIPTION "Enables use of the highest compatible HTTP protocol version-string in the response. E.g. HTTP spec suggests that HTTP/1.1 version-string should be used in response to a request using HTTP/1.0. This does not necessarily affect the response format. "
      ::= { virtualHostEntry 144  }
   
   
   virtualHostDefaultWebAppContextRoot OBJECT-TYPE
      SYNTAX      OCTET STRING
      MAX-ACCESS  read-only
      STATUS      current
      DESCRIPTION "Returns the original context-root for the default Web application for this Web server. Alternatively, you can use the context-root attributes in application.xml or weblogic.xml to set a default Web application. The context-root for a default Web application is /. If '' (empty string) is specified, the Web server defaults to /. "
      ::= { virtualHostEntry 145  }
   
   
   virtualHostClientIpHeader OBJECT-TYPE
      SYNTAX      OCTET STRING
      MAX-ACCESS  read-only
      STATUS      current
      DESCRIPTION "Get the Client IP Header from WebSerevrMBean. "
      ::= { virtualHostEntry 146  }
   
   
   virtualHostMaxRequestParameterCount OBJECT-TYPE
      SYNTAX      INTEGER
      MAX-ACCESS  read-only
      STATUS      current
      DESCRIPTION "Max Request Parameter Count this server allows for reading maximum HTTP POST Parameters count in a servlet request.  Gets the maxRequestParameterCount attribute of the WebServerMBean object "
      ::= { virtualHostEntry 147  }
   
   
   virtualHostTags OBJECT-TYPE
      SYNTAX      OCTET STRING
      MAX-ACCESS  read-only
      STATUS      current
      DESCRIPTION "Return all tags on this Configuration MBean "
      ::= { virtualHostEntry 148  }
   
   
   xmlEntityCacheTable OBJECT-TYPE
      SYNTAX      SEQUENCE OF XmlEntityCacheEntry
      MAX-ACCESS  not-accessible
      STATUS      current
      DESCRIPTION "Configure the behavior of JAXP (Java API for XML Parsing) in the server. "
      ::= { wls 794  }
      
   
   xmlEntityCacheEntry OBJECT-TYPE
      SYNTAX      XmlEntityCacheEntry
      MAX-ACCESS  not-accessible
      STATUS      current
      DESCRIPTION "Entry of XmlEntityCacheTable"
      INDEX { xmlEntityCacheIndex}
      ::= { xmlEntityCacheTable 1 }
      
   XmlEntityCacheEntry ::=
      SEQUENCE
      {
         xmlEntityCacheIndex  DisplayString,
         xmlEntityCacheObjectName DisplayString,
         xmlEntityCacheType   DisplayString,
         xmlEntityCacheName   DisplayString,
         xmlEntityCacheParent DisplayString,
         xmlEntityCacheCacheMemorySize INTEGER,
         xmlEntityCacheCacheDiskSize INTEGER,
         xmlEntityCacheCacheTimeoutInterval INTEGER,
         xmlEntityCacheCacheLocation OCTET STRING,
         xmlEntityCacheMaxSize INTEGER,
         xmlEntityCacheTags   OCTET STRING
      }
      
   
   xmlEntityCacheIndex OBJECT-TYPE
      SYNTAX      DisplayString (SIZE (1..16))
      MAX-ACCESS  read-only
      STATUS      current
      DESCRIPTION "Unique value directed from ObjectName which is used as table index"
      ::= { xmlEntityCacheEntry 1  }
   
   
   xmlEntityCacheObjectName OBJECT-TYPE
      SYNTAX      DisplayString (SIZE (1..256))
      MAX-ACCESS  read-only
      STATUS      current
      DESCRIPTION "JMX-standard MBean name"
      ::= { xmlEntityCacheEntry 5  }
   
   
   xmlEntityCacheType OBJECT-TYPE
      SYNTAX      DisplayString (SIZE (1..64))
      MAX-ACCESS  read-only
      STATUS      current
      DESCRIPTION "Returns the type of the MBean. "
      ::= { xmlEntityCacheEntry 10  }
   
   
   xmlEntityCacheName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { xmlEntityCacheEntry 15  }
   
   
   xmlEntityCacheParent OBJECT-TYPE
      SYNTAX      DisplayString (SIZE (1..256))
      MAX-ACCESS  read-only
      STATUS      current
      DESCRIPTION "BEA-proprietary Parent object's identification, with syntax
      <type>:<name>"
      ::= { xmlEntityCacheEntry 20  }
   
   
   xmlEntityCacheCacheMemorySize OBJECT-TYPE
      SYNTAX      INTEGER
      MAX-ACCESS  read-only
      STATUS      current
      DESCRIPTION "The memory size, in KB, of the cache. The default value is 500 KB.  Return the memory size in KBytes of the cache. "
      ::= { xmlEntityCacheEntry 25  }
   
   
   xmlEntityCacheCacheDiskSize OBJECT-TYPE
      SYNTAX      INTEGER
      MAX-ACCESS  read-only
      STATUS      current
      DESCRIPTION "The disk size, in MB, of the persistent disk cache. The default value is 5 MB.  Return the disk size in MBytes of the cache. "
      ::= { xmlEntityCacheEntry 30  }
   
   
   xmlEntityCacheCacheTimeoutInterval OBJECT-TYPE
      SYNTAX      INTEGER
      MAX-ACCESS  read-only
      STATUS      current
      DESCRIPTION "The default timeout interval, in seconds, for the cache. The default value is 120 seconds.  Return the default timeout interval in seconds for the cache. "
      ::= { xmlEntityCacheEntry 35  }
   
   
   xmlEntityCacheCacheLocation OBJECT-TYPE
      SYNTAX      OCTET STRING
      MAX-ACCESS  read-only
      STATUS      current
      DESCRIPTION "Provides the path name for the persistent cache files. "
      ::= { xmlEntityCacheEntry 36  }
   
   
   xmlEntityCacheMaxSize OBJECT-TYPE
      SYNTAX      INTEGER
      MAX-ACCESS  read-only
      STATUS      current
      DESCRIPTION "Provides the maximum number of entries that can be stored in the cache at any given time. "
      ::= { xmlEntityCacheEntry 37  }
   
   
   xmlEntityCacheTags OBJECT-TYPE
      SYNTAX      OCTET STRING
      MAX-ACCESS  read-only
      STATUS      current
      DESCRIPTION "Return all tags on this Configuration MBean "
      ::= { xmlEntityCacheEntry 38  }
   
   
   xmlEntitySpecRegistryTable OBJECT-TYPE
      SYNTAX      SEQUENCE OF XmlEntitySpecRegistryEntry
      MAX-ACCESS  not-accessible
      STATUS      current
      DESCRIPTION "An Entity Spec Entry specifies how to resolve an external entity based its public and system IDs.  When WebLogic Server is parsing an XML document and it encounters the specified external entity, WebLogic Server resolves the entity according to the values entered for this entry.  You can specify that the external entity resolve to a particular resource whose location is either a pathname reachable by the Administration Server or a URI to a local repository.  An Entity Spec entry is part of an XML Registry.  For this type of registry entry the document type is identified by either or both of:   a public ID (e.g, '-//Sun Microsystems, Inc.//DTD Enterprise JavaBeans 2.0//EN' a system ID (e.g, 'http://java.sun.com/j2ee/dtds/ejb-jar_2_0.dtd')   This configuration information is used by the WebLogic JAXP implementation to set up SAX EntityResolvers. "
      ::= { wls 796  }
      
   
   xmlEntitySpecRegistryEntry OBJECT-TYPE
      SYNTAX      XmlEntitySpecRegistryEntry
      MAX-ACCESS  not-accessible
      STATUS      current
      DESCRIPTION "Entry of XmlEntitySpecRegistryTable"
      INDEX { xmlEntitySpecRegistryIndex}
      ::= { xmlEntitySpecRegistryTable 1 }
      
   XmlEntitySpecRegistryEntry ::=
      SEQUENCE
      {
         xmlEntitySpecRegistryIndex DisplayString,
         xmlEntitySpecRegistryObjectName DisplayString,
         xmlEntitySpecRegistryType DisplayString,
         xmlEntitySpecRegistryName DisplayString,
         xmlEntitySpecRegistryParent DisplayString,
         xmlEntitySpecRegistryPublicId DisplayString,
         xmlEntitySpecRegistrySystemId DisplayString,
         xmlEntitySpecRegistryEntityURI DisplayString,
         xmlEntitySpecRegistryWhenToCache DisplayString,
         xmlEntitySpecRegistryCacheTimeoutInterval INTEGER,
         xmlEntitySpecRegistryHandleEntityInvalidation OCTET STRING,
         xmlEntitySpecRegistryTags OCTET STRING
      }
      
   
   xmlEntitySpecRegistryIndex OBJECT-TYPE
      SYNTAX      DisplayString (SIZE (1..16))
      MAX-ACCESS  read-only
      STATUS      current
      DESCRIPTION "Unique value directed from ObjectName which is used as table index"
      ::= { xmlEntitySpecRegistryEntry 1  }
   
   
   xmlEntitySpecRegistryObjectName OBJECT-TYPE
      SYNTAX      DisplayString (SIZE (1..256))
      MAX-ACCESS  read-only
      STATUS      current
      DESCRIPTION "JMX-standard MBean name"
      ::= { xmlEntitySpecRegistryEntry 5  }
   
   
   xmlEntitySpecRegistryType OBJECT-TYPE
      SYNTAX      DisplayString (SIZE (1..64))
      MAX-ACCESS  read-only
      STATUS      current
      DESCRIPTION "Returns the type of the MBean. "
      ::= { xmlEntitySpecRegistryEntry 10  }
   
   
   xmlEntitySpecRegistryName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { xmlEntitySpecRegistryEntry 15  }
   
   
   xmlEntitySpecRegistryParent OBJECT-TYPE
      SYNTAX      DisplayString (SIZE (1..256))
      MAX-ACCESS  read-only
      STATUS      current
      DESCRIPTION "BEA-proprietary Parent object's identification, with syntax
      <type>:<name>"
      ::= { xmlEntitySpecRegistryEntry 20  }
   
   
   xmlEntitySpecRegistryPublicId OBJECT-TYPE
      SYNTAX      DisplayString (SIZE (1..256))
      MAX-ACCESS  read-only
      STATUS      current
      DESCRIPTION "The public ID of the external entity.  When WebLogic Server is parsing an XML document and it encounters an external entity with this public ID, WebLogic Server resolves the entity (to either a local file or a URL resource) according to the values set for this Entity spec entry. "
      ::= { xmlEntitySpecRegistryEntry 25  }
   
   
   xmlEntitySpecRegistrySystemId OBJECT-TYPE
      SYNTAX      DisplayString (SIZE (1..256))
      MAX-ACCESS  read-only
      STATUS      current
      DESCRIPTION "The system ID of the external entity.  When WebLogic Server is parsing an XML document and it encounters an external entity with this system ID, WebLogic Server resolves the entity (to either a local file or a URL resource) according to the values set for this Entity spec entry. "
      ::= { xmlEntitySpecRegistryEntry 30  }
   
   
   xmlEntitySpecRegistryEntityURI OBJECT-TYPE
      SYNTAX      DisplayString (SIZE (1..256))
      MAX-ACCESS  read-only
      STATUS      current
      DESCRIPTION "The location of the external entity, either a pathname or URI.  The location of the external entity can be either a pathname relative to the XML Registry directories, reachable by the Administration Server, or a URI of the entity location in some local repository. "
      ::= { xmlEntitySpecRegistryEntry 35  }
   
   
   xmlEntitySpecRegistryWhenToCache OBJECT-TYPE
      SYNTAX      DisplayString (SIZE (1..256))
      MAX-ACCESS  read-only
      STATUS      current
      DESCRIPTION "Specifies when WebLogic Server should cache the external entities it retrieves from the Web.  WebLogic Server can cache the entities when they are referenced, as soon as possible (that is, on initialization) or never. Additionally, WebLogic Server can defer to the XML registry's cache setting. "
      ::= { xmlEntitySpecRegistryEntry 40  }
   
   
   xmlEntitySpecRegistryCacheTimeoutInterval OBJECT-TYPE
      SYNTAX      INTEGER
      MAX-ACCESS  read-only
      STATUS      current
      DESCRIPTION "Specifies the default timeout interval (in seconds) of the external entity cache.  A value of -1 means that the entity cache timeout interval defers to the one specified for the XML registry of which this Entity Spec entry is a part. "
      ::= { xmlEntitySpecRegistryEntry 45  }
   
   
   xmlEntitySpecRegistryHandleEntityInvalidation OBJECT-TYPE
      SYNTAX      OCTET STRING
      MAX-ACCESS  read-only
      STATUS      current
      DESCRIPTION "Whether cached DTD/schema is invalidated when parsing error is encountered. "
      ::= { xmlEntitySpecRegistryEntry 46  }
   
   
   xmlEntitySpecRegistryTags OBJECT-TYPE
      SYNTAX      OCTET STRING
      MAX-ACCESS  read-only
      STATUS      current
      DESCRIPTION "Return all tags on this Configuration MBean "
      ::= { xmlEntitySpecRegistryEntry 47  }
   
   
   xmlParserSelectRegistryTable OBJECT-TYPE
      SYNTAX      SEQUENCE OF XmlParserSelectRegistryEntry
      MAX-ACCESS  not-accessible
      STATUS      current
      DESCRIPTION "A Parser Select Entry specifies the SAX/DOM parser factory implementation classes for a particular document type.  By default, WebLogic server uses either the built-in (out-of-the-box) or default SAX/DOM parser factory implementation classes when it parses an XML document.  However, you can specify that particular XML documents, based on their public IDs, system IDs, or root elements, use different parser factory implementation classes than the default.  You do this by first creating an XML Registry and then creating a Parser Select entry and specifying how to identify the document and then the desired implementation classes.   The XML document type is identified by one or more of the following:    a public ID (e.g, '-//Sun Microsystems, Inc.//DTD Enterprise JavaBeans 2.0//EN' a system ID (e.g, 'http://java.sun.com/j2ee/dtds/ejb-jar_2_0.dtd') a document root tag name (e.g., 'ejb-jar')   This configuration information is used by the WebLogic JAXP implementation to choose the appropriate parser factories (SAX and DOM). "
      ::= { wls 798  }
      
   
   xmlParserSelectRegistryEntry OBJECT-TYPE
      SYNTAX      XmlParserSelectRegistryEntry
      MAX-ACCESS  not-accessible
      STATUS      current
      DESCRIPTION "Entry of XmlParserSelectRegistryTable"
      INDEX { xmlParserSelectRegistryIndex}
      ::= { xmlParserSelectRegistryTable 1 }
      
   XmlParserSelectRegistryEntry ::=
      SEQUENCE
      {
         xmlParserSelectRegistryIndex DisplayString,
         xmlParserSelectRegistryObjectName DisplayString,
         xmlParserSelectRegistryType DisplayString,
         xmlParserSelectRegistryName DisplayString,
         xmlParserSelectRegistryParent DisplayString,
         xmlParserSelectRegistryPublicId DisplayString,
         xmlParserSelectRegistrySystemId DisplayString,
         xmlParserSelectRegistryRootElementTag DisplayString,
         xmlParserSelectRegistryDocumentBuilderFactory DisplayString,
         xmlParserSelectRegistrySAXParserFactory DisplayString,
         xmlParserSelectRegistryTransformerFactory DisplayString,
         xmlParserSelectRegistryParserClassName OCTET STRING,
         xmlParserSelectRegistryTags OCTET STRING
      }
      
   
   xmlParserSelectRegistryIndex OBJECT-TYPE
      SYNTAX      DisplayString (SIZE (1..16))
      MAX-ACCESS  read-only
      STATUS      current
      DESCRIPTION "Unique value directed from ObjectName which is used as table index"
      ::= { xmlParserSelectRegistryEntry 1  }
   
   
   xmlParserSelectRegistryObjectName OBJECT-TYPE
      SYNTAX      DisplayString (SIZE (1..256))
      MAX-ACCESS  read-only
      STATUS      current
      DESCRIPTION "JMX-standard MBean name"
      ::= { xmlParserSelectRegistryEntry 5  }
   
   
   xmlParserSelectRegistryType OBJECT-TYPE
      SYNTAX      DisplayString (SIZE (1..64))
      MAX-ACCESS  read-only
      STATUS      current
      DESCRIPTION "Returns the type of the MBean. "
      ::= { xmlParserSelectRegistryEntry 10  }
   
   
   xmlParserSelectRegistryName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { xmlParserSelectRegistryEntry 15  }
   
   
   xmlParserSelectRegistryParent OBJECT-TYPE
      SYNTAX      DisplayString (SIZE (1..256))
      MAX-ACCESS  read-only
      STATUS      current
      DESCRIPTION "BEA-proprietary Parent object's identification, with syntax
      <type>:<name>"
      ::= { xmlParserSelectRegistryEntry 20  }
   
   
   xmlParserSelectRegistryPublicId OBJECT-TYPE
      SYNTAX      DisplayString (SIZE (1..256))
      MAX-ACCESS  read-only
      STATUS      current
      DESCRIPTION "Specifies the public ID of the XML document type for which this XML registry entry is being configured.  When WebLogic Server starts to parse an XML document that is identified with this public ID, it uses the SAX or DOM parser factory implementation class specified by this registry entry, rather than the built-in or default, when obtaining a SAX or DOM parser. "
      ::= { xmlParserSelectRegistryEntry 25  }
   
   
   xmlParserSelectRegistrySystemId OBJECT-TYPE
      SYNTAX      DisplayString (SIZE (1..256))
      MAX-ACCESS  read-only
      STATUS      current
      DESCRIPTION "Specifies the system ID of the XML document type for which this XML registry entry is being configured.  When WebLogic Server starts to parse an XML document that is identified with this system ID, it uses the SAX or DOM parser factory implementation class specified by this registry entry, rather than the built-in or default, when obtaining a SAX or DOM parser. "
      ::= { xmlParserSelectRegistryEntry 30  }
   
   
   xmlParserSelectRegistryRootElementTag OBJECT-TYPE
      SYNTAX      DisplayString (SIZE (1..256))
      MAX-ACCESS  read-only
      STATUS      current
      DESCRIPTION "Specifies the root element of the XML document type for which this XML registry entry is being configured.  When WebLogic Server starts to parse an XML document that is identified with this root element, it uses the SAX or DOM parser factory implementation class specified by this registry entry, rather than the built-in or default, when obtaining a SAX or DOM parser. "
      ::= { xmlParserSelectRegistryEntry 35  }
   
   
   xmlParserSelectRegistryDocumentBuilderFactory OBJECT-TYPE
      SYNTAX      DisplayString (SIZE (1..256))
      MAX-ACCESS  read-only
      STATUS      current
      DESCRIPTION "Specifies the fully qualified name of the class that implements the DocumentBuilderFactory API  When WebLogic Server begins to parse an XML document identified by either the public ID, system ID, or root element specified in this entry, and the applications specifies it wants a DOM parser, then WebLogic Server uses this implementation class when using the javax.xml.parsers.DocumentBuilderFactory to obtain the DOM parser. "
      ::= { xmlParserSelectRegistryEntry 40  }
   
   
   xmlParserSelectRegistrySAXParserFactory OBJECT-TYPE
      SYNTAX      DisplayString (SIZE (1..256))
      MAX-ACCESS  read-only
      STATUS      current
      DESCRIPTION "Specifies the fully qualified name of the class that implements the SAXParserFactory API.  When WebLogic Server begins to parse an XML document identified by either the public ID, system ID, or root element specified in this entry, and the applications specifies it wants a SAX parser, then WebLogic Server uses this implementation class when using the javax.xml.parsers.SAXParserFactory to obtain the SAX parser. "
      ::= { xmlParserSelectRegistryEntry 45  }
   
   
   xmlParserSelectRegistryTransformerFactory OBJECT-TYPE
      SYNTAX      DisplayString (SIZE (1..256))
      MAX-ACCESS  read-only
      STATUS      current
      DESCRIPTION "Specifies the fully qualified name of the class that implements the TransformerFactory API.  When WebLogic Server begins to transform an XML document identified by either the public ID, system ID, or root element specified in this entry, then WebLogic Server uses this implementation class when using the javax.xml.transform.TranformerFactory factory to obtain a Transformer object. "
      ::= { xmlParserSelectRegistryEntry 50  }
   
   
   xmlParserSelectRegistryParserClassName OBJECT-TYPE
      SYNTAX      OCTET STRING
      MAX-ACCESS  read-only
      STATUS      current
      DESCRIPTION "Provides the class name of any custom XML parser that is associated with this parser select entry.  Return class name of any custom XML parser that is associated with the registry entry. "
      ::= { xmlParserSelectRegistryEntry 51  }
   
   
   xmlParserSelectRegistryTags OBJECT-TYPE
      SYNTAX      OCTET STRING
      MAX-ACCESS  read-only
      STATUS      current
      DESCRIPTION "Return all tags on this Configuration MBean "
      ::= { xmlParserSelectRegistryEntry 52  }
   
   
   xmlRegistryTable OBJECT-TYPE
      SYNTAX      SEQUENCE OF XmlRegistryEntry
      MAX-ACCESS  not-accessible
      STATUS      current
      DESCRIPTION "Configure the behavior of JAXP (Java API for XML Parsing) in the server.  You configure this behavior by creating XML Registries that specify the default DOM and Sax factory implementation class, transformer factory implementation class, external entity resolution and caching. "
      ::= { wls 800  }
      
   
   xmlRegistryEntry OBJECT-TYPE
      SYNTAX      XmlRegistryEntry
      MAX-ACCESS  not-accessible
      STATUS      current
      DESCRIPTION "Entry of XmlRegistryTable"
      INDEX { xmlRegistryIndex}
      ::= { xmlRegistryTable 1 }
      
   XmlRegistryEntry ::=
      SEQUENCE
      {
         xmlRegistryIndex     DisplayString,
         xmlRegistryObjectName DisplayString,
         xmlRegistryType      DisplayString,
         xmlRegistryName      DisplayString,
         xmlRegistryParent    DisplayString,
         xmlRegistryDocumentBuilderFactory DisplayString,
         xmlRegistrySAXParserFactory DisplayString,
         xmlRegistryTransformerFactory DisplayString,
         xmlRegistryWhenToCache DisplayString,
         xmlRegistryHandleEntityInvalidation OCTET STRING,
         xmlRegistryXMLInputFactory OCTET STRING,
         xmlRegistrySchemaFactory OCTET STRING,
         xmlRegistryXMLEventFactory OCTET STRING,
         xmlRegistryXpathFactory OCTET STRING,
         xmlRegistryXMLOutputFactory OCTET STRING,
         xmlRegistryTags      OCTET STRING
      }
      
   
   xmlRegistryIndex OBJECT-TYPE
      SYNTAX      DisplayString (SIZE (1..16))
      MAX-ACCESS  read-only
      STATUS      current
      DESCRIPTION "Unique value directed from ObjectName which is used as table index"
      ::= { xmlRegistryEntry 1  }
   
   
   xmlRegistryObjectName OBJECT-TYPE
      SYNTAX      DisplayString (SIZE (1..256))
      MAX-ACCESS  read-only
      STATUS      current
      DESCRIPTION "JMX-standard MBean name"
      ::= { xmlRegistryEntry 5  }
   
   
   xmlRegistryType OBJECT-TYPE
      SYNTAX      DisplayString (SIZE (1..64))
      MAX-ACCESS  read-only
      STATUS      current
      DESCRIPTION "Returns the type of the MBean. "
      ::= { xmlRegistryEntry 10  }
   
   
   xmlRegistryName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { xmlRegistryEntry 15  }
   
   
   xmlRegistryParent OBJECT-TYPE
      SYNTAX      DisplayString (SIZE (1..256))
      MAX-ACCESS  read-only
      STATUS      current
      DESCRIPTION "BEA-proprietary Parent object's identification, with syntax
      <type>:<name>"
      ::= { xmlRegistryEntry 20  }
   
   
   xmlRegistryDocumentBuilderFactory OBJECT-TYPE
      SYNTAX      DisplayString (SIZE (1..256))
      MAX-ACCESS  read-only
      STATUS      current
      DESCRIPTION "The fully qualified name of the class that implements the DocumentBuilderFactory interface.  The javax.xml.parsers.DocumentBuilderFactory factory API enables applications deployed to WebLogic Server to obtain an XML parser that produces DOM object trees from XML documents.  The built-in WebLogic Server DOM factory implementation class is com.sun.org.apache.xerces.internal.jaxp.DocumentBuilderFactoryImpl. This is the factory class applications deployed to WebLogic Server get by default when they request a DOM parser.  You can change this default by updating this value.  Return the class name of the default DocumentBuilderFactory "
      ::= { xmlRegistryEntry 40  }
   
   
   xmlRegistrySAXParserFactory OBJECT-TYPE
      SYNTAX      DisplayString (SIZE (1..256))
      MAX-ACCESS  read-only
      STATUS      current
      DESCRIPTION "The fully qualified name of the class that implements the SAXParserFactory interface.  The javax.xml.parsers.SAXParserFactory factory API enables applications deployed to WebLogic Server to configure and obtain a SAX-based XML parser to parse XML documents.  The built-in WebLogic Server SAX factory implementation class is com.sun.org.apache.xerces.internal.jaxp.SAXParserFactoryImpl. This is the factory class applications deployed to WebLogic Server get by default when they request a SAX parser.  You can change this default by updating this value.  Return the class name of the default SAXParserFactory "
      ::= { xmlRegistryEntry 45  }
   
   
   xmlRegistryTransformerFactory OBJECT-TYPE
      SYNTAX      DisplayString (SIZE (1..256))
      MAX-ACCESS  read-only
      STATUS      current
      DESCRIPTION "The fully qualified name of the class that implements the TransformerFactory interface.  The javax.xml.transform.TransformerFactory factory API enables applications deployed to WebLogic Server to configure and obtain a Transformer object used to transform XML data into another format.  The built-in WebLogic Server Transformer factory implementation class is com.sun.org.apache.xalan.internal.xsltc.trax.TransformerFactoryIml. This is the factory class applications deployed to WebLogic Server get by default when they request a Transformer object.  You can change this default by updating this value.   Return the class name of the default TransformerFactory "
      ::= { xmlRegistryEntry 50  }
   
   
   xmlRegistryWhenToCache OBJECT-TYPE
      SYNTAX      DisplayString (SIZE (1..256))
      MAX-ACCESS  read-only
      STATUS      current
      DESCRIPTION "Specifies when WebLogic Server should cache external entities that it retrieves from the Web.  When WebLogic Server resolves an external entity within an XML file and retrieves the entity from the Web, you can specify that WebLogic Server cache this entity only when the entity is first referenced, when WebLogic Server first starts up, or not at all. "
      ::= { xmlRegistryEntry 55  }
   
   
   xmlRegistryHandleEntityInvalidation OBJECT-TYPE
      SYNTAX      OCTET STRING
      MAX-ACCESS  read-only
      STATUS      current
      DESCRIPTION "Whether cached DTD/schema is invalidated when parsing error is encountered. "
      ::= { xmlRegistryEntry 56  }
   
   
   xmlRegistryXMLInputFactory OBJECT-TYPE
      SYNTAX      OCTET STRING
      MAX-ACCESS  read-only
      STATUS      current
      DESCRIPTION "The fully qualified name of the class that implements the XMLInputFactory interface.  The javax.xml.stream.XMLInputFactory factory API enables applications deployed to WebLogic Server to configure and obtain a XMLEventReader/XMLStreamReader object used to read XML streams.  The built-in WebLogic Server XML Input factory implementation class is com.ctc.wstx.stax.WstxInputFactory. This is the factory class applications deployed to WebLogic Server get by default when they request a XMLEventReader/XMLStreamReader object. You can change this default by updating this value.   Return the class name of the default XMLInputFactory "
      ::= { xmlRegistryEntry 57  }
   
   
   xmlRegistrySchemaFactory OBJECT-TYPE
      SYNTAX      OCTET STRING
      MAX-ACCESS  read-only
      STATUS      current
      DESCRIPTION "The fully qualified name of the class that implements the SchemaFactory interface.  The javax.xml.validation.SchemaFactory factory API enables applications deployed to WebLogic Server to configure and obtain a Schema object used to validate XML document using schema.  The built-in WebLogic Server Schema factory implementation class is com.sun.org.apache.xerces.internal.jaxp.validation.XMLSchemaFactory. This is the factory class applications deployed to WebLogic Server get by default when they request a Schema object.  You can change this default by updating this value.   Return the class name of the default SchemaFactory "
      ::= { xmlRegistryEntry 58  }
   
   
   xmlRegistryXMLEventFactory OBJECT-TYPE
      SYNTAX      OCTET STRING
      MAX-ACCESS  read-only
      STATUS      current
      DESCRIPTION "The fully qualified name of the class that implements the XMLEventFactory interface.  The javax.xml.stream.XMLEventFactory factory API enables applications deployed to WebLogic Server to configure and obtain a XMLEvent object used to parse or build XML streams.  The built-in WebLogic Server XMLEvent factory implementation class is com.ctc.wstx.stax.WstxEventFactory. This is the factory class applications deployed to WebLogic Server get by default when they request a XMLEvent object.  You can change this default by updating this value.   Return the class name of the default XMLEventFactory "
      ::= { xmlRegistryEntry 59  }
   
   
   xmlRegistryXpathFactory OBJECT-TYPE
      SYNTAX      OCTET STRING
      MAX-ACCESS  read-only
      STATUS      current
      DESCRIPTION "The fully qualified name of the class that implements the XPathFactory interface.  The javax.xml.xpath.XPathFactory factory API enables applications deployed to WebLogic Server to configure and obtain a XPath object used to search XML elements.  The built-in WebLogic Server XPath factory implementation class is com.sun.org.apache.xpath.internal.jaxp.XPathFactoryImpl. This is the factory class applications deployed to WebLogic Server get by default when they request a XPath object.  You can change this default by updating this value.   Return the class name of the default XPathFactory "
      ::= { xmlRegistryEntry 60  }
   
   
   xmlRegistryXMLOutputFactory OBJECT-TYPE
      SYNTAX      OCTET STRING
      MAX-ACCESS  read-only
      STATUS      current
      DESCRIPTION "The fully qualified name of the class that implements the XMLOutputFactory interface.  The javax.xml.stream.XMLOutputFactory factory API enables applications deployed to WebLogic Server to configure and obtain a XMLEventWriter/XMLStreamWriter object used to write XML streams.  The built-in WebLogic Server XML Output factory implementation class is com.ctc.wstx.stax.WstxOutputFactory. This is the factory class applications deployed to WebLogic Server get by default when they request a XMLEventWriter/XMLStreamWriter object. You can change this default by updating this value.   Return the class name of the default XMLOutputFactory "
      ::= { xmlRegistryEntry 61  }
   
   
   xmlRegistryTags OBJECT-TYPE
      SYNTAX      OCTET STRING
      MAX-ACCESS  read-only
      STATUS      current
      DESCRIPTION "Return all tags on this Configuration MBean "
      ::= { xmlRegistryEntry 62  }
   
   
   wtctBridgeGlobalTable OBJECT-TYPE
      SYNTAX      SEQUENCE OF WtctBridgeGlobalEntry
      MAX-ACCESS  not-accessible
      STATUS      current
      DESCRIPTION "This interface provides access to the WTC tBridge Global configuration attributes. The methods defined herein are applicable for tBridge configuration at the WLS domain level. "
      ::= { wls 805  }
      
   
   wtctBridgeGlobalEntry OBJECT-TYPE
      SYNTAX      WtctBridgeGlobalEntry
      MAX-ACCESS  not-accessible
      STATUS      current
      DESCRIPTION "Entry of wtctBridgeGlobalTable"
      INDEX { wtctBridgeGlobalIndex}
      ::= { wtctBridgeGlobalTable 1 }
      
   WtctBridgeGlobalEntry ::=
      SEQUENCE
      {
         wtctBridgeGlobalIndex DisplayString,
         wtctBridgeGlobalObjectName DisplayString,
         wtctBridgeGlobalType DisplayString,
         wtctBridgeGlobalName DisplayString,
         wtctBridgeGlobalParent DisplayString,
         wtctBridgeGlobalAllowNonStandardTypes DisplayString,
         wtctBridgeGlobalDefaultReplyDeliveryMode DisplayString,
         wtctBridgeGlobalDeliveryModeOverride DisplayString,
         wtctBridgeGlobalJmsFactory DisplayString,
         wtctBridgeGlobalJmsToTuxPriorityMap DisplayString,
         wtctBridgeGlobalJndiFactory DisplayString,
         wtctBridgeGlobalRetries INTEGER,
         wtctBridgeGlobalRetryDelay INTEGER,
         wtctBridgeGlobalTimeout INTEGER,
         wtctBridgeGlobalTransactional DisplayString,
         wtctBridgeGlobalTuxErrorQueue DisplayString,
         wtctBridgeGlobalTuxFactory DisplayString,
         wtctBridgeGlobalTuxToJmsPriorityMap DisplayString,
         wtctBridgeGlobalUserId DisplayString,
         wtctBridgeGlobalWlsErrorDestination DisplayString,
         wtctBridgeGlobalTags OCTET STRING
      }
      
   
   wtctBridgeGlobalIndex OBJECT-TYPE
      SYNTAX      DisplayString (SIZE (1..16))
      MAX-ACCESS  read-only
      STATUS      current
      DESCRIPTION "Unique value directed from ObjectName which is used as table index"
      ::= { wtctBridgeGlobalEntry 1  }
   
   
   wtctBridgeGlobalObjectName OBJECT-TYPE
      SYNTAX      DisplayString (SIZE (1..256))
      MAX-ACCESS  read-only
      STATUS      current
      DESCRIPTION "JMX-standard MBean name"
      ::= { wtctBridgeGlobalEntry 5  }
   
   
   wtctBridgeGlobalType OBJECT-TYPE
      SYNTAX      DisplayString (SIZE (1..64))
      MAX-ACCESS  read-only
      STATUS      current
      DESCRIPTION "Returns the type of the MBean. "
      ::= { wtctBridgeGlobalEntry 10  }
   
   
   wtctBridgeGlobalName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtctBridgeGlobalEntry 15  }
   
   
   wtctBridgeGlobalParent OBJECT-TYPE
      SYNTAX      DisplayString (SIZE (1..256))
      MAX-ACCESS  read-only
      STATUS      current
      DESCRIPTION "BEA-proprietary Parent object's identification, with syntax
      <type>:<name>"
      ::= { wtctBridgeGlobalEntry 20  }
   
   
   wtctBridgeGlobalAllowNonStandardTypes OBJECT-TYPE
      SYNTAX      DisplayString (SIZE (1..256))
      MAX-ACCESS  read-only
      STATUS      current
      DESCRIPTION "Specifies whether non-standard data types are allowed to pass through this Tuxedo queuing bridge.  A value of NO means that non standard types are rejected and placed onto a specified error location; a value of YES means that non-standard types are placed on the target location as BLOBs with a tag indicating the original type.  Note: Standard types are: ASCII text (TextMessage, STRING), or BLOB (BytesMessage, CARRAY). "
      ::= { wtctBridgeGlobalEntry 25  }
   
   
   wtctBridgeGlobalDefaultReplyDeliveryMode OBJECT-TYPE
      SYNTAX      DisplayString (SIZE (1..256))
      MAX-ACCESS  read-only
      STATUS      current
      DESCRIPTION "The reply delivery mode to associate with a message when placing messages onto the target location.  Usage Notes:   Use when messages are being redirected to Tuxedo/Q from JMS and the JMS_BEA_TuxGtway_Tuxedo_ReplyDeliveryMode property is not set for a message.   If the defaultReplyDeliveryMode and JMS_BEA_TuxGtway_Tuxedo_ReplyDeliveryMode are not set, the default semantics defined for Tuxedo are enforced by the Tuxedo/Q subsystem.   "
      ::= { wtctBridgeGlobalEntry 30  }
   
   
   wtctBridgeGlobalDeliveryModeOverride OBJECT-TYPE
      SYNTAX      DisplayString (SIZE (1..256))
      MAX-ACCESS  read-only
      STATUS      current
      DESCRIPTION "The delivery mode to use when placing messages onto the target location.  If this value is not specified, the message is placed on the target location with the same delivery mode specified from the source location.  Note: This value overrides any delivery mode associated with a message. "
      ::= { wtctBridgeGlobalEntry 35  }
   
   
   wtctBridgeGlobalJmsFactory OBJECT-TYPE
      SYNTAX      DisplayString (SIZE (1..256))
      MAX-ACCESS  read-only
      STATUS      current
      DESCRIPTION "The name of the JMS connection factory.  Example: weblogic.jms.ConnectionFactory "
      ::= { wtctBridgeGlobalEntry 40  }
   
   
   wtctBridgeGlobalJmsToTuxPriorityMap OBJECT-TYPE
      SYNTAX      DisplayString (SIZE (1..256))
      MAX-ACCESS  read-only
      STATUS      current
      DESCRIPTION "The mapping of priorities from JMS to Tuxedo. The default JMS To Tux Priority Map is: 0:1 | 1:12 | 2:23 | 3:34 | 4:45 |5:56 | 6:67 | 7:78 | 8:89 | 9:100  Examples: 0:1 | 1:12 | 2:23 | 3:34 | 4:45 | 5:56 | 6:67 | 7:78 | 8:89 | 9:100 or 0:1-10|1:11-20|2:21-30|3:31-40|4:41-50|5:51-60|6:61-70|7:71-80|8:81-90|9:91-100  Note: The are 10 possible JMS priorities(0=&gt;9) which can be paired to 100 possible Tuxedo priorities(1=&gt;100). A mapping consists of a '|' separated list of value-to-range pairs (jmsvalue:tuxrange) where pairs are separated by ':' and ranges are separated by '-'. "
      ::= { wtctBridgeGlobalEntry 45  }
   
   
   wtctBridgeGlobalJndiFactory OBJECT-TYPE
      SYNTAX      DisplayString (SIZE (1..256))
      MAX-ACCESS  read-only
      STATUS      current
      DESCRIPTION "The name of the JNDI lookup factory.  Example: weblogic.jndi.WLInitialContextFactory "
      ::= { wtctBridgeGlobalEntry 50  }
   
   
   wtctBridgeGlobalRetries OBJECT-TYPE
      SYNTAX      INTEGER
      MAX-ACCESS  read-only
      STATUS      current
      DESCRIPTION "The number of attempts to redirect a message before this Tuxedo queuing bridge places the message in the specified error location and logs an error.  Range of Values: Between 0 and a positive 32-bit integer. "
      ::= { wtctBridgeGlobalEntry 55  }
   
   
   wtctBridgeGlobalRetryDelay OBJECT-TYPE
      SYNTAX      INTEGER
      MAX-ACCESS  read-only
      STATUS      current
      DESCRIPTION "The minimum number of milliseconds this Tuxedo queuing bridge waits before redirecting a message after a failure.  Note: During this waiting period, no other messages are redirected from the thread. Other threads may continue to redirect messages.  Range of Values: Between 0 and a positive 32-bit integer. "
      ::= { wtctBridgeGlobalEntry 60  }
   
   
   wtctBridgeGlobalTimeout OBJECT-TYPE
      SYNTAX      INTEGER
      MAX-ACCESS  read-only
      STATUS      current
      DESCRIPTION "The number of timeout seconds for an entire redirection when this Tuxedo queuing bridge places a message on the target location. A value of 0 specifies an infinite wait.  Range of Values: Between 0 and a positive 32-bit integer. "
      ::= { wtctBridgeGlobalEntry 65  }
   
   
   wtctBridgeGlobalTransactional OBJECT-TYPE
      SYNTAX      DisplayString (SIZE (1..256))
      MAX-ACCESS  read-only
      STATUS      current
      DESCRIPTION "Specifies whether this Tuxedo queuing bridge should use transactions when retrieving messages from a source location and when placing messages on a target location.  A value of YES means that transactions are used for both operations; a value of NO means that transactions are not used for either operation.  Note: Transactional is not supported in this release. "
      ::= { wtctBridgeGlobalEntry 70  }
   
   
   wtctBridgeGlobalTuxErrorQueue OBJECT-TYPE
      SYNTAX      DisplayString (SIZE (1..256))
      MAX-ACCESS  read-only
      STATUS      current
      DESCRIPTION "The name of the Tuxedo queue used to store a message that cannot be redirected to a Tuxedo/Q source queue.  If not specified, all messages not redirected are lost. If the message cannot be placed into the TuxErrorQueue, an error is logged and the message is lost.  Note: This queue is in the same queue space as the source queue. "
      ::= { wtctBridgeGlobalEntry 75  }
   
   
   wtctBridgeGlobalTuxFactory OBJECT-TYPE
      SYNTAX      DisplayString (SIZE (1..256))
      MAX-ACCESS  read-only
      STATUS      current
      DESCRIPTION "The name of the Tuxedo connection factory.  Example: tuxedo.services.TuxedoConnection "
      ::= { wtctBridgeGlobalEntry 80  }
   
   
   wtctBridgeGlobalTuxToJmsPriorityMap OBJECT-TYPE
      SYNTAX      DisplayString (SIZE (1..256))
      MAX-ACCESS  read-only
      STATUS      current
      DESCRIPTION "The mapping of priorities to map from Tuxedo to JMS. The default JMS To Tux Priority Map is: 1-10:0 | 11-20:1 | 21-30:2 | 31-40:3| 41-50:4| 51-60:5 | 61-70:6 | 71-80:7 | 81-90:8 | 91-100:9  Examples: 1:0 | 12:1 | 23:2 | 34:3 | 45:4 | 56:5 | 67:6 | 78:7 | 89:8 | 100:9 or 20:0-1 | 40:2-3 | 60:4-5 | 80:6-7 | 100:8-9  Note: The are 100 possible Tuxedo priorities(1=&gt;100) which can be paired to 10 possible JMS priorities(0=&gt;9). A mapping consists of a '|' separated list of value-to-range pairs (tuxvalue:jmsrange) where pairs are separated by ':' and ranges are separated by '-'. "
      ::= { wtctBridgeGlobalEntry 85  }
   
   
   wtctBridgeGlobalUserId OBJECT-TYPE
      SYNTAX      DisplayString (SIZE (1..256))
      MAX-ACCESS  read-only
      STATUS      current
      DESCRIPTION "The user identity for all messages handled by this Tuxedo queuing bridge for ACL checks when security is configured.  All messages assume this identity until the security/authentication contexts are passed between the subsystems. Until the security contexts are passed, there is no secure method to identify who generated a message received from the source location.  Note: The user argument may be specified as either a user name or a user identification number (uid). "
      ::= { wtctBridgeGlobalEntry 90  }
   
   
   wtctBridgeGlobalWlsErrorDestination OBJECT-TYPE
      SYNTAX      DisplayString (SIZE (1..256))
      MAX-ACCESS  read-only
      STATUS      current
      DESCRIPTION "The name of the location used to store WebLogic Server JMS messages when a message cannot be redirected.  If not specified, all messages not redirected are lost. If the message cannot be placed into WlsErrorDestination for any reason, an error is logged and the message is lost. "
      ::= { wtctBridgeGlobalEntry 95  }
   
   
   wtctBridgeGlobalTags OBJECT-TYPE
      SYNTAX      OCTET STRING
      MAX-ACCESS  read-only
      STATUS      current
      DESCRIPTION "Return all tags on this Configuration MBean "
      ::= { wtctBridgeGlobalEntry 96  }
   
   
   wtcExportTable OBJECT-TYPE
      SYNTAX      SEQUENCE OF WtcExportEntry
      MAX-ACCESS  not-accessible
      STATUS      current
      DESCRIPTION "This interface provides access to the WTC export configuration attributes.  The methods defined herein are applicable for WTC configuration at the WLS domain level. "
      ::= { wls 810  }
      
   
   wtcExportEntry OBJECT-TYPE
      SYNTAX      WtcExportEntry
      MAX-ACCESS  not-accessible
      STATUS      current
      DESCRIPTION "Entry of wtcExportTable"
      INDEX { wtcExportIndex}
      ::= { wtcExportTable 1 }
      
   WtcExportEntry ::=
      SEQUENCE
      {
         wtcExportIndex       DisplayString,
         wtcExportObjectName  DisplayString,
         wtcExportType        DisplayString,
         wtcExportName        DisplayString,
         wtcExportParent      DisplayString,
         wtcExportEJBName     DisplayString,
         wtcExportLocalAccessPoint DisplayString,
         wtcExportRemoteName  DisplayString,
         wtcExportResourceName DisplayString,
         wtcExportTags        OCTET STRING
      }
      
   
   wtcExportIndex OBJECT-TYPE
      SYNTAX      DisplayString (SIZE (1..16))
      MAX-ACCESS  read-only
      STATUS      current
      DESCRIPTION "Unique value directed from ObjectName which is used as table index"
      ::= { wtcExportEntry 1  }
   
   
   wtcExportObjectName OBJECT-TYPE
      SYNTAX      DisplayString (SIZE (1..256))
      MAX-ACCESS  read-only
      STATUS      current
      DESCRIPTION "JMX-standard MBean name"
      ::= { wtcExportEntry 5  }
   
   
   wtcExportType OBJECT-TYPE
      SYNTAX      DisplayString (SIZE (1..64))
      MAX-ACCESS  read-only
      STATUS      current
      DESCRIPTION "Returns the type of the MBean. "
      ::= { wtcExportEntry 10  }
   
   
   wtcExportName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtcExportEntry 15  }
   
   
   wtcExportParent OBJECT-TYPE
      SYNTAX      DisplayString (SIZE (1..256))
      MAX-ACCESS  read-only
      STATUS      current
      DESCRIPTION "BEA-proprietary Parent object's identification, with syntax
      <type>:<name>"
      ::= { wtcExportEntry 20  }
   
   
   wtcExportEJBName OBJECT-TYPE
      SYNTAX      DisplayString (SIZE (1..256))
      MAX-ACCESS  read-only
      STATUS      current
      DESCRIPTION "The complete name of the EJB home interface to use when invoking a service.  If not specified, the default interface used is tuxedo.services.servicenameHome. For example: If the service being invoked is TOUPPER and EJBName attribute is not specified, the home interface looked up in JNDI would be tuxedo.services.TOUPPERHome. "
      ::= { wtcExportEntry 25  }
   
   
   wtcExportLocalAccessPoint OBJECT-TYPE
      SYNTAX      DisplayString (SIZE (1..256))
      MAX-ACCESS  read-only
      STATUS      current
      DESCRIPTION "The name of the local access point that exports this service. "
      ::= { wtcExportEntry 30  }
   
   
   wtcExportRemoteName OBJECT-TYPE
      SYNTAX      DisplayString (SIZE (1..256))
      MAX-ACCESS  read-only
      STATUS      current
      DESCRIPTION "The remote name of this service.   If this value is not specified, the ResourceName value is used. "
      ::= { wtcExportEntry 35  }
   
   
   wtcExportResourceName OBJECT-TYPE
      SYNTAX      DisplayString (SIZE (1..256))
      MAX-ACCESS  read-only
      STATUS      current
      DESCRIPTION "The name used to identify an exported service.  The combination of ResourceName and LocalAccessPoint must be unique within defined Exports. This allows you to define unique configurations having the same ResourceName. "
      ::= { wtcExportEntry 40  }
   
   
   wtcExportTags OBJECT-TYPE
      SYNTAX      OCTET STRING
      MAX-ACCESS  read-only
      STATUS      current
      DESCRIPTION "Return all tags on this Configuration MBean "
      ::= { wtcExportEntry 41  }
   
   
   wtcImportTable OBJECT-TYPE
      SYNTAX      SEQUENCE OF WtcImportEntry
      MAX-ACCESS  not-accessible
      STATUS      current
      DESCRIPTION "This interface provides access to the WTC import configuration attributes.  The methods defined herein are applicable for WTC configuration at the WLS domain level. "
      ::= { wls 815  }
      
   
   wtcImportEntry OBJECT-TYPE
      SYNTAX      WtcImportEntry
      MAX-ACCESS  not-accessible
      STATUS      current
      DESCRIPTION "Entry of wtcImportTable"
      INDEX { wtcImportIndex}
      ::= { wtcImportTable 1 }
      
   WtcImportEntry ::=
      SEQUENCE
      {
         wtcImportIndex       DisplayString,
         wtcImportObjectName  DisplayString,
         wtcImportType        DisplayString,
         wtcImportName        DisplayString,
         wtcImportParent      DisplayString,
         wtcImportRemoteAccessPointList DisplayString,
         wtcImportLocalAccessPoint DisplayString,
         wtcImportRemoteName  DisplayString,
         wtcImportResourceName DisplayString,
         wtcImportTags        OCTET STRING
      }
      
   
   wtcImportIndex OBJECT-TYPE
      SYNTAX      DisplayString (SIZE (1..16))
      MAX-ACCESS  read-only
      STATUS      current
      DESCRIPTION "Unique value directed from ObjectName which is used as table index"
      ::= { wtcImportEntry 1  }
   
   
   wtcImportObjectName OBJECT-TYPE
      SYNTAX      DisplayString (SIZE (1..256))
      MAX-ACCESS  read-only
      STATUS      current
      DESCRIPTION "JMX-standard MBean name"
      ::= { wtcImportEntry 5  }
   
   
   wtcImportType OBJECT-TYPE
      SYNTAX      DisplayString (SIZE (1..64))
      MAX-ACCESS  read-only
      STATUS      current
      DESCRIPTION "Returns the type of the MBean. "
      ::= { wtcImportEntry 10  }
   
   
   wtcImportName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtcImportEntry 15  }
   
   
   wtcImportParent OBJECT-TYPE
      SYNTAX      DisplayString (SIZE (1..256))
      MAX-ACCESS  read-only
      STATUS      current
      DESCRIPTION "BEA-proprietary Parent object's identification, with syntax
      <type>:<name>"
      ::= { wtcImportEntry 20  }
   
   
   wtcImportRemoteAccessPointList OBJECT-TYPE
      SYNTAX      DisplayString (SIZE (1..256))
      MAX-ACCESS  read-only
      STATUS      current
      DESCRIPTION "The comma-separated failover list that identifies the remote domain access points through which resources are imported.  For example: TDOM1,TDOM2,TDOM3 "
      ::= { wtcImportEntry 25  }
   
   
   wtcImportLocalAccessPoint OBJECT-TYPE
      SYNTAX      DisplayString (SIZE (1..256))
      MAX-ACCESS  read-only
      STATUS      current
      DESCRIPTION "The name of the local access point that offers this service. "
      ::= { wtcImportEntry 30  }
   
   
   wtcImportRemoteName OBJECT-TYPE
      SYNTAX      DisplayString (SIZE (1..256))
      MAX-ACCESS  read-only
      STATUS      current
      DESCRIPTION "The remote name of this service.  Note: If not specified, the ResourceName value is used. "
      ::= { wtcImportEntry 35  }
   
   
   wtcImportResourceName OBJECT-TYPE
      SYNTAX      DisplayString (SIZE (1..256))
      MAX-ACCESS  read-only
      STATUS      current
      DESCRIPTION "The name used to identify this imported service.  Note: This name must be unique within defined Imports. This allows you to define unique configurations having the same Remote Name. "
      ::= { wtcImportEntry 40  }
   
   
   wtcImportTags OBJECT-TYPE
      SYNTAX      OCTET STRING
      MAX-ACCESS  read-only
      STATUS      current
      DESCRIPTION "Return all tags on this Configuration MBean "
      ::= { wtcImportEntry 41  }
   
   
   wtcLocalTuxDomTable OBJECT-TYPE
      SYNTAX      SEQUENCE OF WtcLocalTuxDomEntry
      MAX-ACCESS  not-accessible
      STATUS      current
      DESCRIPTION "This interface provides access to the WTC local Tuxedo Domain configuration attributes.  The methods defined herein are applicable for WTC configuration at the WLS domain level. "
      ::= { wls 817  }
      
   
   wtcLocalTuxDomEntry OBJECT-TYPE
      SYNTAX      WtcLocalTuxDomEntry
      MAX-ACCESS  not-accessible
      STATUS      current
      DESCRIPTION "Entry of wtcLocalTuxDomTable"
      INDEX { wtcLocalTuxDomIndex}
      ::= { wtcLocalTuxDomTable 1 }
      
   WtcLocalTuxDomEntry ::=
      SEQUENCE
      {
         wtcLocalTuxDomIndex  DisplayString,
         wtcLocalTuxDomObjectName DisplayString,
         wtcLocalTuxDomType   DisplayString,
         wtcLocalTuxDomName   DisplayString,
         wtcLocalTuxDomParent DisplayString,
         wtcLocalTuxDomAccessPoint DisplayString,
         wtcLocalTuxDomAccessPointId DisplayString,
         wtcLocalTuxDomBlockTime Counter64,
         wtcLocalTuxDomCmpLimit INTEGER,
         wtcLocalTuxDomConnectionPolicy DisplayString,
         wtcLocalTuxDomConnPrincipalName DisplayString,
         wtcLocalTuxDomInteroperate DisplayString,
         wtcLocalTuxDomMaxEncryptBits DisplayString,
         wtcLocalTuxDomMaxRetries Counter64,
         wtcLocalTuxDomMinEncryptBits DisplayString,
         wtcLocalTuxDomNWAddr DisplayString,
         wtcLocalTuxDomRetryInterval Counter64,
         wtcLocalTuxDomSecurity DisplayString,
         wtcLocalTuxDomKeyStoresLocation OCTET STRING,
         wtcLocalTuxDomUseSSL OCTET STRING,
         wtcLocalTuxDomKeepAliveWait INTEGER,
         wtcLocalTuxDomTrustKeyStoreFileName OCTET STRING,
         wtcLocalTuxDomKeepAlive INTEGER,
         wtcLocalTuxDomPrivateKeyAlias OCTET STRING,
         wtcLocalTuxDomIdentityKeyStoreFileName OCTET STRING,
         wtcLocalTuxDomTags   OCTET STRING,
         wtcLocalTuxDomSSLProtocolVersion OCTET STRING
      }
      
   
   wtcLocalTuxDomIndex OBJECT-TYPE
      SYNTAX      DisplayString (SIZE (1..16))
      MAX-ACCESS  read-only
      STATUS      current
      DESCRIPTION "Unique value directed from ObjectName which is used as table index"
      ::= { wtcLocalTuxDomEntry 1  }
   
   
   wtcLocalTuxDomObjectName OBJECT-TYPE
      SYNTAX      DisplayString (SIZE (1..256))
      MAX-ACCESS  read-only
      STATUS      current
      DESCRIPTION "JMX-standard MBean name"
      ::= { wtcLocalTuxDomEntry 5  }
   
   
   wtcLocalTuxDomType OBJECT-TYPE
      SYNTAX      DisplayString (SIZE (1..64))
      MAX-ACCESS  read-only
      STATUS      current
      DESCRIPTION "Returns the type of the MBean. "
      ::= { wtcLocalTuxDomEntry 10  }
   
   
   wtcLocalTuxDomName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtcLocalTuxDomEntry 15  }
   
   
   wtcLocalTuxDomParent OBJECT-TYPE
      SYNTAX      DisplayString (SIZE (1..256))
      MAX-ACCESS  read-only
      STATUS      current
      DESCRIPTION "BEA-proprietary Parent object's identification, with syntax
      <type>:<name>"
      ::= { wtcLocalTuxDomEntry 20  }
   
   
   wtcLocalTuxDomAccessPoint OBJECT-TYPE
      SYNTAX      DisplayString (SIZE (1..256))
      MAX-ACCESS  read-only
      STATUS      current
      DESCRIPTION "The unique name used to identify this local Tuxedo access point. This name should be unique for all local and remote Tuxedo access points defined within a WTC Service. This allows you to define unique configurations having the same Access Point ID. "
      ::= { wtcLocalTuxDomEntry 25  }
   
   
   wtcLocalTuxDomAccessPointId OBJECT-TYPE
      SYNTAX      DisplayString (SIZE (1..256))
      MAX-ACCESS  read-only
      STATUS      current
      DESCRIPTION "The connection principal name used to identify this local Tuxedo access point when attempting to establish a session connection with remote Tuxedo access points.  Note: The AccessPointId must match the corresponding DOMAINID in the *DM_REMOTE_DOMAINS section of your Tuxedo DMCONFIG file. "
      ::= { wtcLocalTuxDomEntry 30  }
   
   
   wtcLocalTuxDomBlockTime OBJECT-TYPE
      SYNTAX      Counter64
      MAX-ACCESS  read-only
      STATUS      current
      DESCRIPTION "The maximum number of seconds this local Tuxedo access point allows for a blocking call.  Range of Values: Between 0 and a positive 32 bit integer. "
      ::= { wtcLocalTuxDomEntry 35  }
   
   
   wtcLocalTuxDomCmpLimit OBJECT-TYPE
      SYNTAX      INTEGER
      MAX-ACCESS  read-only
      STATUS      current
      DESCRIPTION "The compression threshold this local Tuxedo access point uses when sending data to a remote Tuxedo access point. Application buffers larger than this size are compressed.  Range of Values: Between 0 and a positive 32-bit integer. "
      ::= { wtcLocalTuxDomEntry 40  }
   
   
   wtcLocalTuxDomConnectionPolicy OBJECT-TYPE
      SYNTAX      DisplayString (SIZE (1..256))
      MAX-ACCESS  read-only
      STATUS      current
      DESCRIPTION "The conditions under which this local Tuxedo access point establishes a session connection with a remote Tuxedo access point.  The connection policies are:   ON_DEMAND: A connection is attempted only when requested by either a client request to a remote service or an administrative connect command. ON_STARTUP: A domain gateway attempts to establish a connection with its remote Tuxedo access points at gateway server initialization time. Remote services (services advertised in JNDI by the domain gateway for this local access point) are advertised only if a connection is successfully established to that remote Tuxedo access point. If there is no active connection to a remote Tuxedo access point, then the remote services are suspended. By default, this connection policy retries failed connections every 60 seconds. Use the MaxRetry and RetryInterval values to specify application specific values. INCOMING_ONLY: A domain gateway does not attempt an initial connection to remote Tuxedo access points at startup and remote services are initially suspended. The domain gateway is available for incoming connections from remote Tuxedo access points and remote services are advertised when the domain gateway for this local Tuxedo access point receives an incoming connection. Connection retry processing is not allowed.  "
      ::= { wtcLocalTuxDomEntry 45  }
   
   
   wtcLocalTuxDomConnPrincipalName OBJECT-TYPE
      SYNTAX      DisplayString (SIZE (1..256))
      MAX-ACCESS  read-only
      STATUS      current
      DESCRIPTION "The principal name used to verify the identity of this domain when establishing a connection to another domain.  Note: This parameter only applies to domains of type TDOMAIN that are running Oracle  Tuxedo 7.1 or later software. If not specified, the connection principal name defaults to the AccessPointID for this domain.ConnPrincipalName.  Note: ConnPrincipalName is not supported in this release. "
      ::= { wtcLocalTuxDomEntry 50  }
   
   
   wtcLocalTuxDomInteroperate OBJECT-TYPE
      SYNTAX      DisplayString (SIZE (1..256))
      MAX-ACCESS  read-only
      STATUS      current
      DESCRIPTION "Specifies whether this local Tuxedo access point interoperates with remote Tuxedo access points that are based upon Tuxedo release 6.5. If this value is set to Yes, the local Tuxedo access point interoperates with a Tuxedo 6.5 domain. "
      ::= { wtcLocalTuxDomEntry 55  }
   
   
   wtcLocalTuxDomMaxEncryptBits OBJECT-TYPE
      SYNTAX      DisplayString (SIZE (1..256))
      MAX-ACCESS  read-only
      STATUS      current
      DESCRIPTION "The maximum encryption key length (in bits) this local Tuxedo access point uses when establishing a session connection. A value of 0 indicates no encryption is used.  Value Restrictions:   The MaxEncryptBits value must be greater than or equal to the MinEncrypBits value. A MaxEncryptBits of 40 can be used only with domains running Tuxedo 7.1 or higher.  "
      ::= { wtcLocalTuxDomEntry 60  }
   
   
   wtcLocalTuxDomMaxRetries OBJECT-TYPE
      SYNTAX      Counter64
      MAX-ACCESS  read-only
      STATUS      current
      DESCRIPTION "The maximum number of times that this local Tuxedo access point tries to establish a session connection to remote Tuxedo access points. Use this value only when Connection Policy is set to ON_STARTUP.  Range of Values: Between 0 and a positive 64 bit integer.  Note: Use the minimum value to disable the retry mechanism. Use the maximum value to try until a connection is established. "
      ::= { wtcLocalTuxDomEntry 65  }
   
   
   wtcLocalTuxDomMinEncryptBits OBJECT-TYPE
      SYNTAX      DisplayString (SIZE (1..256))
      MAX-ACCESS  read-only
      STATUS      current
      DESCRIPTION "The minimum encryption key length (in bits) this local Tuxedo access point uses when establishing a session connection. A value of 0 indicates no encryption is used.  Value Restrictions:   The MinEncrypBits value must be less than or equal to the MaxEncrypBits value. A MinEncrypBits value of 40 can be used only with domains running Tuxedo 7.1 or higher.  "
      ::= { wtcLocalTuxDomEntry 70  }
   
   
   wtcLocalTuxDomNWAddr OBJECT-TYPE
      SYNTAX      DisplayString (SIZE (1..256))
      MAX-ACCESS  read-only
      STATUS      current
      DESCRIPTION "The network address and port number of this local Tuxedo access point. Specify the address in one of the following formats:  TCP/IP address in the format //hostname:port_number or //#.#.#.#:port_number. SDP address in the format sdp://hostname:port_number or sdp://#.#.#.#:port_number.   Notes:  If the hostname is used, the access point finds an address for hostname using the local name resolution facilities (usually DNS). If dotted decimal format is used, each # should be a number from 0 to 255. This dotted decimal number represents the IP address of the local machine. The port_number is the TCP/SDP port number at which the access point listens for incoming requests.  If SDP format address is specified, the transport protocol for this access point is SDP instead of TCP. This feature is only available when WTC and Tuxedo domain gateway are both deployed on Oracle Exalogic platform. Requires Tuxedo 11gR1PS2 and higher.  "
      ::= { wtcLocalTuxDomEntry 75  }
   
   
   wtcLocalTuxDomRetryInterval OBJECT-TYPE
      SYNTAX      Counter64
      MAX-ACCESS  read-only
      STATUS      current
      DESCRIPTION "The number of seconds that this local Tuxedo access point waits between automatic connection attempts to remote Tuxedo access points. Use this value only when Connection Policy is set to ON_STARTUP.  Range of Values: Between 0 and a positive 32-bit integer. "
      ::= { wtcLocalTuxDomEntry 80  }
   
   
   wtcLocalTuxDomSecurity OBJECT-TYPE
      SYNTAX      DisplayString (SIZE (1..256))
      MAX-ACCESS  read-only
      STATUS      current
      DESCRIPTION "The type of application security enforced.  The types of security are:   NONE: No security is used. APP_PW: Password security is enforced when a connection is established from a remote domain. The application password is defined in the WTCResourcesMBean. DM_PW: Domain password security is enforced when a connection is established from a remote domain. The domain password is defined in the WTCPasswordsMBean.  "
      ::= { wtcLocalTuxDomEntry 85  }
   
   
   wtcLocalTuxDomKeyStoresLocation OBJECT-TYPE
      SYNTAX      OCTET STRING
      MAX-ACCESS  read-only
      STATUS      current
      DESCRIPTION "Provides the configuration rule to be used for finding Local Access Point's identity key store and trust key store. In plain text, it contains information on where the identity key store and trust key store are configured.  When KeyStoreLocation is configured with WLS Store, WTC uses configuration information from the WLS Key Stores configuration.  Otherwise, it uses the key stores information configured in the Local Access Point. "
      ::= { wtcLocalTuxDomEntry 86  }
   
   
   wtcLocalTuxDomUseSSL OBJECT-TYPE
      SYNTAX      OCTET STRING
      MAX-ACCESS  read-only
      STATUS      current
      DESCRIPTION "Specifies if the connection initiated or accepted by this Local Tuxedo access point uses SSL on top of its transport layer. Values are:  Off: SSL not used. TwoWay: Mutual Authentication with SSL required. OneWay: Server Authentication with SSL required.   Note: If SDP transport is configured for this access point, the configured value of this attribute is ignored and off is used. "
      ::= { wtcLocalTuxDomEntry 88  }
   
   
   wtcLocalTuxDomKeepAliveWait OBJECT-TYPE
      SYNTAX      INTEGER
      MAX-ACCESS  read-only
      STATUS      current
      DESCRIPTION "Return value that tells whether this local Tuxedo access point requires the acknowledgement of Application Level Keep Alive, and how long it will wait without receiving acknowledgement before declare the connection is inaccessible. "
      ::= { wtcLocalTuxDomEntry 89  }
   
   
   wtcLocalTuxDomTrustKeyStoreFileName OBJECT-TYPE
      SYNTAX      OCTET STRING
      MAX-ACCESS  read-only
      STATUS      current
      DESCRIPTION "The path and file name of the trust keystore.  The path name must either be absolute or relative to where the server was booted. This file name is only used if KeyStores is 'Custom Stores'. "
      ::= { wtcLocalTuxDomEntry 90  }
   
   
   wtcLocalTuxDomKeepAlive OBJECT-TYPE
      SYNTAX      INTEGER
      MAX-ACCESS  read-only
      STATUS      current
      DESCRIPTION "Return value tells whether this local Tuxedo access point is configured with Application Level Keep Alive, and it maximum idle time value before wait timer start ticking. "
      ::= { wtcLocalTuxDomEntry 91  }
   
   
   wtcLocalTuxDomPrivateKeyAlias OBJECT-TYPE
      SYNTAX      OCTET STRING
      MAX-ACCESS  read-only
      STATUS      current
      DESCRIPTION "The string alias used to store and retrieve the Local Tuxedo access point's private key in the keystore. This private key is associated with the Local Tuxedo access point's digital certificate. "
      ::= { wtcLocalTuxDomEntry 92  }
   
   
   wtcLocalTuxDomIdentityKeyStoreFileName OBJECT-TYPE
      SYNTAX      OCTET STRING
      MAX-ACCESS  read-only
      STATUS      current
      DESCRIPTION "The path and file name of the identity keystore.  The path name must either be absolute or relative to where the server was booted. The identity key store file name is only used if KeystoreLocation is 'Custom Stores'. "
      ::= { wtcLocalTuxDomEntry 93  }
   
   
   wtcLocalTuxDomTags OBJECT-TYPE
      SYNTAX      OCTET STRING
      MAX-ACCESS  read-only
      STATUS      current
      DESCRIPTION "Return all tags on this Configuration MBean "
      ::= { wtcLocalTuxDomEntry 94  }
   
   
   wtcLocalTuxDomSSLProtocolVersion OBJECT-TYPE
      SYNTAX      OCTET STRING
      MAX-ACCESS  read-only
      STATUS      current
      DESCRIPTION "The protocol version of the SSL connection this local access point uses when establishing a SSL connection.   Value Restrictions:    TLSv1.0   TLSv1.1   TLSv1.2   "
      ::= { wtcLocalTuxDomEntry 95  }
   
   
   wtcRemoteTuxDomTable OBJECT-TYPE
      SYNTAX      SEQUENCE OF WtcRemoteTuxDomEntry
      MAX-ACCESS  not-accessible
      STATUS      current
      DESCRIPTION "This interface provides access to the WTC remote Tuxedo Domain configuration attributes. The methods defined herein are applicable for WTC configuration at the WLS domain level. "
      ::= { wls 820  }
      
   
   wtcRemoteTuxDomEntry OBJECT-TYPE
      SYNTAX      WtcRemoteTuxDomEntry
      MAX-ACCESS  not-accessible
      STATUS      current
      DESCRIPTION "Entry of wtcRemoteTuxDomTable"
      INDEX { wtcRemoteTuxDomIndex}
      ::= { wtcRemoteTuxDomTable 1 }
      
   WtcRemoteTuxDomEntry ::=
      SEQUENCE
      {
         wtcRemoteTuxDomIndex DisplayString,
         wtcRemoteTuxDomObjectName DisplayString,
         wtcRemoteTuxDomType  DisplayString,
         wtcRemoteTuxDomName  DisplayString,
         wtcRemoteTuxDomParent DisplayString,
         wtcRemoteTuxDomAccessPoint DisplayString,
         wtcRemoteTuxDomAccessPointId DisplayString,
         wtcRemoteTuxDomAclPolicy DisplayString,
         wtcRemoteTuxDomCmpLimit INTEGER,
         wtcRemoteTuxDomConnectionPolicy DisplayString,
         wtcRemoteTuxDomConnPrincipalName DisplayString,
         wtcRemoteTuxDomCredentialPolicy DisplayString,
         wtcRemoteTuxDomMaxEncryptBits DisplayString,
         wtcRemoteTuxDomMaxRetries Counter64,
         wtcRemoteTuxDomMinEncryptBits DisplayString,
         wtcRemoteTuxDomNWAddr DisplayString,
         wtcRemoteTuxDomRetryInterval Counter64,
         wtcRemoteTuxDomTpUsrFile DisplayString,
         wtcRemoteTuxDomFederationName DisplayString,
         wtcRemoteTuxDomFederationURL DisplayString,
         wtcRemoteTuxDomLocalAccessPoint DisplayString,
         wtcRemoteTuxDomDefaultAppKey INTEGER,
         wtcRemoteTuxDomCustomAppKeyClass OCTET STRING,
         wtcRemoteTuxDomTuxedoGidKw OCTET STRING,
         wtcRemoteTuxDomAllowAnonymous OCTET STRING,
         wtcRemoteTuxDomKeepAliveWait INTEGER,
         wtcRemoteTuxDomCustomAppKeyClassParam OCTET STRING,
         wtcRemoteTuxDomTuxedoUidKw OCTET STRING,
         wtcRemoteTuxDomKeepAlive INTEGER,
         wtcRemoteTuxDomAppKey OCTET STRING,
         wtcRemoteTuxDomTags  OCTET STRING,
         wtcRemoteTuxDomSSLProtocolVersion OCTET STRING
      }
      
   
   wtcRemoteTuxDomIndex OBJECT-TYPE
      SYNTAX      DisplayString (SIZE (1..16))
      MAX-ACCESS  read-only
      STATUS      current
      DESCRIPTION "Unique value directed from ObjectName which is used as table index"
      ::= { wtcRemoteTuxDomEntry 1  }
   
   
   wtcRemoteTuxDomObjectName OBJECT-TYPE
      SYNTAX      DisplayString (SIZE (1..256))
      MAX-ACCESS  read-only
      STATUS      current
      DESCRIPTION "JMX-standard MBean name"
      ::= { wtcRemoteTuxDomEntry 5  }
   
   
   wtcRemoteTuxDomType OBJECT-TYPE
      SYNTAX      DisplayString (SIZE (1..64))
      MAX-ACCESS  read-only
      STATUS      current
      DESCRIPTION "Returns the type of the MBean. "
      ::= { wtcRemoteTuxDomEntry 10  }
   
   
   wtcRemoteTuxDomName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtcRemoteTuxDomEntry 15  }
   
   
   wtcRemoteTuxDomParent OBJECT-TYPE
      SYNTAX      DisplayString (SIZE (1..256))
      MAX-ACCESS  read-only
      STATUS      current
      DESCRIPTION "BEA-proprietary Parent object's identification, with syntax
      <type>:<name>"
      ::= { wtcRemoteTuxDomEntry 20  }
   
   
   wtcRemoteTuxDomAccessPoint OBJECT-TYPE
      SYNTAX      DisplayString (SIZE (1..256))
      MAX-ACCESS  read-only
      STATUS      current
      DESCRIPTION "The unique name used to identify this remote Tuxedo access point. This name should be unique for all local and remote Tuxedo access points defined within a WTC Service. This allows you to define unique configurations having the same Access Point ID. "
      ::= { wtcRemoteTuxDomEntry 25  }
   
   
   wtcRemoteTuxDomAccessPointId OBJECT-TYPE
      SYNTAX      DisplayString (SIZE (1..256))
      MAX-ACCESS  read-only
      STATUS      current
      DESCRIPTION "The connection principal name used to identify this remote domain access point when attempting to establish a session connection to local Tuxedo access points. This value must be globally unique among all interconnected Tuxedo and WTC Domains. "
      ::= { wtcRemoteTuxDomEntry 30  }
   
   
   wtcRemoteTuxDomAclPolicy OBJECT-TYPE
      SYNTAX      DisplayString (SIZE (1..256))
      MAX-ACCESS  read-only
      STATUS      current
      DESCRIPTION "The inbound access control list (ACL) policy toward requests from a remote Tuxedo access point.  The allowed values are:   LOCAL: The local Tuxedo access point modifies the identity of service requests received from a given remote Tuxedo access point to the principal name specified in the local principal name for a given remote Tuxedo access point.  GLOBAL: The local Tuxedo access point passes the service request with no change in identity.   Note: If Interoperate is set to Yes, AclPolicy is ignored. "
      ::= { wtcRemoteTuxDomEntry 35  }
   
   
   wtcRemoteTuxDomCmpLimit OBJECT-TYPE
      SYNTAX      INTEGER
      MAX-ACCESS  read-only
      STATUS      current
      DESCRIPTION "The compression threshold this remote Tuxedo access point uses when sending data to a local Tuxedo access point. Application buffers larger than this size are compressed.  Range of Values: Between 0 and a positive 32-bit integer. "
      ::= { wtcRemoteTuxDomEntry 40  }
   
   
   wtcRemoteTuxDomConnectionPolicy OBJECT-TYPE
      SYNTAX      DisplayString (SIZE (1..256))
      MAX-ACCESS  read-only
      STATUS      current
      DESCRIPTION "The conditions under which this remote Tuxedo access point establishes a session connection with a local Tuxedo access point.  The allowed values are:   ON_DEMAND: A connection is attempted only when requested by either a client request to a remote service or an administrative connect command.  ON_STARTUP: A domain gateway attempts to establish a connection with its remote Tuxedo access points at gateway server initialization time. Remote services (services advertised in JNDI by the domain gateway for this local Tuxedo access point) are advertised only if a connection is successfully established to that remote Tuxedo access point. If there is no active connection to a remote Tuxedo access point, then the remote services are suspended. By default, this connection policy retries failed connections every 60 seconds. Use the MaxRetry and RetryInterval attributes to specify application specific values.  INCOMING_ONLY: A domain gateway does not attempt an initial connection to remote Tuxedo access points at startup and remote services are initially suspended. The domain gateway is available for incoming connections from remote Tuxedo access points and remote services are advertised when the domain gateway for this local Tuxedo access point receives an incoming connection. Connection retry processing is not allowed.  LOCAL: Specifies that the remote domain connection policy is explicitly defaulted to the local domain ConnectionPolicy attribute value.  "
      ::= { wtcRemoteTuxDomEntry 45  }
   
   
   wtcRemoteTuxDomConnPrincipalName OBJECT-TYPE
      SYNTAX      DisplayString (SIZE (1..256))
      MAX-ACCESS  read-only
      STATUS      current
      DESCRIPTION "The principal name used to verify the identity of this remote Tuxedo access point when it establishes a session connection with a local Tuxedo access point. If not specified, the connection principal name defaults to the AccessPointID for this access point.  Note: This parameter only applies to domains of type TDOMAIN that are running Oracle  Tuxedo 7.1 or later software.  Note: ConnPrincipalName is not supported in this release. "
      ::= { wtcRemoteTuxDomEntry 50  }
   
   
   wtcRemoteTuxDomCredentialPolicy OBJECT-TYPE
      SYNTAX      DisplayString (SIZE (1..256))
      MAX-ACCESS  read-only
      STATUS      current
      DESCRIPTION "The outbound access control list (ACL) policy toward requests to a remote Tuxedo access point.  The allowed values are:   LOCAL: The remote Tuxedo access point controls the identity of service requests received from the local Tuxedo access point to the principal name specified in the local principal name for this remote Tuxedo access point.  GLOBAL: The remote Tuxedo access point passes the service request with no change.   Note:If Interoperate is set to Yes, CredentialPolicy is ignored. "
      ::= { wtcRemoteTuxDomEntry 55  }
   
   
   wtcRemoteTuxDomMaxEncryptBits OBJECT-TYPE
      SYNTAX      DisplayString (SIZE (1..256))
      MAX-ACCESS  read-only
      STATUS      current
      DESCRIPTION "The maximum encryption key length (in bits) this remote Tuxedo access point uses when establishing a session connection. A value of 0 indicates no encryption is used.  Value Restrictions:   The value of the MaxEncryptBits attribute must be greater than or equal to the value of the MinEncrypBits attribute.   A MaxEncryptBits of 40 can be used only with domains running Tuxedo 7.1 or higher.   "
      ::= { wtcRemoteTuxDomEntry 60  }
   
   
   wtcRemoteTuxDomMaxRetries OBJECT-TYPE
      SYNTAX      Counter64
      MAX-ACCESS  read-only
      STATUS      current
      DESCRIPTION "The maximum number of times that this remote Tuxedo access point tries to establish a session connections to local Tuxedo access points. Use only when the ConnectionPolicy value is set to ON_STARTUP.  Note: When the ConnectionPolicy value is LOCAL, the MaxRetries value from the local Tuxedo access point is used. When the ConnectionPolicy value is ON_STARTUP, a value of -1 indicates 9223372036854775807.  Range of Values: Between -1 and a positive 64-bit integer.   Use 0 to disable the retry mechanism.  Use the maximum value to try until a connection is established.  "
      ::= { wtcRemoteTuxDomEntry 65  }
   
   
   wtcRemoteTuxDomMinEncryptBits OBJECT-TYPE
      SYNTAX      DisplayString (SIZE (1..256))
      MAX-ACCESS  read-only
      STATUS      current
      DESCRIPTION "The minimum encryption key length (in bits) this remote Tuxedo access point uses when establishing a session connection. A value of 0 indicates no encryption is used.  Value Restrictions:   The MinEncrypBits value must be less than or equal to the MaxEncrypBits value.   A MinEncrypBits value of 40 can be used only with domains running Tuxedo 7.1 or higher.   "
      ::= { wtcRemoteTuxDomEntry 70  }
   
   
   wtcRemoteTuxDomNWAddr OBJECT-TYPE
      SYNTAX      DisplayString (SIZE (1..256))
      MAX-ACCESS  read-only
      STATUS      current
      DESCRIPTION "The network address and port number of this remote Tuxedo access point. Specify the address in one of the following formats:  TCP/IP address in the format //hostname:port_number or //#.#.#.#:port_number. SDP address in the format sdp://hostname:port_number or sdp://#.#.#.#:port_number.   Notes:  If the hostname is used, the access point finds an address for hostname using the local name resolution facilities (usually DNS). If dotted decimal format is used, each # should be a number from 0 to 255. This dotted decimal number represents the IP address of the local machine. The port_number is the TCP/SDP port number at which the access point listens for incoming requests.  If SDP format address is specified, the transport protocol for this access point is SDP instead of TCP. This feature is only available when WTC and Tuxedo domain gateway are both deployed on Oracle Exalogic platform. Requires Tuxedo 11gR1PS2 and higher.  "
      ::= { wtcRemoteTuxDomEntry 75  }
   
   
   wtcRemoteTuxDomRetryInterval OBJECT-TYPE
      SYNTAX      Counter64
      MAX-ACCESS  read-only
      STATUS      current
      DESCRIPTION "The number of seconds that this remote Tuxedo access point waits between automatic connection attempts to local Tuxedo access points. Use this only when the ConnectionPolicy value is set to ON_STARTUP.  Range of Values: Between -1 and a positive 32-bit integer.  Note: When the ConnectionPolicy value is LOCAL, the RetryInterval value from the local Tuxedo access point is used. When the ConnectionPolicy value is ON_STARTUP, a value of -1 indicates 60. "
      ::= { wtcRemoteTuxDomEntry 80  }
   
   
   wtcRemoteTuxDomTpUsrFile OBJECT-TYPE
      SYNTAX      DisplayString (SIZE (1..256))
      MAX-ACCESS  read-only
      STATUS      current
      DESCRIPTION "The full path to the user password file containing UID/GID information. (This field is only relevant if you specify TpUsrFile as the AppKey Generator.)  Note: This file is generated by the Tuxedo tpusradd utility on the remote Tuxedo domain specified by the remote Tuxedo access point. A copy of this file must be available in your WebLogic Tuxedo Connector environment to provide correct authorization, authentication, and auditing. "
      ::= { wtcRemoteTuxDomEntry 85  }
   
   
   wtcRemoteTuxDomFederationName OBJECT-TYPE
      SYNTAX      DisplayString (SIZE (1..256))
      MAX-ACCESS  read-only
      STATUS      current
      DESCRIPTION "The context at which this remote Tuxedo access point federates to a foreign name service. If omitted, the default federation point is tuxedo.domains. "
      ::= { wtcRemoteTuxDomEntry 100  }
   
   
   wtcRemoteTuxDomFederationURL OBJECT-TYPE
      SYNTAX      DisplayString (SIZE (1..256))
      MAX-ACCESS  read-only
      STATUS      current
      DESCRIPTION "The URL for a foreign name service that is federated into JNDI.  Note: The Weblogic Tuxedo Connector can federate to non-CORBA service providers.  Note: If this value is not specified, the WebLogic Tuxedo Connector:   Assumes there is a CosNaming server in the foreign domain.  Federates to the CosNaming server using TGIOP.   "
      ::= { wtcRemoteTuxDomEntry 105  }
   
   
   wtcRemoteTuxDomLocalAccessPoint OBJECT-TYPE
      SYNTAX      DisplayString (SIZE (1..256))
      MAX-ACCESS  read-only
      STATUS      current
      DESCRIPTION "The local domain name from which this remote Tuxedo domain is reached. "
      ::= { wtcRemoteTuxDomEntry 110  }
   
   
   wtcRemoteTuxDomDefaultAppKey OBJECT-TYPE
      SYNTAX      INTEGER
      MAX-ACCESS  read-only
      STATUS      current
      DESCRIPTION "The default AppKey value to be used by the anonymous user and other users who are not defined in the user database if the plug-in allows them to access Tuxedo.  Note: The TpUsrFile and LDAP plug-ins do not allow users that are not defined in user database to access Tuxedo unless Allow Anonymous is enabled. "
      ::= { wtcRemoteTuxDomEntry 111  }
   
   
   wtcRemoteTuxDomCustomAppKeyClass OBJECT-TYPE
      SYNTAX      OCTET STRING
      MAX-ACCESS  read-only
      STATUS      current
      DESCRIPTION "The full pathname to the custom AppKey generator class. (This class is only relevant if you specify Custom as the AppKey Generator.)  Note: This class is loaded at runtime if the Custom AppKey generator plug-in is selected. "
      ::= { wtcRemoteTuxDomEntry 112  }
   
   
   wtcRemoteTuxDomTuxedoGidKw OBJECT-TYPE
      SYNTAX      OCTET STRING
      MAX-ACCESS  read-only
      STATUS      current
      DESCRIPTION "The keyword for Tuxedo GID (Group ID) used in the WlsUser when using the Tuxedo migration utility tpmigldap. This field is only relevant if you specify LDAP as the AppKey Generator.)  Note: The keyword is used to find Tuxedo GID in the user record in the embedded LDAP database. "
      ::= { wtcRemoteTuxDomEntry 113  }
   
   
   wtcRemoteTuxDomAllowAnonymous OBJECT-TYPE
      SYNTAX      OCTET STRING
      MAX-ACCESS  read-only
      STATUS      current
      DESCRIPTION "Specifies whether the anonymous user is allowed to access remote Tuxedo services.  Note: If the anonymous user is allowed to access Tuxedo, the default AppKey will be used for TpUsrFile and LDAP AppKey plug-ins. Interaction with the Custom AppKey plug-in depends on the design of the Custom AppKey generator. "
      ::= { wtcRemoteTuxDomEntry 114  }
   
   
   wtcRemoteTuxDomKeepAliveWait OBJECT-TYPE
      SYNTAX      INTEGER
      MAX-ACCESS  read-only
      STATUS      current
      DESCRIPTION "Indicates whether this remote Tuxedo access point requires the acknowledgement of Application Level Keep Alive. If the value is:   Greater than 0: Application Level Keep Alive is enabled and the value indicates the amount of idle time, in milliseconds rounded to the nearest second, allowed before WebLogic Tuxedo Connector marks the connection as failed if the heartbeat is not acknowledged.  0: Application Level Keep Alive is not enabled for the access point but the access point acknowledges if a heartbeat is received.  "
      ::= { wtcRemoteTuxDomEntry 115  }
   
   
   wtcRemoteTuxDomCustomAppKeyClassParam OBJECT-TYPE
      SYNTAX      OCTET STRING
      MAX-ACCESS  read-only
      STATUS      current
      DESCRIPTION "The optional parameters to be used by the custom AppKey class at the class initialization time. This class is only relevant if you specify Custom as the AppKey Generator.) "
      ::= { wtcRemoteTuxDomEntry 116  }
   
   
   wtcRemoteTuxDomTuxedoUidKw OBJECT-TYPE
      SYNTAX      OCTET STRING
      MAX-ACCESS  read-only
      STATUS      current
      DESCRIPTION "The keyword for Tuxedo UID (User ID) used in the WlsUser when using the Tuxedo migration utility tpmigldap. This keyword is only relevant if you specify LDAP as the AppKey Generator.)  Note: The keyword is used to find Tuxedo UID in the user record in the embedded LDAP database. "
      ::= { wtcRemoteTuxDomEntry 117  }
   
   
   wtcRemoteTuxDomKeepAlive OBJECT-TYPE
      SYNTAX      INTEGER
      MAX-ACCESS  read-only
      STATUS      current
      DESCRIPTION "Indicates whether this remote Tuxedo access point is configured with Application Level Keep Alive.   Greater than 0: Application Level Keep Alive is enabled and the value indicates the amount of idle time, in milliseconds rounded to the nearest second, allowed before starting the wait timer.  0: Application Level Keep Alive is not enabled for the access point.  -1: Application Level Keep Alive is enabled and indicates that the value from the local Tuxedo access point is used to indicate the amount of idle time, in milliseconds rounded to the nearest second, allowed before starting the wait timer.  "
      ::= { wtcRemoteTuxDomEntry 118  }
   
   
   wtcRemoteTuxDomAppKey OBJECT-TYPE
      SYNTAX      OCTET STRING
      MAX-ACCESS  read-only
      STATUS      current
      DESCRIPTION "Specifies the type of AppKey plug-in used.  The allowed values are:   TpUsrFile: TpUsrFile is the default plug-in. It uses an imported Tuxedo TPUSR file to provide user security information. Previous releases of WebLogic Tuxedo Connector support this option.  LDAP: The LDAP plug-in utilizes an embedded LDAP server to provide user security information. The user record must define the Tuxedo UID and GID information in the description field. This functionality is not supported in previous releases of WebLogic Tuxedo Connector.   Custom: The Custom plug-in provides the ability to write your own AppKey generator class to provide the security information required by Tuxedo. This functionality is not supported in previous releases of WebLogic Tuxedo Connector.   "
      ::= { wtcRemoteTuxDomEntry 119  }
   
   
   wtcRemoteTuxDomTags OBJECT-TYPE
      SYNTAX      OCTET STRING
      MAX-ACCESS  read-only
      STATUS      current
      DESCRIPTION "Return all tags on this Configuration MBean "
      ::= { wtcRemoteTuxDomEntry 120  }
   
   
   wtcRemoteTuxDomSSLProtocolVersion OBJECT-TYPE
      SYNTAX      OCTET STRING
      MAX-ACCESS  read-only
      STATUS      current
      DESCRIPTION "The protocol version of the SSL connection this remote access point uses when establishing a SSL connection with specific local access point.   Value Restrictions:    TLSv1.0   TLSv1.1   TLSv1.2   "
      ::= { wtcRemoteTuxDomEntry 121  }
   
   
   wtctBridgeRedirectTable OBJECT-TYPE
      SYNTAX      SEQUENCE OF WtctBridgeRedirectEntry
      MAX-ACCESS  not-accessible
      STATUS      current
      DESCRIPTION "This interface provides access to the WTC tBridge Redirect configuration attributes. The methods defined herein are applicable for tBridge configuration at the WLS domain level. "
      ::= { wls 825  }
      
   
   wtctBridgeRedirectEntry OBJECT-TYPE
      SYNTAX      WtctBridgeRedirectEntry
      MAX-ACCESS  not-accessible
      STATUS      current
      DESCRIPTION "Entry of wtctBridgeRedirectTable"
      INDEX { wtctBridgeRedirectIndex}
      ::= { wtctBridgeRedirectTable 1 }
      
   WtctBridgeRedirectEntry ::=
      SEQUENCE
      {
         wtctBridgeRedirectIndex DisplayString,
         wtctBridgeRedirectObjectName DisplayString,
         wtctBridgeRedirectType DisplayString,
         wtctBridgeRedirectName DisplayString,
         wtctBridgeRedirectParent DisplayString,
         wtctBridgeRedirectDirection DisplayString,
         wtctBridgeRedirectMetaDataFile DisplayString,
         wtctBridgeRedirectReplyQ DisplayString,
         wtctBridgeRedirectSourceAccessPoint DisplayString,
         wtctBridgeRedirectSourceName DisplayString,
         wtctBridgeRedirectSourceQspace DisplayString,
         wtctBridgeRedirectTargetAccessPoint DisplayString,
         wtctBridgeRedirectTargetName DisplayString,
         wtctBridgeRedirectTargetQspace DisplayString,
         wtctBridgeRedirectTranslateFML DisplayString,
         wtctBridgeRedirectTags OCTET STRING
      }
      
   
   wtctBridgeRedirectIndex OBJECT-TYPE
      SYNTAX      DisplayString (SIZE (1..16))
      MAX-ACCESS  read-only
      STATUS      current
      DESCRIPTION "Unique value directed from ObjectName which is used as table index"
      ::= { wtctBridgeRedirectEntry 1  }
   
   
   wtctBridgeRedirectObjectName OBJECT-TYPE
      SYNTAX      DisplayString (SIZE (1..256))
      MAX-ACCESS  read-only
      STATUS      current
      DESCRIPTION "JMX-standard MBean name"
      ::= { wtctBridgeRedirectEntry 5  }
   
   
   wtctBridgeRedirectType OBJECT-TYPE
      SYNTAX      DisplayString (SIZE (1..64))
      MAX-ACCESS  read-only
      STATUS      current
      DESCRIPTION "Returns the type of the MBean. "
      ::= { wtctBridgeRedirectEntry 10  }
   
   
   wtctBridgeRedirectName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtctBridgeRedirectEntry 15  }
   
   
   wtctBridgeRedirectParent OBJECT-TYPE
      SYNTAX      DisplayString (SIZE (1..256))
      MAX-ACCESS  read-only
      STATUS      current
      DESCRIPTION "BEA-proprietary Parent object's identification, with syntax
      <type>:<name>"
      ::= { wtctBridgeRedirectEntry 20  }
   
   
   wtctBridgeRedirectDirection OBJECT-TYPE
      SYNTAX      DisplayString (SIZE (1..256))
      MAX-ACCESS  read-only
      STATUS      current
      DESCRIPTION "The direction of data flow. At least one redirection must be specified or the Tuxedo queuing bridge will fail to start and an error will be logged.  Each defined direction is handled by starting a new thread.  Redirection keywords:   JmsQ2TuxQ  - From JMS to TUXEDO /Q   TuxQ2JmsQ  - From TUXEDO /Q to JMS   JmsQ2TuxS  - From JMS to TUXEDO Service reply to JMS   JmsQ2JmsQ  - From JMS to JMS   "
      ::= { wtctBridgeRedirectEntry 25  }
   
   
   wtctBridgeRedirectMetaDataFile OBJECT-TYPE
      SYNTAX      DisplayString (SIZE (1..256))
      MAX-ACCESS  read-only
      STATUS      current
      DESCRIPTION "The name of the metadata file URL used to pass the call to the XML-to-non-XML WebLogic XML Translator (WLXT).  Note: Not supported for this release. "
      ::= { wtctBridgeRedirectEntry 30  }
   
   
   wtctBridgeRedirectReplyQ OBJECT-TYPE
      SYNTAX      DisplayString (SIZE (1..256))
      MAX-ACCESS  read-only
      STATUS      current
      DESCRIPTION "The name of the JMS queue used specifically for synchronous calls to a Tuxedo service. The response is returned to the JMS ReplyQ. "
      ::= { wtctBridgeRedirectEntry 35  }
   
   
   wtctBridgeRedirectSourceAccessPoint OBJECT-TYPE
      SYNTAX      DisplayString (SIZE (1..256))
      MAX-ACCESS  read-only
      STATUS      current
      DESCRIPTION "The name of the local or remote access point where the source is located. "
      ::= { wtctBridgeRedirectEntry 40  }
   
   
   wtctBridgeRedirectSourceName OBJECT-TYPE
      SYNTAX      DisplayString (SIZE (1..256))
      MAX-ACCESS  read-only
      STATUS      current
      DESCRIPTION "The name of a source queue or service. Specifies a JMS queue name, a Tuxedo queue name, or the name of a Tuxedo service. "
      ::= { wtctBridgeRedirectEntry 45  }
   
   
   wtctBridgeRedirectSourceQspace OBJECT-TYPE
      SYNTAX      DisplayString (SIZE (1..256))
      MAX-ACCESS  read-only
      STATUS      current
      DESCRIPTION "The name of the Qspace for a source location. "
      ::= { wtctBridgeRedirectEntry 50  }
   
   
   wtctBridgeRedirectTargetAccessPoint OBJECT-TYPE
      SYNTAX      DisplayString (SIZE (1..256))
      MAX-ACCESS  read-only
      STATUS      current
      DESCRIPTION "The name of the local or remote access point where the target is located. "
      ::= { wtctBridgeRedirectEntry 55  }
   
   
   wtctBridgeRedirectTargetName OBJECT-TYPE
      SYNTAX      DisplayString (SIZE (1..256))
      MAX-ACCESS  read-only
      STATUS      current
      DESCRIPTION "The name of the target queue or service. Specifies a JMS queue name, a Tuxedo queue name, or the name of a Tuxedo service. "
      ::= { wtctBridgeRedirectEntry 60  }
   
   
   wtctBridgeRedirectTargetQspace OBJECT-TYPE
      SYNTAX      DisplayString (SIZE (1..256))
      MAX-ACCESS  read-only
      STATUS      current
      DESCRIPTION "The name of the Qspace for a target location. "
      ::= { wtctBridgeRedirectEntry 65  }
   
   
   wtctBridgeRedirectTranslateFML OBJECT-TYPE
      SYNTAX      DisplayString (SIZE (1..256))
      MAX-ACCESS  read-only
      STATUS      current
      DESCRIPTION "The type of XML/FML translation.  NO indicates that no data translation is performed. FLAT indicates that the message payload is transformed using the WebLogic Tuxedo Connector translator. WLXT indicates that translation is performed by the XML-to-non-XML WebLogic XML Translator (WLXT).  Note: WLXT is not supported for this release. "
      ::= { wtctBridgeRedirectEntry 70  }
   
   
   wtctBridgeRedirectTags OBJECT-TYPE
      SYNTAX      OCTET STRING
      MAX-ACCESS  read-only
      STATUS      current
      DESCRIPTION "Return all tags on this Configuration MBean "
      ::= { wtctBridgeRedirectEntry 71  }
   
   
   wsReliableDeliveryPolicyTable OBJECT-TYPE
      SYNTAX      SEQUENCE OF WsReliableDeliveryPolicyEntry
      MAX-ACCESS  not-accessible
      STATUS      current
      DESCRIPTION "This class represents the reliable messaging delivery policy for the current WebLogic Server as both a sender and a receiver of a reliable SOAP message to and from a Web service running on a different WebLogic Server.  Reliable messaging is a framework for applications running in WebLogic Server to asynchronously and reliably invoke a Web service running in a different WebLogic Server.  Reliable messaging works only between WebLogic Servers.  This class encapsulates the default reliable messaging parameters for an application running in this WebLogic Server instance that both sends and receives a SOAP message reliably. These parameters include the number of times to retry sending the message, the time to wait between retries, the persistent store for the reliable message, and so on.  "
      ::= { wls 827  }
      
   
   wsReliableDeliveryPolicyEntry OBJECT-TYPE
      SYNTAX      WsReliableDeliveryPolicyEntry
      MAX-ACCESS  not-accessible
      STATUS      current
      DESCRIPTION "Entry of wsReliableDeliveryPolicyTable"
      INDEX { wsReliableDeliveryPolicyIndex}
      ::= { wsReliableDeliveryPolicyTable 1 }
      
   WsReliableDeliveryPolicyEntry ::=
      SEQUENCE
      {
         wsReliableDeliveryPolicyIndex DisplayString,
         wsReliableDeliveryPolicyObjectName DisplayString,
         wsReliableDeliveryPolicyType DisplayString,
         wsReliableDeliveryPolicyName DisplayString,
         wsReliableDeliveryPolicyParent DisplayString,
         wsReliableDeliveryPolicyDefaultRetryCount INTEGER,
         wsReliableDeliveryPolicyDefaultRetryInterval INTEGER,
         wsReliableDeliveryPolicyDefaultTimeToLive INTEGER,
         wsReliableDeliveryPolicyTags OCTET STRING
      }
      
   
   wsReliableDeliveryPolicyIndex OBJECT-TYPE
      SYNTAX      DisplayString (SIZE (1..16))
      MAX-ACCESS  read-only
      STATUS      current
      DESCRIPTION "Unique value directed from ObjectName which is used as table index"
      ::= { wsReliableDeliveryPolicyEntry 1  }
   
   
   wsReliableDeliveryPolicyObjectName OBJECT-TYPE
      SYNTAX      DisplayString (SIZE (1..256))
      MAX-ACCESS  read-only
      STATUS      current
      DESCRIPTION "JMX-standard MBean name"
      ::= { wsReliableDeliveryPolicyEntry 5  }
   
   
   wsReliableDeliveryPolicyType OBJECT-TYPE
      SYNTAX      DisplayString (SIZE (1..64))
      MAX-ACCESS  read-only
      STATUS      current
      DESCRIPTION "Returns the type of the MBean. "
      ::= { wsReliableDeliveryPolicyEntry 10  }
   
   
   wsReliableDeliveryPolicyName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wsReliableDeliveryPolicyEntry 15  }
   
   
   wsReliableDeliveryPolicyParent OBJECT-TYPE
      SYNTAX      DisplayString (SIZE (1..256))
      MAX-ACCESS  read-only
      STATUS      current
      DESCRIPTION "BEA-proprietary Parent object's identification, with syntax
      <type>:<name>"
      ::= { wsReliableDeliveryPolicyEntry 20  }
   
   
   wsReliableDeliveryPolicyDefaultRetryCount OBJECT-TYPE
      SYNTAX      INTEGER
      MAX-ACCESS  read-only
      STATUS      current
      DESCRIPTION "The default maximum number of times that the sender runtime should attempt to redeliver a message that the receiver WebLogic Server has not yet acknowledged.  The default maximum number of times that the sender should attempt to redeliver a message that the receiver WebLogic Web service has not yet acknowledged. "
      ::= { wsReliableDeliveryPolicyEntry 21  }
   
   
   wsReliableDeliveryPolicyDefaultRetryInterval OBJECT-TYPE
      SYNTAX      INTEGER
      MAX-ACCESS  read-only
      STATUS      current
      DESCRIPTION "The default minimum number of seconds that the sender runtime should wait between retries if the receiver does not send an acknowledgement of receiving the message, or if the sender runtime detects a communications error while attempting to send a message.  The default minimum number of seconds that the sender should wait between retries if the receiver does not send an acknowledgement of receiving the message, or if the sender detects a communications error while attempting to send a message. "
      ::= { wsReliableDeliveryPolicyEntry 22  }
   
   
   wsReliableDeliveryPolicyDefaultTimeToLive OBJECT-TYPE
      SYNTAX      INTEGER
      MAX-ACCESS  read-only
      STATUS      current
      DESCRIPTION "The default number of seconds that the receiver of the reliable message should persist the history of the reliable message in its store.  The default minimum number of seconds that the receiver of the reliably sent message should persist the message in its storage.  If the DefaultTimeToLive number of message have passed since the message was first sent, the sender should not resent a message with the same message id.  If a sender cannot send a message successfully before the DefaultTimeToLive has passed, the sender should report a delivery failure. The receiver, after recovering from a crash, will not dispatch saved messages that have expired. "
      ::= { wsReliableDeliveryPolicyEntry 23  }
   
   
   wsReliableDeliveryPolicyTags OBJECT-TYPE
      SYNTAX      OCTET STRING
      MAX-ACCESS  read-only
      STATUS      current
      DESCRIPTION "Return all tags on this Configuration MBean "
      ::= { wsReliableDeliveryPolicyEntry 24  }
   
   
   wtcPasswordTable OBJECT-TYPE
      SYNTAX      SEQUENCE OF WtcPasswordEntry
      MAX-ACCESS  not-accessible
      STATUS      current
      DESCRIPTION "This interface provides access to the WTC password configuration attributes. The methods defined herein are applicable for WTC configuration at the WLS domain level. "
      ::= { wls 829  }
      
   
   wtcPasswordEntry OBJECT-TYPE
      SYNTAX      WtcPasswordEntry
      MAX-ACCESS  not-accessible
      STATUS      current
      DESCRIPTION "Entry of wtcPasswordTable"
      INDEX { wtcPasswordIndex}
      ::= { wtcPasswordTable 1 }
      
   WtcPasswordEntry ::=
      SEQUENCE
      {
         wtcPasswordIndex     DisplayString,
         wtcPasswordObjectName DisplayString,
         wtcPasswordType      DisplayString,
         wtcPasswordName      DisplayString,
         wtcPasswordParent    DisplayString,
         wtcPasswordLocalAccessPoint DisplayString,
         wtcPasswordRemoteAccessPoint DisplayString,
         wtcPasswordRemotePassword OCTET STRING,
         wtcPasswordRemotePasswordIV OCTET STRING,
         wtcPasswordLocalPasswordIV OCTET STRING,
         wtcPasswordLocalPassword OCTET STRING,
         wtcPasswordTags      OCTET STRING
      }
      
   
   wtcPasswordIndex OBJECT-TYPE
      SYNTAX      DisplayString (SIZE (1..16))
      MAX-ACCESS  read-only
      STATUS      current
      DESCRIPTION "Unique value directed from ObjectName which is used as table index"
      ::= { wtcPasswordEntry 1  }
   
   
   wtcPasswordObjectName OBJECT-TYPE
      SYNTAX      DisplayString (SIZE (1..256))
      MAX-ACCESS  read-only
      STATUS      current
      DESCRIPTION "JMX-standard MBean name"
      ::= { wtcPasswordEntry 5  }
   
   
   wtcPasswordType OBJECT-TYPE
      SYNTAX      DisplayString (SIZE (1..64))
      MAX-ACCESS  read-only
      STATUS      current
      DESCRIPTION "Returns the type of the MBean. "
      ::= { wtcPasswordEntry 10  }
   
   
   wtcPasswordName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtcPasswordEntry 15  }
   
   
   wtcPasswordParent OBJECT-TYPE
      SYNTAX      DisplayString (SIZE (1..256))
      MAX-ACCESS  read-only
      STATUS      current
      DESCRIPTION "BEA-proprietary Parent object's identification, with syntax
      <type>:<name>"
      ::= { wtcPasswordEntry 20  }
   
   
   wtcPasswordLocalAccessPoint OBJECT-TYPE
      SYNTAX      DisplayString
      MAX-ACCESS  read-only
      STATUS      current
      DESCRIPTION "The name of the local access point to which this password applies. "
      ::= { wtcPasswordEntry 21  }
   
   
   wtcPasswordRemoteAccessPoint OBJECT-TYPE
      SYNTAX      DisplayString
      MAX-ACCESS  read-only
      STATUS      current
      DESCRIPTION "The name of the remote access point to which this password applies. "
      ::= { wtcPasswordEntry 22  }
   
   
   wtcPasswordRemotePassword OBJECT-TYPE
      SYNTAX      OCTET STRING
      MAX-ACCESS  read-only
      STATUS      current
      DESCRIPTION "The remote password used to authenticate connections between the local access point and remote access point.  Note: This password is used to authenticate connections between the local Tuxedo access point identified by LocalAccessPoint and the remote Tuxedo access point identified by RemoteAccessPoint. "
      ::= { wtcPasswordEntry 23  }
   
   
   wtcPasswordRemotePasswordIV OBJECT-TYPE
      SYNTAX      OCTET STRING
      MAX-ACCESS  read-only
      STATUS      current
      DESCRIPTION "The initialization vector used to encrypt the remote password. "
      ::= { wtcPasswordEntry 24  }
   
   
   wtcPasswordLocalPasswordIV OBJECT-TYPE
      SYNTAX      OCTET STRING
      MAX-ACCESS  read-only
      STATUS      current
      DESCRIPTION "The initialization vector used to encrypt the local password. "
      ::= { wtcPasswordEntry 25  }
   
   
   wtcPasswordLocalPassword OBJECT-TYPE
      SYNTAX      OCTET STRING
      MAX-ACCESS  read-only
      STATUS      current
      DESCRIPTION "The local password used to authenticate connections between the local access point and the remote access point.  Note: This password is used to authenticate connections between the local Tuxedo access point identified by LocalAccessPoint and the remote Tuxedo access point identified by RemoteAccessPoint. "
      ::= { wtcPasswordEntry 26  }
   
   
   wtcPasswordTags OBJECT-TYPE
      SYNTAX      OCTET STRING
      MAX-ACCESS  read-only
      STATUS      current
      DESCRIPTION "Return all tags on this Configuration MBean "
      ::= { wtcPasswordEntry 27  }
   
   
   wtcResourcesTable OBJECT-TYPE
      SYNTAX      SEQUENCE OF WtcResourcesEntry
      MAX-ACCESS  not-accessible
      STATUS      current
      DESCRIPTION "This interface provides access to the WTC resources configuration attributes. The methods defined herein are applicable for WTC configuration at the WLS domain level. "
      ::= { wls 831  }
      
   
   wtcResourcesEntry OBJECT-TYPE
      SYNTAX      WtcResourcesEntry
      MAX-ACCESS  not-accessible
      STATUS      current
      DESCRIPTION "Entry of wtcResourcesTable"
      INDEX { wtcResourcesIndex}
      ::= { wtcResourcesTable 1 }
      
   WtcResourcesEntry ::=
      SEQUENCE
      {
         wtcResourcesIndex    DisplayString,
         wtcResourcesObjectName DisplayString,
         wtcResourcesType     DisplayString,
         wtcResourcesName     DisplayString,
         wtcResourcesParent   DisplayString,
         wtcResourcesFldTbl16Classes DisplayString,
         wtcResourcesFldTbl32Classes DisplayString,
         wtcResourcesTpUsrFile DisplayString,
         wtcResourcesViewTbl16Classes DisplayString,
         wtcResourcesViewTbl32Classes DisplayString,
         wtcResourcesAppPassword OCTET STRING,
         wtcResourcesRemoteMBEncoding OCTET STRING,
         wtcResourcesMBEncodingMapFile OCTET STRING,
         wtcResourcesAppPasswordIV OCTET STRING,
         wtcResourcesTags     OCTET STRING
      }
      
   
   wtcResourcesIndex OBJECT-TYPE
      SYNTAX      DisplayString (SIZE (1..16))
      MAX-ACCESS  read-only
      STATUS      current
      DESCRIPTION "Unique value directed from ObjectName which is used as table index"
      ::= { wtcResourcesEntry 1  }
   
   
   wtcResourcesObjectName OBJECT-TYPE
      SYNTAX      DisplayString (SIZE (1..256))
      MAX-ACCESS  read-only
      STATUS      current
      DESCRIPTION "JMX-standard MBean name"
      ::= { wtcResourcesEntry 5  }
   
   
   wtcResourcesType OBJECT-TYPE
      SYNTAX      DisplayString (SIZE (1..64))
      MAX-ACCESS  read-only
      STATUS      current
      DESCRIPTION "Returns the type of the MBean. "
      ::= { wtcResourcesEntry 10  }
   
   
   wtcResourcesName OBJECT-TYPE
      SYNTAX      DisplayString (SIZE (1..64))
      MAX-ACCESS  read-only
      STATUS      current
      DESCRIPTION "The user-specified name of this MBean instance.  This name is included as one of the key properties in the MBean's javax.management.ObjectName:  Name=user-specified-name "
      ::= { wtcResourcesEntry 15  }
   
   
   wtcResourcesParent OBJECT-TYPE
      SYNTAX      DisplayString (SIZE (1..256))
      MAX-ACCESS  read-only
      STATUS      current
      DESCRIPTION "BEA-proprietary Parent object's identification, with syntax
      <type>:<name>"
      ::= { wtcResourcesEntry 20  }
   
   
   wtcResourcesFldTbl16Classes OBJECT-TYPE
      SYNTAX      DisplayString
      MAX-ACCESS  read-only
      STATUS      current
      DESCRIPTION "The names of FldTbl16Classes that are loaded via a class loader and added to a FldTbl array.  Value Requirements:   Used fully qualified names of the desired classes.   Use a comma-separated list to enter multiple classes.   "
      ::= { wtcResourcesEntry 21  }
   
   
   wtcResourcesFldTbl32Classes OBJECT-TYPE
      SYNTAX      DisplayString
      MAX-ACCESS  read-only
      STATUS      current
      DESCRIPTION "The names of FldTbl32Classes that are loaded via a class loader and added to a FldTbl array.  Value Requirements:   Used fully qualified names of the desired classes.   Use a comma-separated list to enter multiple classes   "
      ::= { wtcResourcesEntry 22  }
   
   
   wtcResourcesTpUsrFile OBJECT-TYPE
      SYNTAX      DisplayString
      MAX-ACCESS  read-only
      STATUS      current
      DESCRIPTION "The full path to the TPUSR file, which contains Tuxedo UID/GID information.  Note: This file is generated by the Tuxedo tpusradd utility on the remote Tuxedo domain. "
      ::= { wtcResourcesEntry 23  }
   
   
   wtcResourcesViewTbl16Classes OBJECT-TYPE
      SYNTAX      DisplayString
      MAX-ACCESS  read-only
      STATUS      current
      DESCRIPTION "The names of ViewTbl16Classes that are loaded via a class loader and added to a ViewTbl array.  Value Requirements:   Used fully qualified names of the desired classes.   Use a comma-separated list to enter multiple classes.   "
      ::= { wtcResourcesEntry 24  }
   
   
   wtcResourcesViewTbl32Classes OBJECT-TYPE
      SYNTAX      DisplayString
      MAX-ACCESS  read-only
      STATUS      current
      DESCRIPTION "The names of ViewTbl32Classes that are loaded via a class loader and added to a ViewTbl array.  Value Requirements:   Used fully qualified names of the desired classes.   Use a comma-separated list to enter multiple classes.   "
      ::= { wtcResourcesEntry 25  }
   
   
   wtcResourcesAppPassword OBJECT-TYPE
      SYNTAX      OCTET STRING
      MAX-ACCESS  read-only
      STATUS      current
      DESCRIPTION "The application password as returned from the genpasswd utility.  Note: This Tuxedo application password is the encrypted password used to authenticate connections. "
      ::= { wtcResourcesEntry 26  }
   
   
   wtcResourcesRemoteMBEncoding OBJECT-TYPE
      SYNTAX      OCTET STRING
      MAX-ACCESS  read-only
      STATUS      current
      DESCRIPTION "The default encoding name of sending MBSTRING data. "
      ::= { wtcResourcesEntry 27  }
   
   
   wtcResourcesMBEncodingMapFile OBJECT-TYPE
      SYNTAX      OCTET STRING
      MAX-ACCESS  read-only
      STATUS      current
      DESCRIPTION "The encoding name map file between Java and Tuxedo MBSTRING. "
      ::= { wtcResourcesEntry 28  }
   
   
   wtcResourcesAppPasswordIV OBJECT-TYPE
      SYNTAX      OCTET STRING
      MAX-ACCESS  read-only
      STATUS      current
      DESCRIPTION "The initialization vector used to encrypt the AppPassword.  Note: This value is returned from the genpasswd utility with the AppPassword. "
      ::= { wtcResourcesEntry 29  }
   
   
   wtcResourcesTags OBJECT-TYPE
      SYNTAX      OCTET STRING
      MAX-ACCESS  read-only
      STATUS      current
      DESCRIPTION "Return all tags on this Configuration MBean "
      ::= { wtcResourcesEntry 30  }
   
   
   adminConsoleTable OBJECT-TYPE
      SYNTAX      SEQUENCE OF AdminConsoleEntry
      MAX-ACCESS  not-accessible
      STATUS      current
      DESCRIPTION "AdminConsoleMBean is a console specific MBean to configure weblogic administration console attributes. "
      ::= { wls 840  }
      
   
   adminConsoleEntry OBJECT-TYPE
      SYNTAX      AdminConsoleEntry
      MAX-ACCESS  not-accessible
      STATUS      current
      DESCRIPTION "Generated SNMP Table Entry."
      INDEX { adminConsoleIndex}
      ::= { adminConsoleTable 1 }
      
   AdminConsoleEntry ::=
      SEQUENCE
      {
         adminConsoleIndex    OCTET STRING,
         adminConsoleObjectName OCTET STRING,
         adminConsoleType     OCTET STRING,
         adminConsoleSessionTimeout Integer32,
         adminConsoleCookieName OCTET STRING,
         adminConsoleName     OCTET STRING,
         adminConsoleSSOLogoutURL OCTET STRING,
         adminConsoleTags     OCTET STRING,
         adminConsoleProtectedCookieEnabled OCTET STRING,
         adminConsoleMinThreads INTEGER
      }
      
   
   adminConsoleIndex OBJECT-TYPE
      SYNTAX      OCTET STRING
      MAX-ACCESS  not-accessible
      STATUS      current
      DESCRIPTION "Index column"
      ::= { adminConsoleEntry 1  }
   
   
   adminConsoleObjectName OBJECT-TYPE
      SYNTAX      OCTET STRING
      MAX-ACCESS  read-only
      STATUS      current
      DESCRIPTION "ObjectName column"
      ::= { adminConsoleEntry 2  }
   
   
   adminConsoleType OBJECT-TYPE
      SYNTAX      OCTET STRING
      MAX-ACCESS  read-only
      STATUS      current
      DESCRIPTION "Returns the type of the MBean. "
      ::= { adminConsoleEntry 3  }
   
   
   adminConsoleSessionTimeout OBJECT-TYPE
      SYNTAX      Integer32
      MAX-ACCESS  read-only
      STATUS      current
      DESCRIPTION "Returns Session Timeout value (in seconds) for Administration Console.  "
      ::= { adminConsoleEntry 4  }
   
   
   adminConsoleCookieName OBJECT-TYPE
      SYNTAX      OCTET STRING
      MAX-ACCESS  read-only
      STATUS      current
      DESCRIPTION "Returns the Cookie Name used by the Administration Console.  "
      ::= { adminConsoleEntry 5  }
   
   
   adminConsoleName OBJECT-TYPE
      SYNTAX      OCTET STRING
      MAX-ACCESS  read-only
      STATUS      current
      DESCRIPTION "The user-specified name of this MBean instance.  This name is included as one of the key properties in the MBean's javax.management.ObjectName:  Name=user-specified-name "
      ::= { adminConsoleEntry 6  }
   
   
   adminConsoleSSOLogoutURL OBJECT-TYPE
      SYNTAX      OCTET STRING
      MAX-ACCESS  read-only
      STATUS      current
      DESCRIPTION "Returns the log out URL for the Administration Console in a single sign-on (SSO) environment. Only needed when you use the Console with an SSO provider that requires a log out URL so that it can clean up its SSO session state. See the SSO provider documentation for details on the URL value "
      ::= { adminConsoleEntry 7  }
   
   
   adminConsoleTags OBJECT-TYPE
      SYNTAX      OCTET STRING
      MAX-ACCESS  read-only
      STATUS      current
      DESCRIPTION "Return all tags on this Configuration MBean "
      ::= { adminConsoleEntry 8  }
   
   
   adminConsoleProtectedCookieEnabled OBJECT-TYPE
      SYNTAX      OCTET STRING
      MAX-ACCESS  read-only
      STATUS      current
      DESCRIPTION "Set to true if the Administration Console's session cookie is protected so that it is only visible to the Console. This may prevent use of this shared cookie in other applications. "
      ::= { adminConsoleEntry 9  }
   
   
   adminConsoleMinThreads OBJECT-TYPE
      SYNTAX      INTEGER
      MAX-ACCESS  read-only
      STATUS      current
      DESCRIPTION "Specify the minimum number of threads that should be dedicated to the Administration Console. These threads are used to interact with managed servers in parallel for improved responsiveness in large domains. 5 is the smallest accepted number. "
      ::= { adminConsoleEntry 10  }
   
   
   capacityTable OBJECT-TYPE
      SYNTAX      SEQUENCE OF CapacityEntry
      MAX-ACCESS  not-accessible
      STATUS      current
      DESCRIPTION "CapacityMBean defines the maximum number of requests that can be enqueued by all the work managers that share it.  The server starts rejecting requests once the capacity threshold is reached. Note that the capacity includes all requests, queued or executing, from the constrained work set. This constraint is independent of the global queue threshold specified by {@link OverloadProtectionMBean#getSharedCapacityForWorkManagers()}.   Requests are rejected by performing overload actions. RMI work is rejected by sending back a recoverable exception to the clients. Servlet requests are rejected by sending back a 503 response.  "
      ::= { wls 850  }
      
   
   capacityEntry OBJECT-TYPE
      SYNTAX      CapacityEntry
      MAX-ACCESS  not-accessible
      STATUS      current
      DESCRIPTION "Generated SNMP Table Entry."
      INDEX { capacityIndex}
      ::= { capacityTable 1 }
      
   CapacityEntry ::=
      SEQUENCE
      {
         capacityIndex        OCTET STRING,
         capacityObjectName   OCTET STRING,
         capacityType         OCTET STRING,
         capacityDeploymentOrder Integer32,
         capacityCount        Integer32,
         capacityName         OCTET STRING,
         capacityTags         OCTET STRING
      }
      
   
   capacityIndex OBJECT-TYPE
      SYNTAX      OCTET STRING
      MAX-ACCESS  not-accessible
      STATUS      current
      DESCRIPTION "Index column"
      ::= { capacityEntry 1  }
   
   
   capacityObjectName OBJECT-TYPE
      SYNTAX      OCTET STRING
      MAX-ACCESS  read-only
      STATUS      current
      DESCRIPTION "ObjectName column"
      ::= { capacityEntry 2  }
   
   
   capacityType OBJECT-TYPE
      SYNTAX      OCTET STRING
      MAX-ACCESS  read-only
      STATUS      current
      DESCRIPTION "Returns the type of the MBean. "
      ::= { capacityEntry 3  }
   
   
   capacityDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { capacityEntry 4  }
   
   
   capacityCount OBJECT-TYPE
      SYNTAX      Integer32
      MAX-ACCESS  read-only
      STATUS      current
      DESCRIPTION "Total number of requests that can be enqueued. "
      ::= { capacityEntry 5  }
   
   
   capacityName OBJECT-TYPE
      SYNTAX      OCTET STRING
      MAX-ACCESS  read-only
      STATUS      current
      DESCRIPTION "The user-specified name of this MBean instance.  This name is included as one of the key properties in the MBean's javax.management.ObjectName:  Name=user-specified-name "
      ::= { capacityEntry 6  }
   
   
   capacityTags OBJECT-TYPE
      SYNTAX      OCTET STRING
      MAX-ACCESS  read-only
      STATUS      current
      DESCRIPTION "Return all tags on this Configuration MBean "
      ::= { capacityEntry 7  }
   
   
   configurationPropertyTable OBJECT-TYPE
      SYNTAX      SEQUENCE OF ConfigurationPropertyEntry
      MAX-ACCESS  not-accessible
      STATUS      current
      DESCRIPTION "Encapsulates information about a property, such as its value and whether it is encrypted. "
      ::= { wls 855  }
      
   
   configurationPropertyEntry OBJECT-TYPE
      SYNTAX      ConfigurationPropertyEntry
      MAX-ACCESS  not-accessible
      STATUS      current
      DESCRIPTION "Generated SNMP Table Entry."
      INDEX { configurationPropertyIndex}
      ::= { configurationPropertyTable 1 }
      
   ConfigurationPropertyEntry ::=
      SEQUENCE
      {
         configurationPropertyIndex OCTET STRING,
         configurationPropertyObjectName OCTET STRING,
         configurationPropertyType OCTET STRING,
         configurationPropertyEncryptValueRequired OCTET STRING,
         configurationPropertyValue OCTET STRING,
         configurationPropertyName OCTET STRING,
         configurationPropertyTags OCTET STRING
      }
      
   
   configurationPropertyIndex OBJECT-TYPE
      SYNTAX      OCTET STRING
      MAX-ACCESS  not-accessible
      STATUS      current
      DESCRIPTION "Index column"
      ::= { configurationPropertyEntry 1  }
   
   
   configurationPropertyObjectName OBJECT-TYPE
      SYNTAX      OCTET STRING
      MAX-ACCESS  read-only
      STATUS      current
      DESCRIPTION "ObjectName column"
      ::= { configurationPropertyEntry 2  }
   
   
   configurationPropertyType OBJECT-TYPE
      SYNTAX      OCTET STRING
      MAX-ACCESS  read-only
      STATUS      current
      DESCRIPTION "Returns the type of the MBean. "
      ::= { configurationPropertyEntry 3  }
   
   
   configurationPropertyEncryptValueRequired OBJECT-TYPE
      SYNTAX      OCTET STRING
      MAX-ACCESS  read-only
      STATUS      current
      DESCRIPTION "Specifies whether the property should be encrypted.   By default, the value of a property is not encrypted and anyone using the Administration Console can view the value of the property. If this attribute is set to true, then the value of the property on the Administration Console will be set to all asterisks. "
      ::= { configurationPropertyEntry 4  }
   
   
   configurationPropertyValue OBJECT-TYPE
      SYNTAX      OCTET STRING
      MAX-ACCESS  read-only
      STATUS      current
      DESCRIPTION "Specifies the value of the property.  If the property is encrypted, then attribute is null and one should use the EncryptedValue attribute to get the decrypted value. "
      ::= { configurationPropertyEntry 5  }
   
   
   configurationPropertyName OBJECT-TYPE
      SYNTAX      OCTET STRING
      MAX-ACCESS  read-only
      STATUS      current
      DESCRIPTION "The user-specified name of this MBean instance.  This name is included as one of the key properties in the MBean's javax.management.ObjectName:  Name=user-specified-name "
      ::= { configurationPropertyEntry 6  }
   
   
   configurationPropertyTags OBJECT-TYPE
      SYNTAX      OCTET STRING
      MAX-ACCESS  read-only
      STATUS      current
      DESCRIPTION "Return all tags on this Configuration MBean "
      ::= { configurationPropertyEntry 7  }
   
   
   contextCaseTable OBJECT-TYPE
      SYNTAX      SEQUENCE OF ContextCaseEntry
      MAX-ACCESS  not-accessible
      STATUS      current
      DESCRIPTION "This mbean defines the mapping between the current context (security principal, group etc) and the request class to use. "
      ::= { wls 860  }
      
   
   contextCaseEntry OBJECT-TYPE
      SYNTAX      ContextCaseEntry
      MAX-ACCESS  not-accessible
      STATUS      current
      DESCRIPTION "Generated SNMP Table Entry."
      INDEX { contextCaseIndex}
      ::= { contextCaseTable 1 }
      
   ContextCaseEntry ::=
      SEQUENCE
      {
         contextCaseIndex     OCTET STRING,
         contextCaseObjectName OCTET STRING,
         contextCaseType      OCTET STRING,
         contextCaseRequestClassName OCTET STRING,
         contextCaseDeploymentOrder Integer32,
         contextCaseGroupName OCTET STRING,
         contextCaseName      OCTET STRING,
         contextCaseUserName  OCTET STRING,
         contextCaseTags      OCTET STRING
      }
      
   
   contextCaseIndex OBJECT-TYPE
      SYNTAX      OCTET STRING
      MAX-ACCESS  not-accessible
      STATUS      current
      DESCRIPTION "Index column"
      ::= { contextCaseEntry 1  }
   
   
   contextCaseObjectName OBJECT-TYPE
      SYNTAX      OCTET STRING
      MAX-ACCESS  read-only
      STATUS      current
      DESCRIPTION "ObjectName column"
      ::= { contextCaseEntry 2  }
   
   
   contextCaseType OBJECT-TYPE
      SYNTAX      OCTET STRING
      MAX-ACCESS  read-only
      STATUS      current
      DESCRIPTION "Returns the type of the MBean. "
      ::= { contextCaseEntry 3  }
   
   
   contextCaseRequestClassName OBJECT-TYPE
      SYNTAX      OCTET STRING
      MAX-ACCESS  read-only
      STATUS      current
      DESCRIPTION "The name of the request class to be used for processing requests for the specified user and/or group. "
      ::= { contextCaseEntry 4  }
   
   
   contextCaseDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { contextCaseEntry 5  }
   
   
   contextCaseGroupName OBJECT-TYPE
      SYNTAX      OCTET STRING
      MAX-ACCESS  read-only
      STATUS      current
      DESCRIPTION "The name of the user group whose requests are to be processed by the request class with the name specified in RequestClassName. "
      ::= { contextCaseEntry 6  }
   
   
   contextCaseName OBJECT-TYPE
      SYNTAX      OCTET STRING
      MAX-ACCESS  read-only
      STATUS      current
      DESCRIPTION "The user-specified name of this MBean instance.  This name is included as one of the key properties in the MBean's javax.management.ObjectName:  Name=user-specified-name "
      ::= { contextCaseEntry 7  }
   
   
   contextCaseUserName OBJECT-TYPE
      SYNTAX      OCTET STRING
      MAX-ACCESS  read-only
      STATUS      current
      DESCRIPTION "The name of the user whose requests are to be processed by the request class with the name specified in RequestClassName. "
      ::= { contextCaseEntry 8  }
   
   
   contextCaseTags OBJECT-TYPE
      SYNTAX      OCTET STRING
      MAX-ACCESS  read-only
      STATUS      current
      DESCRIPTION "Return all tags on this Configuration MBean "
      ::= { contextCaseEntry 9  }
   
   
   contextRequestClassTable OBJECT-TYPE
      SYNTAX      SEQUENCE OF ContextRequestClassEntry
      MAX-ACCESS  not-accessible
      STATUS      current
      DESCRIPTION "This mbean defines the mapping between the current context (security principal, group) and the request class to use.   ContextRequestClass provides a mapping between security names/groups and request classes. During work schedule, the exact request class is determined by looking at the security information of the caller. ContextRequestClass is not a request class by itself and is used to hold the mapping of request classes.  "
      ::= { wls 865  }
      
   
   contextRequestClassEntry OBJECT-TYPE
      SYNTAX      ContextRequestClassEntry
      MAX-ACCESS  not-accessible
      STATUS      current
      DESCRIPTION "Generated SNMP Table Entry."
      INDEX { contextRequestClassIndex}
      ::= { contextRequestClassTable 1 }
      
   ContextRequestClassEntry ::=
      SEQUENCE
      {
         contextRequestClassIndex OCTET STRING,
         contextRequestClassObjectName OCTET STRING,
         contextRequestClassType OCTET STRING,
         contextRequestClassDeploymentOrder Integer32,
         contextRequestClassName OCTET STRING,
         contextRequestClassTags OCTET STRING
      }
      
   
   contextRequestClassIndex OBJECT-TYPE
      SYNTAX      OCTET STRING
      MAX-ACCESS  not-accessible
      STATUS      current
      DESCRIPTION "Index column"
      ::= { contextRequestClassEntry 1  }
   
   
   contextRequestClassObjectName OBJECT-TYPE
      SYNTAX      OCTET STRING
      MAX-ACCESS  read-only
      STATUS      current
      DESCRIPTION "ObjectName column"
      ::= { contextRequestClassEntry 2  }
   
   
   contextRequestClassType OBJECT-TYPE
      SYNTAX      OCTET STRING
      MAX-ACCESS  read-only
      STATUS      current
      DESCRIPTION "Returns the type of the MBean. "
      ::= { contextRequestClassEntry 3  }
   
   
   contextRequestClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { contextRequestClassEntry 4  }
   
   
   contextRequestClassName OBJECT-TYPE
      SYNTAX      OCTET STRING
      MAX-ACCESS  read-only
      STATUS      current
      DESCRIPTION "The user-specified name of this MBean instance.  This name is included as one of the key properties in the MBean's javax.management.ObjectName:  Name=user-specified-name "
      ::= { contextRequestClassEntry 5  }
   
   
   contextRequestClassTags OBJECT-TYPE
      SYNTAX      OCTET STRING
      MAX-ACCESS  read-only
      STATUS      current
      DESCRIPTION "Return all tags on this Configuration MBean "
      ::= { contextRequestClassEntry 6  }
   
   
   customResourceTable OBJECT-TYPE
      SYNTAX      SEQUENCE OF CustomResourceEntry
      MAX-ACCESS  not-accessible
      STATUS      current
      DESCRIPTION "A CustomResource is an untyped SystemResource for which creator of the bean defines the name of the class that will be used when the resource is deployed on the managed server. "
      ::= { wls 875  }
      
   
   customResourceEntry OBJECT-TYPE
      SYNTAX      CustomResourceEntry
      MAX-ACCESS  not-accessible
      STATUS      current
      DESCRIPTION "Generated SNMP Table Entry."
      INDEX { customResourceIndex}
      ::= { customResourceTable 1 }
      
   CustomResourceEntry ::=
      SEQUENCE
      {
         customResourceIndex  OCTET STRING,
         customResourceObjectName OCTET STRING,
         customResourceType   OCTET STRING,
         customResourceResourceClass OCTET STRING,
         customResourceCompatibilityName OCTET STRING,
         customResourceDeploymentOrder Integer32,
         customResourceDescriptorBeanClass OCTET STRING,
         customResourceDeploymentPrincipalName OCTET STRING,
         customResourceDescriptorFileName OCTET STRING,
         customResourceModuleType OCTET STRING,
         customResourceName   OCTET STRING,
         customResourceSourcePath OCTET STRING,
         customResourceTags   OCTET STRING
      }
      
   
   customResourceIndex OBJECT-TYPE
      SYNTAX      OCTET STRING
      MAX-ACCESS  not-accessible
      STATUS      current
      DESCRIPTION "Index column"
      ::= { customResourceEntry 1  }
   
   
   customResourceObjectName OBJECT-TYPE
      SYNTAX      OCTET STRING
      MAX-ACCESS  read-only
      STATUS      current
      DESCRIPTION "ObjectName column"
      ::= { customResourceEntry 2  }
   
   
   customResourceType OBJECT-TYPE
      SYNTAX      OCTET STRING
      MAX-ACCESS  read-only
      STATUS      current
      DESCRIPTION "Returns the type of the MBean. "
      ::= { customResourceEntry 3  }
   
   
   customResourceResourceClass OBJECT-TYPE
      SYNTAX      OCTET STRING
      MAX-ACCESS  read-only
      STATUS      current
      DESCRIPTION "This is the name of the class that is used to manage the lifecycle of the resource.  An instance of the ResourceClass is created and is passed the DescriptorBean.  If this value is not set then the resource does not participate in the deployment lifecycle and simply represent a distribution of configuration information to be used by other subsystems. "
      ::= { customResourceEntry 4  }
   
   
   customResourceCompatibilityName OBJECT-TYPE
      SYNTAX      OCTET STRING
      MAX-ACCESS  read-only
      STATUS      current
      DESCRIPTION " This is only set for beans created as a result of conversion from an 8.1 application configured using ApplicationMBean and ComponentMBean.  Standalone modules in 8.1 have both an ApplicationMBean name and ComponentMBean name. This attribute stores the name of the latter, to be used when the server creates the transient ComponentMBean for backward compatibility. "
      ::= { customResourceEntry 5  }
   
   
   customResourceDeploymentOrder OBJECT-TYPE
      SYNTAX      Integer32
      MAX-ACCESS  read-only
      STATUS      current
      DESCRIPTION "An integer value that indicates when this unit is deployed, relative to other deployable units on a server, during startup.  Units with lower values are deployed before those with higher values. "
      ::= { customResourceEntry 6  }
   
   
   customResourceDescriptorBeanClass OBJECT-TYPE
      SYNTAX      OCTET STRING
      MAX-ACCESS  read-only
      STATUS      current
      DESCRIPTION "Returns the interface of the bean that is returned by the #getResource method. "
      ::= { customResourceEntry 7  }
   
   
   customResourceDeploymentPrincipalName OBJECT-TYPE
      SYNTAX      OCTET STRING
      MAX-ACCESS  read-only
      STATUS      current
      DESCRIPTION "A string value that indicates the principal that should be used when deploying the file or archive during startup and shutdown. This principal will be used to set the current subject when calling out into application code for interfaces such as ApplicationLifecycleListener. If no principal name is specified, then the anonymous principal will be used. "
      ::= { customResourceEntry 8  }
   
   
   customResourceDescriptorFileName OBJECT-TYPE
      SYNTAX      OCTET STRING
      MAX-ACCESS  read-only
      STATUS      current
      DESCRIPTION "The name of the file that contains the module. By default the file resides in the DOMAIN_DIR/config directory. By default, the file name is derived from the bean name using the following pattern:  &lt;beanName&gt;.xml  Note that this is a read-only property that can only be set when the bean is created. "
      ::= { customResourceEntry 9  }
   
   
   customResourceModuleType OBJECT-TYPE
      SYNTAX      OCTET STRING
      MAX-ACCESS  read-only
      STATUS      current
      DESCRIPTION "The values match those defined by jsr88. This attribute may move to another MBean. "
      ::= { customResourceEntry 10  }
   
   
   customResourceName OBJECT-TYPE
      SYNTAX      OCTET STRING
      MAX-ACCESS  read-only
      STATUS      current
      DESCRIPTION "Unique identifier for this bean instance. "
      ::= { customResourceEntry 11  }
   
   
   customResourceSourcePath OBJECT-TYPE
      SYNTAX      OCTET STRING
      MAX-ACCESS  read-only
      STATUS      current
      DESCRIPTION " "
      ::= { customResourceEntry 12  }
   
   
   customResourceTags OBJECT-TYPE
      SYNTAX      OCTET STRING
      MAX-ACCESS  read-only
      STATUS      current
      DESCRIPTION "Return all tags on this Configuration MBean "
      ::= { customResourceEntry 13  }
   
   
   databaseLessLeasingBasisTable OBJECT-TYPE
      SYNTAX      SEQUENCE OF DatabaseLessLeasingBasisEntry
      MAX-ACCESS  not-accessible
      STATUS      current
      DESCRIPTION "DatabaseLessLeasingBasisMBean defines attributes related to the functioning of singleton services and server migration without the use of a HA database. "
      ::= { wls 880  }
      
   
   databaseLessLeasingBasisEntry OBJECT-TYPE
      SYNTAX      DatabaseLessLeasingBasisEntry
      MAX-ACCESS  not-accessible
      STATUS      current
      DESCRIPTION "Generated SNMP Table Entry."
      INDEX { databaseLessLeasingBasisIndex}
      ::= { databaseLessLeasingBasisTable 1 }
      
   DatabaseLessLeasingBasisEntry ::=
      SEQUENCE
      {
         databaseLessLeasingBasisIndex OCTET STRING,
         databaseLessLeasingBasisObjectName OCTET STRING,
         databaseLessLeasingBasisType OCTET STRING,
         databaseLessLeasingBasisMemberDiscoveryTimeout Integer32,
         databaseLessLeasingBasisName OCTET STRING,
         databaseLessLeasingBasisTags OCTET STRING
      }
      
   
   databaseLessLeasingBasisIndex OBJECT-TYPE
      SYNTAX      OCTET STRING
      MAX-ACCESS  not-accessible
      STATUS      current
      DESCRIPTION "Index column"
      ::= { databaseLessLeasingBasisEntry 1  }
   
   
   databaseLessLeasingBasisObjectName OBJECT-TYPE
      SYNTAX      OCTET STRING
      MAX-ACCESS  read-only
      STATUS      current
      DESCRIPTION "ObjectName column"
      ::= { databaseLessLeasingBasisEntry 2  }
   
   
   databaseLessLeasingBasisType OBJECT-TYPE
      SYNTAX      OCTET STRING
      MAX-ACCESS  read-only
      STATUS      current
      DESCRIPTION "Returns the type of the MBean. "
      ::= { databaseLessLeasingBasisEntry 3  }
   
   
   databaseLessLeasingBasisMemberDiscoveryTimeout OBJECT-TYPE
      SYNTAX      Integer32
      MAX-ACCESS  read-only
      STATUS      current
      DESCRIPTION "Gets the MemberDiscoveryTimeout value. This value defines the amount of time a server waits during or after startup to discover members that belong to the same cluster. This information is used to join or form a new cluster. "
      ::= { databaseLessLeasingBasisEntry 4  }
   
   
   databaseLessLeasingBasisName OBJECT-TYPE
      SYNTAX      OCTET STRING
      MAX-ACCESS  read-only
      STATUS      current
      DESCRIPTION "The user-specified name of this MBean instance.  This name is included as one of the key properties in the MBean's javax.management.ObjectName:  Name=user-specified-name "
      ::= { databaseLessLeasingBasisEntry 5  }
   
   
   databaseLessLeasingBasisTags OBJECT-TYPE
      SYNTAX      OCTET STRING
      MAX-ACCESS  read-only
      STATUS      current
      DESCRIPTION "Return all tags on this Configuration MBean "
      ::= { databaseLessLeasingBasisEntry 6  }
   
   
   defaultFileStoreTable OBJECT-TYPE
      SYNTAX      SEQUENCE OF DefaultFileStoreEntry
      MAX-ACCESS  not-accessible
      STATUS      current
      DESCRIPTION "This MBean describes the configuration of the default file store. Each WebLogic Server instance has a default file store. "
      ::= { wls 890  }
      
   
   defaultFileStoreEntry OBJECT-TYPE
      SYNTAX      DefaultFileStoreEntry
      MAX-ACCESS  not-accessible
      STATUS      current
      DESCRIPTION "Generated SNMP Table Entry."
      INDEX { defaultFileStoreIndex}
      ::= { defaultFileStoreTable 1 }
      
   DefaultFileStoreEntry ::=
      SEQUENCE
      {
         defaultFileStoreIndex OCTET STRING,
         defaultFileStoreObjectName OCTET STRING,
         defaultFileStoreType OCTET STRING,
         defaultFileStoreName OCTET STRING,
         defaultFileStoreMinWindowBufferSize INTEGER,
         defaultFileStoreInitialSize Counter64,
         defaultFileStoreBlockSize INTEGER,
         defaultFileStoreMaxFileSize Counter64,
         defaultFileStoreIoBufferSize INTEGER,
         defaultFileStoreMaxWindowBufferSize INTEGER,
         defaultFileStoreSynchronousWritePolicy OCTET STRING,
         defaultFileStoreDirectory OCTET STRING,
         defaultFileStoreFileLockingEnabled OCTET STRING,
         defaultFileStoreCacheDirectory OCTET STRING,
         defaultFileStoreTags OCTET STRING
      }
      
   
   defaultFileStoreIndex OBJECT-TYPE
      SYNTAX      OCTET STRING
      MAX-ACCESS  not-accessible
      STATUS      current
      DESCRIPTION "Index column"
      ::= { defaultFileStoreEntry 1  }
   
   
   defaultFileStoreObjectName OBJECT-TYPE
      SYNTAX      OCTET STRING
      MAX-ACCESS  read-only
      STATUS      current
      DESCRIPTION "ObjectName column"
      ::= { defaultFileStoreEntry 2  }
   
   
   defaultFileStoreType OBJECT-TYPE
      SYNTAX      OCTET STRING
      MAX-ACCESS  read-only
      STATUS      current
      DESCRIPTION "Returns the type of the MBean. "
      ::= { defaultFileStoreEntry 3  }
   
   
   defaultFileStoreName OBJECT-TYPE
      SYNTAX      OCTET STRING
      MAX-ACCESS  read-only
      STATUS      current
      DESCRIPTION "The user-specified name of this MBean instance.  This name is included as one of the key properties in the MBean's javax.management.ObjectName:  Name=user-specified-name "
      ::= { defaultFileStoreEntry 4  }
   
   
   defaultFileStoreMinWindowBufferSize OBJECT-TYPE
      SYNTAX      INTEGER
      MAX-ACCESS  read-only
      STATUS      current
      DESCRIPTION "The minimum amount of data, in bytes and rounded down to the nearest power of 2, mapped into the JVM's address space per primary store file. Applies to synchronous write policies Direct-Write-With-Cache and Disabled, but only when a native wlfileio library is loaded. See Maximum Window Buffer Size. "
      ::= { defaultFileStoreEntry 5  }
   
   
   defaultFileStoreInitialSize OBJECT-TYPE
      SYNTAX      Counter64
      MAX-ACCESS  read-only
      STATUS      current
      DESCRIPTION "The initial file size, in bytes.  Set InitialSize to pre-allocate file space during a file store boot. If InitialSize exceeds MaxFileSize, a store creates multiple files (number of files = InitialSize/MaxFileSize rounded up).  A file store automatically reuses the space from deleted records and automatically expands a file if there is not enough space for a new write request.  Use InitialSize to limit or prevent file expansions during runtime, as file expansion introduces temporary latencies that may be noticeable under rare circumstances.  Changes to initial size only take effect for new file stores, or after any current files have been deleted prior to restart.   See Maximum File Size.  "
      ::= { defaultFileStoreEntry 6  }
   
   
   defaultFileStoreBlockSize OBJECT-TYPE
      SYNTAX      INTEGER
      MAX-ACCESS  read-only
      STATUS      current
      DESCRIPTION "The smallest addressable block, in bytes, of a file. When a native wlfileio driver is available and the block size has not been configured by the user, the store selects the minimum OS specific value for unbuffered (direct) I/O, if it is within the range [512, 8192]. A file store's block size does not change once the file store creates its files. Changes to block size only take effect for new file stores or after the current files have been deleted. See 'Tuning the Persistent Store' in Tuning Performance of Oracle WebLogic Server. "
      ::= { defaultFileStoreEntry 7  }
   
   
   defaultFileStoreMaxFileSize OBJECT-TYPE
      SYNTAX      Counter64
      MAX-ACCESS  read-only
      STATUS      current
      DESCRIPTION "The maximum file size, in bytes, of an individual data file.  The MaxFileSize value affects the number of files needed to accommodate a store of a particular size (number of files = store size/MaxFileSize rounded up).  A file store automatically reuses space freed by deleted records and automatically expands individual files up to MaxFileSize if there is not enough space for a new record. If there is no space left in exiting files for a new record, a store creates an additional file.   A small number of larger files is normally preferred over a large number of smaller files as each file allocates Window Buffer and file handles.    If MaxFileSize is larger than 2^24 * BlockSize, then MaxFileSize is ignored, and the value becomes 2^24 * BlockSize. The default BlockSize is 512, and 2^24 * 512 is 8 GB.  The minimum size for MaxFileSize is 10 MB when multiple data files are used by the store. If InitialSize is less than MaxFileSize then a single file will be created of InitialSize bytes. If InitialSize is larger than MaxFileSize then (InitialSize / MaxFileSize) files will be created of MaxFileSize bytes and an additional file if necessary to contain any remainder.   See Initial Size.  "
      ::= { defaultFileStoreEntry 8  }
   
   
   defaultFileStoreIoBufferSize OBJECT-TYPE
      SYNTAX      INTEGER
      MAX-ACCESS  read-only
      STATUS      current
      DESCRIPTION "The I/O buffer size, in bytes, automatically rounded down to the nearest power of 2.   For the Direct-Write-With-Cache policy when a native wlfileio driver is available, IOBufferSize describes the maximum portion of a cache view that is passed to a system call. This portion does not consume off-heap (native) or Java heap memory.   For the Direct-Write and Cache-Flush policies, IOBufferSize is the size of a per store buffer which consumes off-heap (native) memory, where one buffer is allocated during run-time, but multiple buffers may be temporarily created during boot recovery.  When a native wlfileio driver is not available, the setting applies to off-heap (native) memory for all policies (including Disabled).  For the best runtime performance, Oracle recommends setting IOBufferSize so that it is larger than the largest write (multiple concurrent store requests may be combined into a single write).  For the best boot recovery time performance of large stores, Oracle recommends setting IOBufferSize to at least 2 megabytes.   See AllocatedIOBufferBytes to find out the actual allocated off-heap (native) memory amount. It is a multiple of IOBufferSize for the Direct-Write and Cache-Flush policies, or zero. "
      ::= { defaultFileStoreEntry 9  }
   
   
   defaultFileStoreMaxWindowBufferSize OBJECT-TYPE
      SYNTAX      INTEGER
      MAX-ACCESS  read-only
      STATUS      current
      DESCRIPTION "The maximum amount of data, in bytes and rounded down to the nearest power of 2, mapped into the JVM's address space per primary store file. Applies to synchronous write policies Direct-Write-With-Cache and Disabled but only when the native wlfileio library is loaded.  A window buffer does not consume Java heap memory, but does consume off-heap (native) memory. If the store is unable to allocate the requested buffer size, it allocates smaller and smaller buffers until it reaches MinWindowBufferSize, and then fails if cannot honor MinWindowBufferSize.  Oracle recommends setting the max window buffer size to more than double the size of the largest write (multiple concurrently updated records may be combined into a single write), and greater than or equal to the file size, unless there are other constraints. 32-bit JVMs may impose a total limit of between 2 and 4GB for combined Java heap plus off-heap (native) memory usage.   See store attribute AllocatedWindowBufferBytes to find out the actual allocated Window Buffer Size.   See Maximum File Size and Minimum Window Buffer Size.  "
      ::= { defaultFileStoreEntry 10  }
   
   
   defaultFileStoreSynchronousWritePolicy OBJECT-TYPE
      SYNTAX      OCTET STRING
      MAX-ACCESS  read-only
      STATUS      current
      DESCRIPTION "The disk write policy that determines how the file store writes data to disk.  This policy also affects the JMS file store's performance, scalability, and reliability. Oracle recommends Direct-Write-With-Cache which tends to have the highest performance. The default value is Direct-Write. The valid policy options are:   Direct-Write Direct I/O is supported on all platforms. When available, file stores in direct I/O mode automatically load the native I/O wlfileio driver. This option tends to out-perform Cache-Flush and tend to be slower than Direct-Write-With-Cache. This mode does not require a native store wlfileio driver, but performs faster when they are available.  Direct-Write-With-Cache Store records are written synchronously to primary files in the directory specified by the Directory attribute and asynchronously to a corresponding cache file in the Cache Directory. The Cache Directory provides information about disk space, locking, security, and performance implications. This mode requires a native store wlfileiocode driver. If the native driver cannot be loaded, then the write mode automatically switches to Direct-Write. See Cache Directory.  Cache-Flush Transactions cannot complete until all of their writes have been flushed down to disk. This policy is reliable and scales well as the number of simultaneous users increases.Transactionally safe but tends to be a lower performer than direct-write policies.  Disabled Transactions are complete as soon as their writes are cached in memory, instead of waiting for the writes to successfully reach the disk. This is the fastest policy because write requests do not block waiting to be synchronized to disk, but, unlike other policies, is not transactionally safe in the event of operating system or hardware failures. Such failures can lead to duplicate or lost data/messages. This option does not require native store wlfileio drivers, but may run faster when they are available. Some non-WebLogic JMS vendors default to a policy that is equivalent to Disabled.   Notes:  When available, file stores load WebLogic wlfileio native drivers, which can improve performance. These drivers are included with Windows, Solaris, Linux, and AIX WebLogic installations.  Certain older versions of Microsoft Windows may incorrectly report storage device synchronous write completion if the Windows default Write Cache Enabled setting is used. This violates the transactional semantics of transactional products (not specific to Oracle), including file stores configured with a Direct-Write (default) or Direct-Write-With-Cache policy, as a system crash or power failure can lead to a loss or a duplication of records/messages. One of the visible symptoms is that this problem may manifest itself in high persistent message/transaction throughput exceeding the physical capabilities of your storage device. You can address the problem by applying a Microsoft supplied patch, disabling the Windows Write Cache Enabled setting, or by using a power-protected storage device. See http://support.microsoft.com/kb/281672 and http://support.microsoft.com/kb/332023.  NFS storage note:  On some operating systems, native driver memory-mapping is incompatible with NFS when files are locked. Stores with synchronous write policies Direct-Write-With-Cache or Disabled, and WebLogic JMS paging stores enhance performance by using the native wlfileio driver to perform memory-map operating system calls. When a store detects an incompatibility between NFS, file locking, and memory mapping, it automatically downgrades to conventional read/write system calls instead of memory mapping. For best performance, Oracle recommends investigating alternative NFS client drivers, configuring a non-NFS storage location, or in controlled environments and at your own risk, disabling the file locks (See Enable File Locking). For more information, see 'Tuning the WebLogic Persistent Store' in Tuning Performance of Oracle WebLogic Server.  "
      ::= { defaultFileStoreEntry 11  }
   
   
   defaultFileStoreDirectory OBJECT-TYPE
      SYNTAX      OCTET STRING
      MAX-ACCESS  read-only
      STATUS      current
      DESCRIPTION "The path name to the file system directory where the file store maintains its data files.  When targeting a file store to a migratable target, the store directory must be accessible from all candidate server members in the migratable target. For highest availability, use either a SAN (Storage Area Network) or other reliable shared storage. Use of NFS mounts is discouraged, but supported. Most NFS mounts are not transactionally safe by default, and, to ensure transactional correctness, need to be configured using your NFS vendor documentation in order to honor synchronous write requests. For SynchronousWritePolicy of Direct-Write-With-Cache, see Cache Directory.  Additional O/S tuning may be required if the directory is hosted by Microsoft Windows, see Synchronous Write Policy for details. "
      ::= { defaultFileStoreEntry 12  }
   
   
   defaultFileStoreFileLockingEnabled OBJECT-TYPE
      SYNTAX      OCTET STRING
      MAX-ACCESS  read-only
      STATUS      current
      DESCRIPTION "Determines whether OS file locking is used.  When file locking protection is enabled, a store boot fails if another store instance already has opened the store files. Do not disable this setting unless you have procedures in place to prevent multiple store instances from opening the same file. File locking is not required but helps prevent corruption in the event that two same-named file store instances attempt to operate in the same directories. This setting applies to both primary and cache files. "
      ::= { defaultFileStoreEntry 13  }
   
   
   defaultFileStoreCacheDirectory OBJECT-TYPE
      SYNTAX      OCTET STRING
      MAX-ACCESS  read-only
      STATUS      current
      DESCRIPTION "The location of the cache directory for Direct-Write-With-Cache, ignored for other policies.  When Direct-Write-With-Cache is specified as the SynchronousWritePolicy, cache files are created in addition to primary files (see Directory for the location of primary files). If a cache directory location is specified, the cache file path is CacheDirectory/WLStoreCache/StoreNameFileNum.DAT.cache. When specified, Oracle recommends using absolute paths, but if the directory location is a relative path, then CacheDirectory is created relative to the WebLogic Server instance's home directory. If '' or Null is specified, the Cache Directory is located in the current operating system temp directory as determined by the java.io.tmpdir Java System property (JDK's default: /tmp on UNIX, %TEMP%  on Windows) and is  TempDirectory/WLStoreCache/DomainName/unique-id/StoreNameFileNum.DAT.cache. The value of java.io.tmpdir varies between operating systems and configurations, and can be overridden by passing -Djava.io.tmpdir=My_path on the JVM command line.   Considerations:  Security: Some users may want to set specific directory permissions to limit access to the cache directory, especially if there are custom configured user access limitations on the primary directory. For a complete guide to WebLogic security, see 'Securing a Production Environment for Oracle WebLogic Server.'   Additional Disk Space Usage: Cache files consume the same amount of disk space as the primary store files that they mirror. See Directory for the location of primary store files.  Performance: For the best performance, a cache directory should be located in local storage instead of NAS/SAN (remote) storage, preferably in the operating system's temp directory. Relative paths should be avoided, as relative paths are located based on the domain installation, which is typically on remote storage. It is safe to delete a cache directory while the store is not running, but this may slow down the next store boot.  Preventing Corruption and File Locking: Two same named stores must not be configured to share the same primary or cache directory. There are store file locking checks that are designed to detect such conflicts and prevent corruption by failing the store boot, but it is not recommended to depend on the file locking feature for correctness. See Enable File Locking.   Boot Recovery: Cache files are reused to speed up the File Store boot and recovery process, but only if the store's host WebLogic Server instance has been shut down cleanly prior to the current boot. For example, cache files are not re-used and are instead fully recreated: after a kill -9, after an OS or JVM crash, or after an off-line change to the primary files, such as a store admin compaction. When cache files are recreated, a Warning log message 280102 is generated.  Fail-Over/Migration Recovery: A file store safely recovers its data without its cache directory. Therefore, a cache directory does not need to be copied or otherwise made accessible after a fail-over or migration, and similarly does not need to be placed in NAS/SAN storage. A Warning log message 280102, which is generated to indicate the need to recreate the cache on the new host system, can be ignored.   Cache File Cleanup: To prevent unused cache files from consuming disk space, test and developer environments should periodically delete cache files.  "
      ::= { defaultFileStoreEntry 14  }
   
   
   defaultFileStoreTags OBJECT-TYPE
      SYNTAX      OCTET STRING
      MAX-ACCESS  read-only
      STATUS      current
      DESCRIPTION "Return all tags on this Configuration MBean "
      ::= { defaultFileStoreEntry 15  }
   
   
   deploymentConfigurationTable OBJECT-TYPE
      SYNTAX      SEQUENCE OF DeploymentConfigurationEntry
      MAX-ACCESS  not-accessible
      STATUS      current
      DESCRIPTION "Specifies the domain-level deployment configuration attributes. "
      ::= { wls 895  }
      
   
   deploymentConfigurationEntry OBJECT-TYPE
      SYNTAX      DeploymentConfigurationEntry
      MAX-ACCESS  not-accessible
      STATUS      current
      DESCRIPTION "Generated SNMP Table Entry."
      INDEX { deploymentConfigurationIndex}
      ::= { deploymentConfigurationTable 1 }
      
   DeploymentConfigurationEntry ::=
      SEQUENCE
      {
         deploymentConfigurationIndex OCTET STRING,
         deploymentConfigurationObjectName OCTET STRING,
         deploymentConfigurationType OCTET STRING,
         deploymentConfigurationName OCTET STRING,
         deploymentConfigurationRestageOnlyOnRedeploy OCTET STRING,
         deploymentConfigurationMaxRetiredTasks INTEGER,
         deploymentConfigurationTags OCTET STRING,
         deploymentConfigurationLongRunningRetireThreadDumpCount INTEGER,
         deploymentConfigurationLongRunningRetireThreadDumpInterval Counter64,
         deploymentConfigurationDeploymentServiceMessageRetryCount INTEGER,
         deploymentConfigurationLongRunningRetireThreadDumpStartTime Counter64,
         deploymentConfigurationDeploymentServiceMessageRetryInterval INTEGER,
         deploymentConfigurationDefaultMultiVersionAppRetireTimeout INTEGER
      }
      
   
   deploymentConfigurationIndex OBJECT-TYPE
      SYNTAX      OCTET STRING
      MAX-ACCESS  not-accessible
      STATUS      current
      DESCRIPTION "Index column"
      ::= { deploymentConfigurationEntry 1  }
   
   
   deploymentConfigurationObjectName OBJECT-TYPE
      SYNTAX      OCTET STRING
      MAX-ACCESS  read-only
      STATUS      current
      DESCRIPTION "ObjectName column"
      ::= { deploymentConfigurationEntry 2  }
   
   
   deploymentConfigurationType OBJECT-TYPE
      SYNTAX      OCTET STRING
      MAX-ACCESS  read-only
      STATUS      current
      DESCRIPTION "Returns the type of the MBean. "
      ::= { deploymentConfigurationEntry 3  }
   
   
   deploymentConfigurationName OBJECT-TYPE
      SYNTAX      OCTET STRING
      MAX-ACCESS  read-only
      STATUS      current
      DESCRIPTION "The user-specified name of this MBean instance.  This name is included as one of the key properties in the MBean's javax.management.ObjectName:  Name=user-specified-name "
      ::= { deploymentConfigurationEntry 5  }
   
   
   deploymentConfigurationRestageOnlyOnRedeploy OBJECT-TYPE
      SYNTAX      OCTET STRING
      MAX-ACCESS  read-only
      STATUS      current
      DESCRIPTION "Specifies whether applications with staging mode of STAGE are restaged only during redeploy operation. If set to true, then applications will never restage during server startup and will only be restaged on an explicit redeploy operation. "
      ::= { deploymentConfigurationEntry 6  }
   
   
   deploymentConfigurationMaxRetiredTasks OBJECT-TYPE
      SYNTAX      INTEGER
      MAX-ACCESS  read-only
      STATUS      current
      DESCRIPTION "Gets the value of the maximum number of retired tasks to save information for. "
      ::= { deploymentConfigurationEntry 7  }
   
   
   deploymentConfigurationTags OBJECT-TYPE
      SYNTAX      OCTET STRING
      MAX-ACCESS  read-only
      STATUS      current
      DESCRIPTION "Return all tags on this Configuration MBean "
      ::= { deploymentConfigurationEntry 8  }
   
   
   deploymentConfigurationLongRunningRetireThreadDumpCount OBJECT-TYPE
      SYNTAX      INTEGER
      MAX-ACCESS  read-only
      STATUS      current
      DESCRIPTION "The maximum number of times the thread dump generation will be retried on a long running Retire operation "
      ::= { deploymentConfigurationEntry 9  }
   
   
   deploymentConfigurationLongRunningRetireThreadDumpInterval OBJECT-TYPE
      SYNTAX      Counter64
      MAX-ACCESS  read-only
      STATUS      current
      DESCRIPTION "The number of milliseconds between thread dump retry on a long running Retire operation. "
      ::= { deploymentConfigurationEntry 10  }
   
   
   deploymentConfigurationDeploymentServiceMessageRetryCount OBJECT-TYPE
      SYNTAX      INTEGER
      MAX-ACCESS  read-only
      STATUS      current
      DESCRIPTION "The maximum number of times the Deployment Service will retry sending a message if a connection exception occurs during the during a deployment or activate changes operation. "
      ::= { deploymentConfigurationEntry 11  }
   
   
   deploymentConfigurationLongRunningRetireThreadDumpStartTime OBJECT-TYPE
      SYNTAX      Counter64
      MAX-ACCESS  read-only
      STATUS      current
      DESCRIPTION "The number of milliseconds a thread dump generation will start for a long running Retire operation. "
      ::= { deploymentConfigurationEntry 12  }
   
   
   deploymentConfigurationDeploymentServiceMessageRetryInterval OBJECT-TYPE
      SYNTAX      INTEGER
      MAX-ACCESS  read-only
      STATUS      current
      DESCRIPTION "The number of milliseconds between retry attempts if a connection exception occurs during the during the deployment or activate changes operation. "
      ::= { deploymentConfigurationEntry 13  }
   
   
   deploymentConfigurationDefaultMultiVersionAppRetireTimeout OBJECT-TYPE
      SYNTAX      INTEGER
      MAX-ACCESS  read-only
      STATUS      current
      DESCRIPTION "Specifies the default retire timeout to be used for multi version apps. The value is in seconds "
      ::= { deploymentConfigurationEntry 14  }
   
   
   domainLibraryTable OBJECT-TYPE
      SYNTAX      SEQUENCE OF DomainLibraryEntry
      MAX-ACCESS  not-accessible
      STATUS      current
      DESCRIPTION "Configuration bean for Libraries.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 900  }
      
   
   domainLibraryEntry OBJECT-TYPE
      SYNTAX      DomainLibraryEntry
      MAX-ACCESS  not-accessible
      STATUS      current
      DESCRIPTION "Generated SNMP Table Entry."
      INDEX { domainLibraryIndex}
      ::= { domainLibraryTable 1 }
      
   DomainLibraryEntry ::=
      SEQUENCE
      {
         domainLibraryIndex   OCTET STRING,
         domainLibraryObjectName OCTET STRING,
         domainLibraryType    OCTET STRING,
         domainLibraryCompatibilityName OCTET STRING,
         domainLibraryApplicationName OCTET STRING,
         domainLibraryAbsolutePlanDir OCTET STRING,
         domainLibraryAbsolutePlanPath OCTET STRING,
         domainLibraryStagingMode OCTET STRING,
         domainLibraryInstallDir OCTET STRING,
         domainLibraryValidateDDSecurityData OCTET STRING,
         domainLibraryName    OCTET STRING,
         domainLibraryAbsoluteSourcePath OCTET STRING,
         domainLibrarySourcePath OCTET STRING,
         domainLibraryAbsoluteInstallDir OCTET STRING,
         domainLibraryDeploymentOrder Integer32,
         domainLibrarySecurityDDModel OCTET STRING,
         domainLibraryApplicationIdentifier OCTET STRING,
         domainLibraryDeploymentPrincipalName OCTET STRING,
         domainLibraryPlanDir OCTET STRING,
         domainLibraryPlanPath OCTET STRING,
         domainLibraryVersionIdentifier OCTET STRING,
         domainLibraryModuleType OCTET STRING
      }
      
   
   domainLibraryIndex OBJECT-TYPE
      SYNTAX      OCTET STRING
      MAX-ACCESS  not-accessible
      STATUS      current
      DESCRIPTION "Index column"
      ::= { domainLibraryEntry 1  }
   
   
   domainLibraryObjectName OBJECT-TYPE
      SYNTAX      OCTET STRING
      MAX-ACCESS  read-only
      STATUS      current
      DESCRIPTION "ObjectName column"
      ::= { domainLibraryEntry 2  }
   
   
   domainLibraryType OBJECT-TYPE
      SYNTAX      OCTET STRING
      MAX-ACCESS  read-only
      STATUS      current
      DESCRIPTION "Returns the type of the MBean."
      ::= { domainLibraryEntry 3  }
   
   
   domainLibraryCompatibilityName OBJECT-TYPE
      SYNTAX      OCTET STRING
      MAX-ACCESS  read-only
      STATUS      current
      DESCRIPTION "This is only set for beans created as a result of conversion from an 8.1 application configured using ApplicationMBean and ComponentMBean.  Standalone modules in 8.1 have both an ApplicationMBean name and ComponentMBean name. This attribute stores the name of the latter, to be used when the server creates the transient ComponentMBean for backward compatibility."
      ::= { domainLibraryEntry 4  }
   
   
   domainLibraryApplicationName OBJECT-TYPE
      SYNTAX      OCTET STRING
      MAX-ACCESS  read-only
      STATUS      current
      DESCRIPTION "The name of the application. Note that the name of the current MBean is not the name of the application."
      ::= { domainLibraryEntry 5  }
   
   
   domainLibraryAbsolutePlanDir OBJECT-TYPE
      SYNTAX      OCTET STRING
      MAX-ACCESS  read-only
      STATUS      current
      DESCRIPTION "The fully resolved location of this application's deployment plan directory on the admin server."
      ::= { domainLibraryEntry 6  }
   
   
   domainLibraryAbsolutePlanPath OBJECT-TYPE
      SYNTAX      OCTET STRING
      MAX-ACCESS  read-only
      STATUS      current
      DESCRIPTION "The fully resolved location of this application's deployment plan on the admin server."
      ::= { domainLibraryEntry 7  }
   
   
   domainLibraryStagingMode OBJECT-TYPE
      SYNTAX      OCTET STRING
      MAX-ACCESS  read-only
      STATUS      current
      DESCRIPTION "The mode that specifies whether a deployment's files are copied from a source on the Administration Server to the Managed Server's staging area during application preparation.  Staging mode for an application can only be set the first time the application is deployed. Once staging mode for an application is set, it cannot be changed while the application is configured in the domain. The only way to change staging mode is to undeploy then redeploy the application. This attribute overrides the server's staging mode."
      ::= { domainLibraryEntry 8  }
   
   
   domainLibraryInstallDir OBJECT-TYPE
      SYNTAX      OCTET STRING
      MAX-ACCESS  read-only
      STATUS      current
      DESCRIPTION "The path to application's install-root directory, relative to the domain/config/deployments directory. When the Install Directory is specified, SourcePath, PlanDir, and PlanPath are derived from this path, and need not be specified. Default value for this is the name of the deployment."
      ::= { domainLibraryEntry 9  }
   
   
   domainLibraryValidateDDSecurityData OBJECT-TYPE
      SYNTAX      OCTET STRING
      MAX-ACCESS  read-only
      STATUS      current
      DESCRIPTION "This attribute is not used in the current BEA release."
      ::= { domainLibraryEntry 10  }
   
   
   domainLibraryName OBJECT-TYPE
      SYNTAX      OCTET STRING
      MAX-ACCESS  read-only
      STATUS      current
      DESCRIPTION "Unique identifier for this bean instance."
      ::= { domainLibraryEntry 11  }
   
   
   domainLibraryAbsoluteSourcePath OBJECT-TYPE
      SYNTAX      OCTET STRING
      MAX-ACCESS  read-only
      STATUS      current
      DESCRIPTION "The fully resolved location of this application's source files on the admin server."
      ::= { domainLibraryEntry 12  }
   
   
   domainLibrarySourcePath OBJECT-TYPE
      SYNTAX      OCTET STRING
      MAX-ACCESS  read-only
      STATUS      current
      DESCRIPTION "The path to the source of the deployable unit on the Administration Server. Rules:  If InstallDir is null, the source path must be an absolute path. If the source path is relative, it is resolved relative to InstallDir/app.  Use AbsoluteSourcePath to get a fully resolved value."
      ::= { domainLibraryEntry 13  }
   
   
   domainLibraryAbsoluteInstallDir OBJECT-TYPE
      SYNTAX      OCTET STRING
      MAX-ACCESS  read-only
      STATUS      current
      DESCRIPTION "The fully resolved location of this application's installation root directory on the admin server."
      ::= { domainLibraryEntry 14  }
   
   
   domainLibraryDeploymentOrder OBJECT-TYPE
      SYNTAX      Integer32
      MAX-ACCESS  read-only
      STATUS      current
      DESCRIPTION "A numerical value that indicates when this unit is deployed, relative to other DeployableUnits on a server, during startup.  Units with lower Load Order values are deployed before those with higher values."
      ::= { domainLibraryEntry 15  }
   
   
   domainLibrarySecurityDDModel OBJECT-TYPE
      SYNTAX      OCTET STRING
      MAX-ACCESS  read-only
      STATUS      current
      DESCRIPTION "The security model that is used to secure a deployed module.  To set this value, you can use the weblogic.Deployer command-line tool, the Deployment Assistant in the Administration Console, the WebLogic Scripting Tool (WLST), or some other JMX client.  If you deploy a module using one of the previously mentioned tools and you do not specify a security model value, the module is secured with the security realm's default model ( see {@link weblogic.security.RealmMBean#getSecurityDDModel RealmMBean SecurityDDModel}).  If you deploy a module by modifying the domain's config.xml file and restarting the server, and if you do not specify a security model value for the module in config.xml, the module is secured with the DDOnly model, which is the default value of this AppDeploymentMBean attribute.  In summary, the order of precedence for the value of this attribute is as follows:   If you deploy a module using a runtime deployment utility, the order of precedence is: The value set by the deployment utility. The value set as the security realm's default security model.  If you deploy a module by modifying config.xml and restarting the server, the order of precedence is: The value that you specify for the module in config.xml. The default value of this AppDeploymentMBean SecurityDDModel attribute."
      ::= { domainLibraryEntry 16  }
   
   
   domainLibraryApplicationIdentifier OBJECT-TYPE
      SYNTAX      OCTET STRING
      MAX-ACCESS  read-only
      STATUS      current
      DESCRIPTION "The Application Identifier of the application version uniquely identifies the application version across all versions of all applications. If the application is not versioned, the Application Identifier is the same as the application name."
      ::= { domainLibraryEntry 17  }
   
   
   domainLibraryDeploymentPrincipalName OBJECT-TYPE
      SYNTAX      OCTET STRING
      MAX-ACCESS  read-only
      STATUS      current
      DESCRIPTION "A string value that indicates what principal should be used when deploying the file or archive during startup and shutdown. This principal will be used to set the current subject when calling out into application code for interfaces such as ApplicationLifecycleListener, If no principal name is specifed, then the anonymous principal will be used."
      ::= { domainLibraryEntry 18  }
   
   
   domainLibraryPlanDir OBJECT-TYPE
      SYNTAX      OCTET STRING
      MAX-ACCESS  read-only
      STATUS      current
      DESCRIPTION "The location of this application's configuration area. This directory can contain external descriptor files as specified within the deployment plan document.  Rules:  If InstallDir is null, plan directory should be an absolute path. If the plan directory is a relative path, it is resolved relative to InstallDir.   Use AbsolutePlanDir to get a fully resolved value."
      ::= { domainLibraryEntry 19  }
   
   
   domainLibraryPlanPath OBJECT-TYPE
      SYNTAX      OCTET STRING
      MAX-ACCESS  read-only
      STATUS      current
      DESCRIPTION "The path to the deployment plan document on Administration Server. Rules:  If PlanDir is null, the plan path must be an absolute path. If the plan path is a relative path, it is resolved relative to PlanDir.  Use AbsolutePlanPath to get a fully resolved value. If there is no plan, this returns no plan specified."
      ::= { domainLibraryEntry 20  }
   
   
   domainLibraryVersionIdentifier OBJECT-TYPE
      SYNTAX      OCTET STRING
      MAX-ACCESS  read-only
      STATUS      current
      DESCRIPTION "Uniquely identifies the application version across all versions of the same application. If the application is not versioned, this returns null."
      ::= { domainLibraryEntry 21  }
   
   
   domainLibraryModuleType OBJECT-TYPE
      SYNTAX      OCTET STRING
      MAX-ACCESS  read-only
      STATUS      current
      DESCRIPTION "The values match those defined by jsr88. This attribute may move to another MBean."
      ::= { domainLibraryEntry 22  }
   
   
   embeddedLDAPTable OBJECT-TYPE
      SYNTAX      SEQUENCE OF EmbeddedLDAPEntry
      MAX-ACCESS  not-accessible
      STATUS      current
      DESCRIPTION "The MBean that defines the configuration properties for the embedded LDAP server for the WebLogic domain. "
      ::= { wls 905  }
      
   
   embeddedLDAPEntry OBJECT-TYPE
      SYNTAX      EmbeddedLDAPEntry
      MAX-ACCESS  not-accessible
      STATUS      current
      DESCRIPTION "Generated SNMP Table Entry."
      INDEX { embeddedLDAPIndex}
      ::= { embeddedLDAPTable 1 }
      
   EmbeddedLDAPEntry ::=
      SEQUENCE
      {
         embeddedLDAPIndex    OCTET STRING,
         embeddedLDAPObjectName OCTET STRING,
         embeddedLDAPType     OCTET STRING,
         embeddedLDAPTimeout  Integer32,
         embeddedLDAPAnonymousBindAllowed OCTET STRING,
         embeddedLDAPMasterFirst OCTET STRING,
         embeddedLDAPCacheTTL Integer32,
         embeddedLDAPBackupCopies Integer32,
         embeddedLDAPRefreshReplicaAtStartup OCTET STRING,
         embeddedLDAPBackupMinute Integer32,
         embeddedLDAPCacheSize Integer32,
         embeddedLDAPBackupHour Integer32,
         embeddedLDAPName     OCTET STRING,
         embeddedLDAPCacheEnabled OCTET STRING,
         embeddedLDAPKeepAliveEnabled OCTET STRING,
         embeddedLDAPTags     OCTET STRING
      }
      
   
   embeddedLDAPIndex OBJECT-TYPE
      SYNTAX      OCTET STRING
      MAX-ACCESS  not-accessible
      STATUS      current
      DESCRIPTION "Index column"
      ::= { embeddedLDAPEntry 1  }
   
   
   embeddedLDAPObjectName OBJECT-TYPE
      SYNTAX      OCTET STRING
      MAX-ACCESS  read-only
      STATUS      current
      DESCRIPTION "ObjectName column"
      ::= { embeddedLDAPEntry 2  }
   
   
   embeddedLDAPType OBJECT-TYPE
      SYNTAX      OCTET STRING
      MAX-ACCESS  read-only
      STATUS      current
      DESCRIPTION "Returns the type of the MBean. "
      ::= { embeddedLDAPEntry 3  }
   
   
   embeddedLDAPTimeout OBJECT-TYPE
      SYNTAX      Integer32
      MAX-ACCESS  read-only
      STATUS      current
      DESCRIPTION "Specifies the maximum number of seconds to wait for results from the embedded LDAP server before timing out. If this option is set to 0, there is no maximum time limit. "
      ::= { embeddedLDAPEntry 4  }
   
   
   embeddedLDAPAnonymousBindAllowed OBJECT-TYPE
      SYNTAX      OCTET STRING
      MAX-ACCESS  read-only
      STATUS      current
      DESCRIPTION "Specifies whether the embedded LDAP server should allow anonymous connections. "
      ::= { embeddedLDAPEntry 5  }
   
   
   embeddedLDAPMasterFirst OBJECT-TYPE
      SYNTAX      OCTET STRING
      MAX-ACCESS  read-only
      STATUS      current
      DESCRIPTION "Specifies whether a Managed Server should always connect to the master LDAP server (contained in the Administration Server), instead of connecting to the local replicated LDAP server (contained in the Managed Server). "
      ::= { embeddedLDAPEntry 6  }
   
   
   embeddedLDAPCacheTTL OBJECT-TYPE
      SYNTAX      Integer32
      MAX-ACCESS  read-only
      STATUS      current
      DESCRIPTION "The time-to-live of the cache (in seconds) that is used with the embedded LDAP server. "
      ::= { embeddedLDAPEntry 7  }
   
   
   embeddedLDAPBackupCopies OBJECT-TYPE
      SYNTAX      Integer32
      MAX-ACCESS  read-only
      STATUS      current
      DESCRIPTION "The maximum number of backup copies that should be made for the embedded LDAP server.  This value limits the number of zip files in the ldap/backup directory. "
      ::= { embeddedLDAPEntry 8  }
   
   
   embeddedLDAPRefreshReplicaAtStartup OBJECT-TYPE
      SYNTAX      OCTET STRING
      MAX-ACCESS  read-only
      STATUS      current
      DESCRIPTION "Specifies whether a Managed Server should refresh all replicated data at boot time. (This is useful if you have made a large amount of changes when the Managed Server was not active, and you want to download the entire replica instead of having the Administration Server push each change to the Managed Server.) "
      ::= { embeddedLDAPEntry 9  }
   
   
   embeddedLDAPBackupMinute OBJECT-TYPE
      SYNTAX      Integer32
      MAX-ACCESS  read-only
      STATUS      current
      DESCRIPTION "The minute at which the embedded LDAP server should be backed up.  The Backup Minute value is used in conjunction with the Back Up Hour value to determine the time at which the embedded LDAP server data files are backed up "
      ::= { embeddedLDAPEntry 10  }
   
   
   embeddedLDAPCacheSize OBJECT-TYPE
      SYNTAX      Integer32
      MAX-ACCESS  read-only
      STATUS      current
      DESCRIPTION "The size of the cache (in kilobytes) that is used with the embedded LDAP server. "
      ::= { embeddedLDAPEntry 11  }
   
   
   embeddedLDAPBackupHour OBJECT-TYPE
      SYNTAX      Integer32
      MAX-ACCESS  read-only
      STATUS      current
      DESCRIPTION "The hour at which the embedded LDAP server should be backed up.  The Backup Hour value is used in conjunction with the Backup Minute value to determine the time at which the embedded LDAP server data files are backed up. At the specified time, WebLogic Server suspends writes to the embedded LDAP server, backs up the data files into a zip files in the ldap/backup directory, and then resumes writes. "
      ::= { embeddedLDAPEntry 12  }
   
   
   embeddedLDAPName OBJECT-TYPE
      SYNTAX      OCTET STRING
      MAX-ACCESS  read-only
      STATUS      current
      DESCRIPTION "The user-specified name of this MBean instance.  This name is included as one of the key properties in the MBean's javax.management.ObjectName:  Name=user-specified-name "
      ::= { embeddedLDAPEntry 13  }
   
   
   embeddedLDAPCacheEnabled OBJECT-TYPE
      SYNTAX      OCTET STRING
      MAX-ACCESS  read-only
      STATUS      current
      DESCRIPTION "Specifies whether a cache is used with the embedded LDAP server.  This cache is used when a managed server is reading or writing to the master embedded LDAP server that is running on the Administration server. "
      ::= { embeddedLDAPEntry 14  }
   
   
   embeddedLDAPKeepAliveEnabled OBJECT-TYPE
      SYNTAX      OCTET STRING
      MAX-ACCESS  read-only
      STATUS      current
      DESCRIPTION "Whether keep alive is enabled in the socket connection "
      ::= { embeddedLDAPEntry 15  }
   
   
   embeddedLDAPTags OBJECT-TYPE
      SYNTAX      OCTET STRING
      MAX-ACCESS  read-only
      STATUS      current
      DESCRIPTION "Return all tags on this Configuration MBean "
      ::= { embeddedLDAPEntry 16  }
   
   
   errorHandlingTable OBJECT-TYPE
      SYNTAX      SEQUENCE OF ErrorHandlingEntry
      MAX-ACCESS  not-accessible
      STATUS      current
      DESCRIPTION "Fake ErrorHandlingMBean"
      ::= { wls 910  }
      
   
   errorHandlingEntry OBJECT-TYPE
      SYNTAX      ErrorHandlingEntry
      MAX-ACCESS  not-accessible
      STATUS      current
      DESCRIPTION "Generated SNMP Table Entry."
      INDEX { errorHandlingIndex}
      ::= { errorHandlingTable 1 }
      
   ErrorHandlingEntry ::=
      SEQUENCE
      {
         errorHandlingIndex   OCTET STRING,
         errorHandlingObjectName OCTET STRING,
         errorHandlingType    OCTET STRING,
         errorHandlingLogPolicy OCTET STRING,
         errorHandlingPolicy  OCTET STRING,
         errorHandlingName    OCTET STRING,
         errorHandlingTags    OCTET STRING
      }
      
   
   errorHandlingIndex OBJECT-TYPE
      SYNTAX      OCTET STRING
      MAX-ACCESS  not-accessible
      STATUS      current
      DESCRIPTION "Index column"
      ::= { errorHandlingEntry 1  }
   
   
   errorHandlingObjectName OBJECT-TYPE
      SYNTAX      OCTET STRING
      MAX-ACCESS  read-only
      STATUS      current
      DESCRIPTION "ObjectName column"
      ::= { errorHandlingEntry 2  }
   
   
   errorHandlingType OBJECT-TYPE
      SYNTAX      OCTET STRING
      MAX-ACCESS  read-only
      STATUS      current
      DESCRIPTION "Returns the type of the MBean."
      ::= { errorHandlingEntry 3  }
   
   
   errorHandlingLogPolicy OBJECT-TYPE
      SYNTAX      OCTET STRING
      MAX-ACCESS  read-only
      STATUS      current
      DESCRIPTION "Policy"
      ::= { errorHandlingEntry 4  }
   
   
   errorHandlingPolicy OBJECT-TYPE
      SYNTAX      OCTET STRING
      MAX-ACCESS  read-only
      STATUS      current
      DESCRIPTION "Policy"
      ::= { errorHandlingEntry 5  }
   
   
   errorHandlingName OBJECT-TYPE
      SYNTAX      OCTET STRING
      MAX-ACCESS  read-only
      STATUS      current
      DESCRIPTION "The user-specified name of this MBean instance.  This name is included as one of the key properties in the MBean's javax.management.ObjectName:  Name=user-specified-name"
      ::= { errorHandlingEntry 6  }
   
   
   errorHandlingTags OBJECT-TYPE
      SYNTAX      OCTET STRING
      MAX-ACCESS  read-only
      STATUS      current
      DESCRIPTION "Return all tags on this Configuration MBean"
      ::= { errorHandlingEntry 7  }
   
   
   fairShareRequestClassTable OBJECT-TYPE
      SYNTAX      SEQUENCE OF FairShareRequestClassEntry
      MAX-ACCESS  not-accessible
      STATUS      current
      DESCRIPTION "This mbean defines the fair share value to use for this request class. One of the components of work managers is a request class that indicates the proportional of the total server thread use time this request class gets. The default fair share value is 50.  Fair shares are reflected in scheduling logic such that as long as multiple fair shares compete, the average number of threads used by each is in proportion to their fair share. For example, consider we only have two fair shares, A and B, having a fair share of 80 and 20, respectively. During a period in which both fair shares are sufficiently requested, say, zero think time and more clients than threads, the probability that a thread will work on behalf of A or B will tend toward 80% or 20%, respectively. The scheduling logic ensures this even when A tends to use a thread for much longer than B.   Fair share values can range from 1 to 1000. The default fair share value is 50.  "
      ::= { wls 915  }
      
   
   fairShareRequestClassEntry OBJECT-TYPE
      SYNTAX      FairShareRequestClassEntry
      MAX-ACCESS  not-accessible
      STATUS      current
      DESCRIPTION "Generated SNMP Table Entry."
      INDEX { fairShareRequestClassIndex}
      ::= { fairShareRequestClassTable 1 }
      
   FairShareRequestClassEntry ::=
      SEQUENCE
      {
         fairShareRequestClassIndex OCTET STRING,
         fairShareRequestClassObjectName OCTET STRING,
         fairShareRequestClassType OCTET STRING,
         fairShareRequestClassDeploymentOrder Integer32,
         fairShareRequestClassFairShare Integer32,
         fairShareRequestClassName OCTET STRING,
         fairShareRequestClassTags OCTET STRING
      }
      
   
   fairShareRequestClassIndex OBJECT-TYPE
      SYNTAX      OCTET STRING
      MAX-ACCESS  not-accessible
      STATUS      current
      DESCRIPTION "Index column"
      ::= { fairShareRequestClassEntry 1  }
   
   
   fairShareRequestClassObjectName OBJECT-TYPE
      SYNTAX      OCTET STRING
      MAX-ACCESS  read-only
      STATUS      current
      DESCRIPTION "ObjectName column"
      ::= { fairShareRequestClassEntry 2  }
   
   
   fairShareRequestClassType OBJECT-TYPE
      SYNTAX      OCTET STRING
      MAX-ACCESS  read-only
      STATUS      current
      DESCRIPTION "Returns the type of the MBean. "
      ::= { fairShareRequestClassEntry 3  }
   
   
   fairShareRequestClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { fairShareRequestClassEntry 4  }
   
   
   fairShareRequestClassFairShare OBJECT-TYPE
      SYNTAX      Integer32
      MAX-ACCESS  read-only
      STATUS      current
      DESCRIPTION "Fair share value "
      ::= { fairShareRequestClassEntry 5  }
   
   
   fairShareRequestClassName OBJECT-TYPE
      SYNTAX      OCTET STRING
      MAX-ACCESS  read-only
      STATUS      current
      DESCRIPTION "The user-specified name of this MBean instance.  This name is included as one of the key properties in the MBean's javax.management.ObjectName:  Name=user-specified-name "
      ::= { fairShareRequestClassEntry 6  }
   
   
   fairShareRequestClassTags OBJECT-TYPE
      SYNTAX      OCTET STRING
      MAX-ACCESS  read-only
      STATUS      current
      DESCRIPTION "Return all tags on this Configuration MBean "
      ::= { fairShareRequestClassEntry 7  }
   
   
   federationServicesTable OBJECT-TYPE
      SYNTAX      SEQUENCE OF FederationServicesEntry
      MAX-ACCESS  not-accessible
      STATUS      current
      DESCRIPTION "This MBean represents configuration for SAML 1.1-based Federation Services, including the intersite transfer service, assertion consumer service, and assertion retrieval service. "
      ::= { wls 920  }
      
   
   federationServicesEntry OBJECT-TYPE
      SYNTAX      FederationServicesEntry
      MAX-ACCESS  not-accessible
      STATUS      current
      DESCRIPTION "Generated SNMP Table Entry."
      INDEX { federationServicesIndex}
      ::= { federationServicesTable 1 }
      
   FederationServicesEntry ::=
      SEQUENCE
      {
         federationServicesIndex OCTET STRING,
         federationServicesObjectName OCTET STRING,
         federationServicesType OCTET STRING,
         federationServicesSourceIdHex OCTET STRING,
         federationServicesAssertionStoreClassName OCTET STRING,
         federationServicesITSRequiresSSL OCTET STRING,
         federationServicesARSRequiresTwoWaySSL OCTET STRING,
         federationServicesPOSTRecipientCheckEnabled OCTET STRING,
         federationServicesACSRequiresSSL OCTET STRING,
         federationServicesSourceSiteURL OCTET STRING,
         federationServicesSigningKeyAlias OCTET STRING,
         federationServicesName OCTET STRING,
         federationServicesSSLClientIdentityAlias OCTET STRING,
         federationServicesSourceIdBase64 OCTET STRING,
         federationServicesDestinationSiteEnabled OCTET STRING,
         federationServicesPOSTOneUseCheckEnabled OCTET STRING,
         federationServicesUsedAssertionCacheClassName OCTET STRING,
         federationServicesARSRequiresSSL OCTET STRING,
         federationServicesSourceSiteEnabled OCTET STRING,
         federationServicesAssertionConsumerURIs OCTET STRING,
         federationServicesAssertionRetrievalURIs OCTET STRING,
         federationServicesIntersiteTransferURIs OCTET STRING,
         federationServicesTags OCTET STRING,
         federationServicesAllowedTargetHosts OCTET STRING
      }
      
   
   federationServicesIndex OBJECT-TYPE
      SYNTAX      OCTET STRING
      MAX-ACCESS  not-accessible
      STATUS      current
      DESCRIPTION "Index column"
      ::= { federationServicesEntry 1  }
   
   
   federationServicesObjectName OBJECT-TYPE
      SYNTAX      OCTET STRING
      MAX-ACCESS  read-only
      STATUS      current
      DESCRIPTION "ObjectName column"
      ::= { federationServicesEntry 2  }
   
   
   federationServicesType OBJECT-TYPE
      SYNTAX      OCTET STRING
      MAX-ACCESS  read-only
      STATUS      current
      DESCRIPTION "Returns the type of the MBean. "
      ::= { federationServicesEntry 3  }
   
   
   federationServicesSourceIdHex OBJECT-TYPE
      SYNTAX      OCTET STRING
      MAX-ACCESS  read-only
      STATUS      current
      DESCRIPTION "The Source Site ID in hexadecimal. This read-only value is a hexadecimal representation of a 20-byte binary value that is calculated from the SourceSiteURL. If you want to configure ARTIFACT profile with another site, you will need to give a SourceId value to the other site. This value is automatically updated when the SourceSiteURL changes. "
      ::= { federationServicesEntry 4  }
   
   
   federationServicesAssertionStoreClassName OBJECT-TYPE
      SYNTAX      OCTET STRING
      MAX-ACCESS  read-only
      STATUS      current
      DESCRIPTION "The class that provides persistent storage for assertions, if you use an Assertion Store class other than the default class. "
      ::= { federationServicesEntry 5  }
   
   
   federationServicesITSRequiresSSL OBJECT-TYPE
      SYNTAX      OCTET STRING
      MAX-ACCESS  read-only
      STATUS      current
      DESCRIPTION "Specifies whether the Intersite Transfer Service requires SSL. "
      ::= { federationServicesEntry 6  }
   
   
   federationServicesARSRequiresTwoWaySSL OBJECT-TYPE
      SYNTAX      OCTET STRING
      MAX-ACCESS  read-only
      STATUS      current
      DESCRIPTION "Specifies whether the Assertion Retrieval Service requires two-way SSL authentication. "
      ::= { federationServicesEntry 7  }
   
   
   federationServicesPOSTRecipientCheckEnabled OBJECT-TYPE
      SYNTAX      OCTET STRING
      MAX-ACCESS  read-only
      STATUS      current
      DESCRIPTION "Specifies whether the POST recipient check is enabled. When true, the recipient of the SAML Response must match the URL in the HTTP Request. "
      ::= { federationServicesEntry 8  }
   
   
   federationServicesACSRequiresSSL OBJECT-TYPE
      SYNTAX      OCTET STRING
      MAX-ACCESS  read-only
      STATUS      current
      DESCRIPTION "Specifies whether the Assertion Consumer Service requires SSL. "
      ::= { federationServicesEntry 9  }
   
   
   federationServicesSourceSiteURL OBJECT-TYPE
      SYNTAX      OCTET STRING
      MAX-ACCESS  read-only
      STATUS      current
      DESCRIPTION "The URL for the Source Site. "
      ::= { federationServicesEntry 10  }
   
   
   federationServicesSigningKeyAlias OBJECT-TYPE
      SYNTAX      OCTET STRING
      MAX-ACCESS  read-only
      STATUS      current
      DESCRIPTION "The alias used to store and retrieve the Source Site's signing key in the keystore. This key is used to sign POST profile responses. "
      ::= { federationServicesEntry 11  }
   
   
   federationServicesName OBJECT-TYPE
      SYNTAX      OCTET STRING
      MAX-ACCESS  read-only
      STATUS      current
      DESCRIPTION "The user-specified name of this MBean instance.  This name is included as one of the key properties in the MBean's javax.management.ObjectName:  Name=user-specified-name "
      ::= { federationServicesEntry 12  }
   
   
   federationServicesSSLClientIdentityAlias OBJECT-TYPE
      SYNTAX      OCTET STRING
      MAX-ACCESS  read-only
      STATUS      current
      DESCRIPTION "The alias used to store and retrieve the Destination Site's SSL client identity in the keystore. "
      ::= { federationServicesEntry 13  }
   
   
   federationServicesSourceIdBase64 OBJECT-TYPE
      SYNTAX      OCTET STRING
      MAX-ACCESS  read-only
      STATUS      current
      DESCRIPTION "The Source Site ID base64-encoded. This read-only value is a Base64 representation of a 20-byte binary value that is calculated from the SourceSiteURL. If you want to configure ARTIFACT profile with another site, you will need to give a SourceId value to the other site. This value is automatically updated when the SourceSiteURL changes. "
      ::= { federationServicesEntry 14  }
   
   
   federationServicesDestinationSiteEnabled OBJECT-TYPE
      SYNTAX      OCTET STRING
      MAX-ACCESS  read-only
      STATUS      current
      DESCRIPTION "Specifies whether the Destination Site is enabled. "
      ::= { federationServicesEntry 15  }
   
   
   federationServicesPOSTOneUseCheckEnabled OBJECT-TYPE
      SYNTAX      OCTET STRING
      MAX-ACCESS  read-only
      STATUS      current
      DESCRIPTION "Specifies whether the POST one-use check is enabled. "
      ::= { federationServicesEntry 16  }
   
   
   federationServicesUsedAssertionCacheClassName OBJECT-TYPE
      SYNTAX      OCTET STRING
      MAX-ACCESS  read-only
      STATUS      current
      DESCRIPTION "The class used as the persistent store for the Used Assertion Cache. When no class is specified, the default Used Assertion Cache implementation is used. "
      ::= { federationServicesEntry 17  }
   
   
   federationServicesARSRequiresSSL OBJECT-TYPE
      SYNTAX      OCTET STRING
      MAX-ACCESS  read-only
      STATUS      current
      DESCRIPTION "Specifies whether the Assertion Retrieval Service requires SSL. "
      ::= { federationServicesEntry 18  }
   
   
   federationServicesSourceSiteEnabled OBJECT-TYPE
      SYNTAX      OCTET STRING
      MAX-ACCESS  read-only
      STATUS      current
      DESCRIPTION "Indicates whether the Source Site is enabled. "
      ::= { federationServicesEntry 19  }
   
   
   federationServicesAssertionConsumerURIs OBJECT-TYPE
      SYNTAX      OCTET STRING
      MAX-ACCESS  read-only
      STATUS      current
      DESCRIPTION "The Assertion Consumer URIs. "
      ::= { federationServicesEntry 20  }
   
   
   federationServicesAssertionRetrievalURIs OBJECT-TYPE
      SYNTAX      OCTET STRING
      MAX-ACCESS  read-only
      STATUS      current
      DESCRIPTION "One or more URIs on which to listen for incoming assertion retrieval requests.  For artifact profile, the destination site receives a SAML artifact that represents a source site (why we need the source site ID values) and an assertion ID. The destination site sends a request containing the artifact to the source site's assertion retrieval URL, and the source site responds with the corresponding assertion. You may configure multiple URIs here, although typically one will be sufficient. The URI includes the application context, followed by the resource context. For example:   /my_application/saml/ars  which would be accessible from the outside as https://my.example.com/my_application/saml/ars "
      ::= { federationServicesEntry 21  }
   
   
   federationServicesIntersiteTransferURIs OBJECT-TYPE
      SYNTAX      OCTET STRING
      MAX-ACCESS  read-only
      STATUS      current
      DESCRIPTION "The Intersite Transfer URIs. "
      ::= { federationServicesEntry 22  }
   
   
   federationServicesTags OBJECT-TYPE
      SYNTAX      OCTET STRING
      MAX-ACCESS  read-only
      STATUS      current
      DESCRIPTION "Return all tags on this Configuration MBean "
      ::= { federationServicesEntry 23  }
   
   
   federationServicesAllowedTargetHosts OBJECT-TYPE
      SYNTAX      OCTET STRING
      MAX-ACCESS  read-only
      STATUS      current
      DESCRIPTION "List of hosts to compare against the host in the SAML SP target redirect URL. When the list is empty, the target redirect URL will not be checked. "
      ::= { federationServicesEntry 24  }
   
   
   fileStoreTable OBJECT-TYPE
      SYNTAX      SEQUENCE OF FileStoreEntry
      MAX-ACCESS  not-accessible
      STATUS      current
      DESCRIPTION "Defines an instance of the persistent store on the specified target that will keep its persistent objects in files on the filesystem. It may be used by JMS and by other subsystems. "
      ::= { wls 925  }
      
   
   fileStoreEntry OBJECT-TYPE
      SYNTAX      FileStoreEntry
      MAX-ACCESS  not-accessible
      STATUS      current
      DESCRIPTION "Generated SNMP Table Entry."
      INDEX { fileStoreIndex}
      ::= { fileStoreTable 1 }
      
   FileStoreEntry ::=
      SEQUENCE
      {
         fileStoreIndex       OCTET STRING,
         fileStoreObjectName  OCTET STRING,
         fileStoreType        OCTET STRING,
         fileStoreDeploymentOrder Integer32,
         fileStoreLogicalName OCTET STRING,
         fileStoreXAResourceName OCTET STRING,
         fileStoreName        OCTET STRING,
         fileStoreMinWindowBufferSize INTEGER,
         fileStoreInitialSize Counter64,
         fileStoreBlockSize   INTEGER,
         fileStoreMaxFileSize Counter64,
         fileStoreIoBufferSize INTEGER,
         fileStoreMaxWindowBufferSize INTEGER,
         fileStoreSynchronousWritePolicy OCTET STRING,
         fileStoreDirectory   OCTET STRING,
         fileStoreFileLockingEnabled OCTET STRING,
         fileStoreCacheDirectory OCTET STRING,
         fileStorePartialClusterStabilityDelaySeconds Counter64,
         fileStoreRestartInPlace OCTET STRING,
         fileStoreNumberOfRestartAttempts INTEGER,
         fileStoreSecondsBetweenRestarts INTEGER,
         fileStoreDistributionPolicy OCTET STRING,
         fileStoreTags        OCTET STRING,
         fileStoreMigrationPolicy OCTET STRING,
         fileStoreFailbackDelaySeconds Counter64,
         fileStoreInitialBootDelaySeconds Counter64,
         fileStoreFailOverLimit INTEGER
      }
      
   
   fileStoreIndex OBJECT-TYPE
      SYNTAX      OCTET STRING
      MAX-ACCESS  not-accessible
      STATUS      current
      DESCRIPTION "Index column"
      ::= { fileStoreEntry 1  }
   
   
   fileStoreObjectName OBJECT-TYPE
      SYNTAX      OCTET STRING
      MAX-ACCESS  read-only
      STATUS      current
      DESCRIPTION "ObjectName column"
      ::= { fileStoreEntry 2  }
   
   
   fileStoreType OBJECT-TYPE
      SYNTAX      OCTET STRING
      MAX-ACCESS  read-only
      STATUS      current
      DESCRIPTION "Returns the type of the MBean. "
      ::= { fileStoreEntry 3  }
   
   
   fileStoreDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { fileStoreEntry 4  }
   
   
   fileStoreLogicalName OBJECT-TYPE
      SYNTAX      OCTET STRING
      MAX-ACCESS  read-only
      STATUS      current
      DESCRIPTION "The name used by subsystems to refer to different stores on different servers using the same name.  For example, an EJB that uses the timer service may refer to its store using the logical name, and this name may be valid on multiple servers in the same cluster, even if each server has a store with a different physical name.  Multiple stores in the same domain or the same cluster may share the same logical name. However, a given logical name may not be assigned to more than one store on the same server. "
      ::= { fileStoreEntry 5  }
   
   
   fileStoreXAResourceName OBJECT-TYPE
      SYNTAX      OCTET STRING
      MAX-ACCESS  read-only
      STATUS      current
      DESCRIPTION "Overrides the name of the XAResource that this store registers with JTA.  You should not normally set this attribute. Its purpose is to allow the name of the XAResource to be overridden when a store has been upgraded from an older release and the store contained prepared transactions. The generated name should be used in all other cases. "
      ::= { fileStoreEntry 6  }
   
   
   fileStoreName OBJECT-TYPE
      SYNTAX      OCTET STRING
      MAX-ACCESS  read-only
      STATUS      current
      DESCRIPTION "The user-specified name of this MBean instance.  This name is included as one of the key properties in the MBean's javax.management.ObjectName:  Name=user-specified-name "
      ::= { fileStoreEntry 7  }
   
   
   fileStoreMinWindowBufferSize OBJECT-TYPE
      SYNTAX      INTEGER
      MAX-ACCESS  read-only
      STATUS      current
      DESCRIPTION "The minimum amount of data, in bytes and rounded down to the nearest power of 2, mapped into the JVM's address space per primary store file. Applies to synchronous write policies Direct-Write-With-Cache and Disabled, but only when a native wlfileio library is loaded. See Maximum Window Buffer Size. "
      ::= { fileStoreEntry 8  }
   
   
   fileStoreInitialSize OBJECT-TYPE
      SYNTAX      Counter64
      MAX-ACCESS  read-only
      STATUS      current
      DESCRIPTION "The initial file size, in bytes.  Set InitialSize to pre-allocate file space during a file store boot. If InitialSize exceeds MaxFileSize, a store creates multiple files (number of files = InitialSize/MaxFileSize rounded up).  A file store automatically reuses the space from deleted records and automatically expands a file if there is not enough space for a new write request.  Use InitialSize to limit or prevent file expansions during runtime, as file expansion introduces temporary latencies that may be noticeable under rare circumstances.  Changes to initial size only take effect for new file stores, or after any current files have been deleted prior to restart.   See Maximum File Size.  "
      ::= { fileStoreEntry 9  }
   
   
   fileStoreBlockSize OBJECT-TYPE
      SYNTAX      INTEGER
      MAX-ACCESS  read-only
      STATUS      current
      DESCRIPTION "The smallest addressable block, in bytes, of a file. When a native wlfileio driver is available and the block size has not been configured by the user, the store selects the minimum OS specific value for unbuffered (direct) I/O, if it is within the range [512, 8192]. A file store's block size does not change once the file store creates its files. Changes to block size only take effect for new file stores or after the current files have been deleted. See 'Tuning the Persistent Store' in Tuning Performance of Oracle WebLogic Server. "
      ::= { fileStoreEntry 10  }
   
   
   fileStoreMaxFileSize OBJECT-TYPE
      SYNTAX      Counter64
      MAX-ACCESS  read-only
      STATUS      current
      DESCRIPTION "The maximum file size, in bytes, of an individual data file.  The MaxFileSize value affects the number of files needed to accommodate a store of a particular size (number of files = store size/MaxFileSize rounded up).  A file store automatically reuses space freed by deleted records and automatically expands individual files up to MaxFileSize if there is not enough space for a new record. If there is no space left in exiting files for a new record, a store creates an additional file.   A small number of larger files is normally preferred over a large number of smaller files as each file allocates Window Buffer and file handles.    If MaxFileSize is larger than 2^24 * BlockSize, then MaxFileSize is ignored, and the value becomes 2^24 * BlockSize. The default BlockSize is 512, and 2^24 * 512 is 8 GB.  The minimum size for MaxFileSize is 10 MB when multiple data files are used by the store. If InitialSize is less than MaxFileSize then a single file will be created of InitialSize bytes. If InitialSize is larger than MaxFileSize then (InitialSize / MaxFileSize) files will be created of MaxFileSize bytes and an additional file if necessary to contain any remainder.   See Initial Size.  "
      ::= { fileStoreEntry 11  }
   
   
   fileStoreIoBufferSize OBJECT-TYPE
      SYNTAX      INTEGER
      MAX-ACCESS  read-only
      STATUS      current
      DESCRIPTION "The I/O buffer size, in bytes, automatically rounded down to the nearest power of 2.   For the Direct-Write-With-Cache policy when a native wlfileio driver is available, IOBufferSize describes the maximum portion of a cache view that is passed to a system call. This portion does not consume off-heap (native) or Java heap memory.   For the Direct-Write and Cache-Flush policies, IOBufferSize is the size of a per store buffer which consumes off-heap (native) memory, where one buffer is allocated during run-time, but multiple buffers may be temporarily created during boot recovery.  When a native wlfileio driver is not available, the setting applies to off-heap (native) memory for all policies (including Disabled).  For the best runtime performance, Oracle recommends setting IOBufferSize so that it is larger than the largest write (multiple concurrent store requests may be combined into a single write).  For the best boot recovery time performance of large stores, Oracle recommends setting IOBufferSize to at least 2 megabytes.   See AllocatedIOBufferBytes to find out the actual allocated off-heap (native) memory amount. It is a multiple of IOBufferSize for the Direct-Write and Cache-Flush policies, or zero. "
      ::= { fileStoreEntry 12  }
   
   
   fileStoreMaxWindowBufferSize OBJECT-TYPE
      SYNTAX      INTEGER
      MAX-ACCESS  read-only
      STATUS      current
      DESCRIPTION "The maximum amount of data, in bytes and rounded down to the nearest power of 2, mapped into the JVM's address space per primary store file. Applies to synchronous write policies Direct-Write-With-Cache and Disabled but only when the native wlfileio library is loaded.  A window buffer does not consume Java heap memory, but does consume off-heap (native) memory. If the store is unable to allocate the requested buffer size, it allocates smaller and smaller buffers until it reaches MinWindowBufferSize, and then fails if cannot honor MinWindowBufferSize.  Oracle recommends setting the max window buffer size to more than double the size of the largest write (multiple concurrently updated records may be combined into a single write), and greater than or equal to the file size, unless there are other constraints. 32-bit JVMs may impose a total limit of between 2 and 4GB for combined Java heap plus off-heap (native) memory usage.   See store attribute AllocatedWindowBufferBytes to find out the actual allocated Window Buffer Size.   See Maximum File Size and Minimum Window Buffer Size.  "
      ::= { fileStoreEntry 13  }
   
   
   fileStoreSynchronousWritePolicy OBJECT-TYPE
      SYNTAX      OCTET STRING
      MAX-ACCESS  read-only
      STATUS      current
      DESCRIPTION "The disk write policy that determines how the file store writes data to disk.  This policy also affects the JMS file store's performance, scalability, and reliability. Oracle recommends Direct-Write-With-Cache which tends to have the highest performance. The default value is Direct-Write. The valid policy options are:   Direct-Write Direct I/O is supported on all platforms. When available, file stores in direct I/O mode automatically load the native I/O wlfileio driver. This option tends to out-perform Cache-Flush and tend to be slower than Direct-Write-With-Cache. This mode does not require a native store wlfileio driver, but performs faster when they are available.  Direct-Write-With-Cache Store records are written synchronously to primary files in the directory specified by the Directory attribute and asynchronously to a corresponding cache file in the Cache Directory. The Cache Directory provides information about disk space, locking, security, and performance implications. This mode requires a native store wlfileiocode driver. If the native driver cannot be loaded, then the write mode automatically switches to Direct-Write. See Cache Directory.  Cache-Flush Transactions cannot complete until all of their writes have been flushed down to disk. This policy is reliable and scales well as the number of simultaneous users increases.Transactionally safe but tends to be a lower performer than direct-write policies.  Disabled Transactions are complete as soon as their writes are cached in memory, instead of waiting for the writes to successfully reach the disk. This is the fastest policy because write requests do not block waiting to be synchronized to disk, but, unlike other policies, is not transactionally safe in the event of operating system or hardware failures. Such failures can lead to duplicate or lost data/messages. This option does not require native store wlfileio drivers, but may run faster when they are available. Some non-WebLogic JMS vendors default to a policy that is equivalent to Disabled.   Notes:  When available, file stores load WebLogic wlfileio native drivers, which can improve performance. These drivers are included with Windows, Solaris, Linux, and AIX WebLogic installations.  Certain older versions of Microsoft Windows may incorrectly report storage device synchronous write completion if the Windows default Write Cache Enabled setting is used. This violates the transactional semantics of transactional products (not specific to Oracle), including file stores configured with a Direct-Write (default) or Direct-Write-With-Cache policy, as a system crash or power failure can lead to a loss or a duplication of records/messages. One of the visible symptoms is that this problem may manifest itself in high persistent message/transaction throughput exceeding the physical capabilities of your storage device. You can address the problem by applying a Microsoft supplied patch, disabling the Windows Write Cache Enabled setting, or by using a power-protected storage device. See http://support.microsoft.com/kb/281672 and http://support.microsoft.com/kb/332023.  NFS storage note:  On some operating systems, native driver memory-mapping is incompatible with NFS when files are locked. Stores with synchronous write policies Direct-Write-With-Cache or Disabled, and WebLogic JMS paging stores enhance performance by using the native wlfileio driver to perform memory-map operating system calls. When a store detects an incompatibility between NFS, file locking, and memory mapping, it automatically downgrades to conventional read/write system calls instead of memory mapping. For best performance, Oracle recommends investigating alternative NFS client drivers, configuring a non-NFS storage location, or in controlled environments and at your own risk, disabling the file locks (See Enable File Locking). For more information, see 'Tuning the WebLogic Persistent Store' in Tuning Performance of Oracle WebLogic Server.  "
      ::= { fileStoreEntry 14  }
   
   
   fileStoreDirectory OBJECT-TYPE
      SYNTAX      OCTET STRING
      MAX-ACCESS  read-only
      STATUS      current
      DESCRIPTION "The path name to the file system directory where the file store maintains its data files.  When targeting a file store to a migratable target, the store directory must be accessible from all candidate server members in the migratable target. For highest availability, use either a SAN (Storage Area Network) or other reliable shared storage. Use of NFS mounts is discouraged, but supported. Most NFS mounts are not transactionally safe by default, and, to ensure transactional correctness, need to be configured using your NFS vendor documentation in order to honor synchronous write requests. For SynchronousWritePolicy of Direct-Write-With-Cache, see Cache Directory.  Additional O/S tuning may be required if the directory is hosted by Microsoft Windows, see Synchronous Write Policy for details. "
      ::= { fileStoreEntry 15  }
   
   
   fileStoreFileLockingEnabled OBJECT-TYPE
      SYNTAX      OCTET STRING
      MAX-ACCESS  read-only
      STATUS      current
      DESCRIPTION "Determines whether OS file locking is used.  When file locking protection is enabled, a store boot fails if another store instance already has opened the store files. Do not disable this setting unless you have procedures in place to prevent multiple store instances from opening the same file. File locking is not required but helps prevent corruption in the event that two same-named file store instances attempt to operate in the same directories. This setting applies to both primary and cache files. "
      ::= { fileStoreEntry 16  }
   
   
   fileStoreCacheDirectory OBJECT-TYPE
      SYNTAX      OCTET STRING
      MAX-ACCESS  read-only
      STATUS      current
      DESCRIPTION "The location of the cache directory for Direct-Write-With-Cache, ignored for other policies.  When Direct-Write-With-Cache is specified as the SynchronousWritePolicy, cache files are created in addition to primary files (see Directory for the location of primary files). If a cache directory location is specified, the cache file path is CacheDirectory/WLStoreCache/StoreNameFileNum.DAT.cache. When specified, Oracle recommends using absolute paths, but if the directory location is a relative path, then CacheDirectory is created relative to the WebLogic Server instance's home directory. If '' or Null is specified, the Cache Directory is located in the current operating system temp directory as determined by the java.io.tmpdir Java System property (JDK's default: /tmp on UNIX, %TEMP%  on Windows) and is  TempDirectory/WLStoreCache/DomainName/unique-id/StoreNameFileNum.DAT.cache. The value of java.io.tmpdir varies between operating systems and configurations, and can be overridden by passing -Djava.io.tmpdir=My_path on the JVM command line.   Considerations:  Security: Some users may want to set specific directory permissions to limit access to the cache directory, especially if there are custom configured user access limitations on the primary directory. For a complete guide to WebLogic security, see 'Securing a Production Environment for Oracle WebLogic Server.'   Additional Disk Space Usage: Cache files consume the same amount of disk space as the primary store files that they mirror. See Directory for the location of primary store files.  Performance: For the best performance, a cache directory should be located in local storage instead of NAS/SAN (remote) storage, preferably in the operating system's temp directory. Relative paths should be avoided, as relative paths are located based on the domain installation, which is typically on remote storage. It is safe to delete a cache directory while the store is not running, but this may slow down the next store boot.  Preventing Corruption and File Locking: Two same named stores must not be configured to share the same primary or cache directory. There are store file locking checks that are designed to detect such conflicts and prevent corruption by failing the store boot, but it is not recommended to depend on the file locking feature for correctness. See Enable File Locking.   Boot Recovery: Cache files are reused to speed up the File Store boot and recovery process, but only if the store's host WebLogic Server instance has been shut down cleanly prior to the current boot. For example, cache files are not re-used and are instead fully recreated: after a kill -9, after an OS or JVM crash, or after an off-line change to the primary files, such as a store admin compaction. When cache files are recreated, a Warning log message 280102 is generated.  Fail-Over/Migration Recovery: A file store safely recovers its data without its cache directory. Therefore, a cache directory does not need to be copied or otherwise made accessible after a fail-over or migration, and similarly does not need to be placed in NAS/SAN storage. A Warning log message 280102, which is generated to indicate the need to recreate the cache on the new host system, can be ignored.   Cache File Cleanup: To prevent unused cache files from consuming disk space, test and developer environments should periodically delete cache files.  "
      ::= { fileStoreEntry 17  }
   
   
   fileStorePartialClusterStabilityDelaySeconds OBJECT-TYPE
      SYNTAX      Counter64
      MAX-ACCESS  read-only
      STATUS      current
      DESCRIPTION "Specifies the amount of time, in seconds, to delay before a partially started cluster starts all cluster-targeted JMS artifact instances that are configured with a Migration Policy of Always or On-Failure.   Before this timeout expires or all servers are running, a cluster starts a subset of such instances based on the total number of servers running and the configured cluster size. Once the timeout expires or all servers have started, the system considers the cluster stable and starts any remaining services.  This delay ensures that services are balanced across a cluster even if the servers are started sequentially. It is ignored after a cluster is fully started (stable) or when individual servers are started.   A value > 0 specifies the time, in seconds, to delay before a partially started cluster starts dynamically configured services. A value of 0 specifies no delay.  "
      ::= { fileStoreEntry 18  }
   
   
   fileStoreRestartInPlace OBJECT-TYPE
      SYNTAX      OCTET STRING
      MAX-ACCESS  read-only
      STATUS      current
      DESCRIPTION " Enables a periodic automatic in-place restart of failed cluster-targeted or standalone-server-targeted JMS artifact instance(s) running on healthy WebLogic Server instances. See the migratable target settings for in-place restarts of migratable-targeted JMS artifacts. When the Restart In Place setting is configured on a store, it applies to all JMS artifacts that reference the store.    If the Migration Policy of the JMS artifact is set to Off, Restart In Place is disabled by default.  If the Migration Policy of the JMS artifact is set to On-Failure or Always, Restart In Place is enabled by default.  This attribute is not used by WebLogic messaging bridges which automatically restart internal connections as needed.  For a JMS artifact that is cluster-targeted and the Migration Policy is set to On-Failure or Always, if restart fails after the configured maximum retry attempts, it will migrate to a different server within the cluster.    "
      ::= { fileStoreEntry 19  }
   
   
   fileStoreNumberOfRestartAttempts OBJECT-TYPE
      SYNTAX      INTEGER
      MAX-ACCESS  read-only
      STATUS      current
      DESCRIPTION "Specifies the maximum number of restart attempts.   A value > 0 specifies the maximum number of restart attempts. A value of 0 specifies the same behavior as setting {@link #getRestartInPlace} to false. A value of -1 means infinite retry restart until it either starts or the server instance shuts down.  "
      ::= { fileStoreEntry 20  }
   
   
   fileStoreSecondsBetweenRestarts OBJECT-TYPE
      SYNTAX      INTEGER
      MAX-ACCESS  read-only
      STATUS      current
      DESCRIPTION "Specifies the amount of time, in seconds, to wait in between attempts to restart a failed service instance. "
      ::= { fileStoreEntry 21  }
   
   
   fileStoreDistributionPolicy OBJECT-TYPE
      SYNTAX      OCTET STRING
      MAX-ACCESS  read-only
      STATUS      current
      DESCRIPTION "Specifies how the instances of a configured JMS artifact are named and distributed when cluster-targeted.  A JMS artifact is cluster-targeted when its target is directly set to a cluster, or when it is scoped to a resource group and the resource group is in turn targeted to a cluster.  When this setting is configured on a store, it applies to all JMS artifacts that reference the store.  Valid options:   Distributed Creates an instance on each server JVM in a cluster. Required for all SAF agents and for cluster-targeted or resource-group-scoped JMS servers that host distributed destinations.    Singleton Creates a single instance on a single server JVM within a cluster. Required for cluster-targeted or resource-group-scoped JMS servers that host standalone (non-distributed) destinations and for cluster-targeted or resource-group-scoped path services.  The Migration Policy must be On-Failure or Always when using this option with a JMS server, On-Failure when using this option with a messaging bridge, and Always when using this option with a path service.    Instance Naming Note:   The DistributionPolicy determines the instance name suffix for cluster-targeted JMS artifacts.  The suffix for a cluster-targeted Singleton is -01 and for a cluster-targeted Distributed is @ClusterMemberName.    Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   If you cannot cluster-target a bridge and still need singleton behavior in a configured cluster, you can target the bridge to a migratable target and configure the Migration Policy on the migratable target to Exactly-Once.   "
      ::= { fileStoreEntry 22  }
   
   
   fileStoreTags OBJECT-TYPE
      SYNTAX      OCTET STRING
      MAX-ACCESS  read-only
      STATUS      current
      DESCRIPTION "Return all tags on this Configuration MBean "
      ::= { fileStoreEntry 23  }
   
   
   fileStoreMigrationPolicy OBJECT-TYPE
      SYNTAX      OCTET STRING
      MAX-ACCESS  read-only
      STATUS      current
      DESCRIPTION "Controls migration and restart behavior of cluster-targeted JMS service artifact instances. When this setting is configured on a cluster-targeted store, it applies to all JMS artifacts that reference the store. See the migratable target settings for enabling migration and restart on migratable-targeted JMS artifacts.  Off Disables migration support for cluster-targeted JMS service objects, and changes the default for Restart In Place to false. If you want a restart to be enabled when the Migration Policy is Off, then Restart In Place must be explicitly configured to true. This policy cannot be combined with the Singleton Migration Policy.  On-Failure Enables automatic migration and restart of instances on the failure of a subsystem Service or WebLogic Server instance, including automatic fail-back and load balancing of instances.   Always Provides the same behavior as On-Failure and automatically migrates instances even in the event of a graceful shutdown or a partial cluster start.   Note: Cluster leasing must be configured for On-Failure and Always.  Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   A Migration Policy of Always is not recommended for bridges.   If you cannot cluster-target a bridge and still need singleton behavior in a configured cluster, you can target the bridge to a migratable target and configure the Migration Policy on the migratable target to Exactly-Once.   "
      ::= { fileStoreEntry 24  }
   
   
   fileStoreFailbackDelaySeconds OBJECT-TYPE
      SYNTAX      Counter64
      MAX-ACCESS  read-only
      STATUS      current
      DESCRIPTION "Specifies the amount of time, in seconds, to delay before failing a cluster-targeted JMS artifact instance back to its preferred server after the preferred server failed and was restarted.  This delay allows time for the system to stabilize and dependent services to be restarted, preventing a system failure during a reboot.   A value > 0 specifies the time, in seconds, to delay before failing a JMS artifact back to its user preferred server. A value of 0 indicates that the instance would never failback. A value of -1 indicates that there is no delay and the instance would failback immediately.   Note: This setting only applies when the JMS artifact is cluster-targeted and the Migration Policy is set to On-Failure or Always. "
      ::= { fileStoreEntry 25  }
   
   
   fileStoreInitialBootDelaySeconds OBJECT-TYPE
      SYNTAX      Counter64
      MAX-ACCESS  read-only
      STATUS      current
      DESCRIPTION "Specifies the amount of time, in seconds, to delay before starting a cluster-targeted JMS instance on a newly booted WebLogic Server instance. When this setting is configured on a store, it applies to all JMS artifacts that reference the store.  This allows time for the system to stabilize and dependent services to be restarted, preventing a system failure during a reboot.   A value > 0 is the time, in seconds, to delay before before loading resources after a failure and restart. A value of 0 specifies no delay.  Note: This setting only applies when the JMS artifact is cluster-targeted and the Migration Policy is set to On-Failure or Always. "
      ::= { fileStoreEntry 26  }
   
   
   fileStoreFailOverLimit OBJECT-TYPE
      SYNTAX      INTEGER
      MAX-ACCESS  read-only
      STATUS      current
      DESCRIPTION "Specify a limit for the number of cluster-targeted JMS artifact instances that can fail over to a particular JVM.  This can be used to prevent too many instances from starting on a server, avoiding a system failure when starting too few servers of a formerly large cluster.  A typical limit value should allow all instances to run in the smallest desired cluster size, which means (smallest-cluster-size * (limit + 1)) should equal or exceed the total number of instances.    A value of -1 means there is no fail over limit (unlimited). A value of 0 prevents any fail overs of cluster-targeted JMS artifact instances, so no more than 1 instance will run per server (this is an instance that has not failed over). A value of 1 allows one fail-over instance on each server, so no more than two instances will run per server (one failed over instance plus an instance that has not failed over).   Note: This setting only applies when the JMS artifact is cluster-targeted and the Migration Policy is set to On-Failure or Always. "
      ::= { fileStoreEntry 27  }
   
   
   foreignJNDILinkTable OBJECT-TYPE
      SYNTAX      SEQUENCE OF ForeignJNDILinkEntry
      MAX-ACCESS  not-accessible
      STATUS      current
      DESCRIPTION "This class represents a JNDI link that is outside the WebLogic server. "
      ::= { wls 930  }
      
   
   foreignJNDILinkEntry OBJECT-TYPE
      SYNTAX      ForeignJNDILinkEntry
      MAX-ACCESS  not-accessible
      STATUS      current
      DESCRIPTION "Generated SNMP Table Entry."
      INDEX { foreignJNDILinkIndex}
      ::= { foreignJNDILinkTable 1 }
      
   ForeignJNDILinkEntry ::=
      SEQUENCE
      {
         foreignJNDILinkIndex OCTET STRING,
         foreignJNDILinkObjectName OCTET STRING,
         foreignJNDILinkType  OCTET STRING,
         foreignJNDILinkLocalJNDIName OCTET STRING,
         foreignJNDILinkName  OCTET STRING,
         foreignJNDILinkRemoteJNDIName OCTET STRING,
         foreignJNDILinkTags  OCTET STRING
      }
      
   
   foreignJNDILinkIndex OBJECT-TYPE
      SYNTAX      OCTET STRING
      MAX-ACCESS  not-accessible
      STATUS      current
      DESCRIPTION "Index column"
      ::= { foreignJNDILinkEntry 1  }
   
   
   foreignJNDILinkObjectName OBJECT-TYPE
      SYNTAX      OCTET STRING
      MAX-ACCESS  read-only
      STATUS      current
      DESCRIPTION "ObjectName column"
      ::= { foreignJNDILinkEntry 2  }
   
   
   foreignJNDILinkType OBJECT-TYPE
      SYNTAX      OCTET STRING
      MAX-ACCESS  read-only
      STATUS      current
      DESCRIPTION "Returns the type of the MBean. "
      ::= { foreignJNDILinkEntry 3  }
   
   
   foreignJNDILinkLocalJNDIName OBJECT-TYPE
      SYNTAX      OCTET STRING
      MAX-ACCESS  read-only
      STATUS      current
      DESCRIPTION "The local JNDI name. "
      ::= { foreignJNDILinkEntry 4  }
   
   
   foreignJNDILinkName OBJECT-TYPE
      SYNTAX      OCTET STRING
      MAX-ACCESS  read-only
      STATUS      current
      DESCRIPTION "The user-specified name of this MBean instance.  This name is included as one of the key properties in the MBean's javax.management.ObjectName:  Name=user-specified-name "
      ::= { foreignJNDILinkEntry 5  }
   
   
   foreignJNDILinkRemoteJNDIName OBJECT-TYPE
      SYNTAX      OCTET STRING
      MAX-ACCESS  read-only
      STATUS      current
      DESCRIPTION "The foreign JNDI name. "
      ::= { foreignJNDILinkEntry 6  }
   
   
   foreignJNDILinkTags OBJECT-TYPE
      SYNTAX      OCTET STRING
      MAX-ACCESS  read-only
      STATUS      current
      DESCRIPTION "Return all tags on this Configuration MBean "
      ::= { foreignJNDILinkEntry 7  }
   
   
   foreignJNDIProviderTable OBJECT-TYPE
      SYNTAX      SEQUENCE OF ForeignJNDIProviderEntry
      MAX-ACCESS  not-accessible
      STATUS      current
      DESCRIPTION "This class represents a JNDI provider that is outside the WebLogic server. "
      ::= { wls 935  }
      
   
   foreignJNDIProviderEntry OBJECT-TYPE
      SYNTAX      ForeignJNDIProviderEntry
      MAX-ACCESS  not-accessible
      STATUS      current
      DESCRIPTION "Generated SNMP Table Entry."
      INDEX { foreignJNDIProviderIndex}
      ::= { foreignJNDIProviderTable 1 }
      
   ForeignJNDIProviderEntry ::=
      SEQUENCE
      {
         foreignJNDIProviderIndex OCTET STRING,
         foreignJNDIProviderObjectName OCTET STRING,
         foreignJNDIProviderType OCTET STRING,
         foreignJNDIProviderInitialContextFactory OCTET STRING,
         foreignJNDIProviderUser OCTET STRING,
         foreignJNDIProviderProviderURL OCTET STRING,
         foreignJNDIProviderName OCTET STRING,
         foreignJNDIProviderDeploymentOrder INTEGER,
         foreignJNDIProviderTags OCTET STRING
      }
      
   
   foreignJNDIProviderIndex OBJECT-TYPE
      SYNTAX      OCTET STRING
      MAX-ACCESS  not-accessible
      STATUS      current
      DESCRIPTION "Index column"
      ::= { foreignJNDIProviderEntry 1  }
   
   
   foreignJNDIProviderObjectName OBJECT-TYPE
      SYNTAX      OCTET STRING
      MAX-ACCESS  read-only
      STATUS      current
      DESCRIPTION "ObjectName column"
      ::= { foreignJNDIProviderEntry 2  }
   
   
   foreignJNDIProviderType OBJECT-TYPE
      SYNTAX      OCTET STRING
      MAX-ACCESS  read-only
      STATUS      current
      DESCRIPTION "Returns the type of the MBean. "
      ::= { foreignJNDIProviderEntry 3  }
   
   
   foreignJNDIProviderInitialContextFactory OBJECT-TYPE
      SYNTAX      OCTET STRING
      MAX-ACCESS  read-only
      STATUS      current
      DESCRIPTION "The initial context factory to use to connect. This class name depends on the JNDI provider and the vendor you are using. The value corresponds to the standard JNDI property, java.naming.factory.initial. "
      ::= { foreignJNDIProviderEntry 4  }
   
   
   foreignJNDIProviderUser OBJECT-TYPE
      SYNTAX      OCTET STRING
      MAX-ACCESS  read-only
      STATUS      current
      DESCRIPTION "The remote server's user name. "
      ::= { foreignJNDIProviderEntry 5  }
   
   
   foreignJNDIProviderProviderURL OBJECT-TYPE
      SYNTAX      OCTET STRING
      MAX-ACCESS  read-only
      STATUS      current
      DESCRIPTION "The foreign JNDI provider URL. This value corresponds to the standard JNDI property, java.naming.provider.url. "
      ::= { foreignJNDIProviderEntry 6  }
   
   
   foreignJNDIProviderName OBJECT-TYPE
      SYNTAX      OCTET STRING
      MAX-ACCESS  read-only
      STATUS      current
      DESCRIPTION "The user-specified name of this MBean instance.  This name is included as one of the key properties in the MBean's javax.management.ObjectName:  Name=user-specified-name "
      ::= { foreignJNDIProviderEntry 7  }
   
   
   foreignJNDIProviderDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { foreignJNDIProviderEntry 8  }
   
   
   foreignJNDIProviderTags OBJECT-TYPE
      SYNTAX      OCTET STRING
      MAX-ACCESS  read-only
      STATUS      current
      DESCRIPTION "Return all tags on this Configuration MBean "
      ::= { foreignJNDIProviderEntry 9  }
   
   
   httpProxyTable OBJECT-TYPE
      SYNTAX      SEQUENCE OF HttpProxyEntry
      MAX-ACCESS  not-accessible
      STATUS      current
      DESCRIPTION "This class represents the HTTP proxy configuration. "
      ::= { wls 940  }
      
   
   httpProxyEntry OBJECT-TYPE
      SYNTAX      HttpProxyEntry
      MAX-ACCESS  not-accessible
      STATUS      current
      DESCRIPTION "Generated SNMP Table Entry."
      INDEX { httpProxyIndex}
      ::= { httpProxyTable 1 }
      
   HttpProxyEntry ::=
      SEQUENCE
      {
         httpProxyIndex       OCTET STRING,
         httpProxyObjectName  OCTET STRING,
         httpProxyType        OCTET STRING,
         httpProxyServerList  OCTET STRING,
         httpProxyDeploymentOrder Integer32,
         httpProxyMaxHealthCheckInterval Integer32,
         httpProxyHealthCheckInterval Integer32,
         httpProxyInitialConnections Integer32,
         httpProxyMaxConnections Integer32,
         httpProxyName        OCTET STRING,
         httpProxyMaxRetries  Integer32,
         httpProxyTags        OCTET STRING
      }
      
   
   httpProxyIndex OBJECT-TYPE
      SYNTAX      OCTET STRING
      MAX-ACCESS  not-accessible
      STATUS      current
      DESCRIPTION "Index column"
      ::= { httpProxyEntry 1  }
   
   
   httpProxyObjectName OBJECT-TYPE
      SYNTAX      OCTET STRING
      MAX-ACCESS  read-only
      STATUS      current
      DESCRIPTION "ObjectName column"
      ::= { httpProxyEntry 2  }
   
   
   httpProxyType OBJECT-TYPE
      SYNTAX      OCTET STRING
      MAX-ACCESS  read-only
      STATUS      current
      DESCRIPTION "Returns the type of the MBean. "
      ::= { httpProxyEntry 3  }
   
   
   httpProxyServerList OBJECT-TYPE
      SYNTAX      OCTET STRING
      MAX-ACCESS  read-only
      STATUS      current
      DESCRIPTION "The list of servers in the back end that the HCS should proxy to. "
      ::= { httpProxyEntry 4  }
   
   
   httpProxyDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { httpProxyEntry 5  }
   
   
   httpProxyMaxHealthCheckInterval OBJECT-TYPE
      SYNTAX      Integer32
      MAX-ACCESS  read-only
      STATUS      current
      DESCRIPTION "The maximum interval between health checks. "
      ::= { httpProxyEntry 6  }
   
   
   httpProxyHealthCheckInterval OBJECT-TYPE
      SYNTAX      Integer32
      MAX-ACCESS  read-only
      STATUS      current
      DESCRIPTION "The health check interval in milliseconds between pings. "
      ::= { httpProxyEntry 7  }
   
   
   httpProxyInitialConnections OBJECT-TYPE
      SYNTAX      Integer32
      MAX-ACCESS  read-only
      STATUS      current
      DESCRIPTION "The number of initial connections that should be opened to each server in the back end servers. "
      ::= { httpProxyEntry 8  }
   
   
   httpProxyMaxConnections OBJECT-TYPE
      SYNTAX      Integer32
      MAX-ACCESS  read-only
      STATUS      current
      DESCRIPTION "The maximum number of connections that each server can open to the back end servers. "
      ::= { httpProxyEntry 9  }
   
   
   httpProxyName OBJECT-TYPE
      SYNTAX      OCTET STRING
      MAX-ACCESS  read-only
      STATUS      current
      DESCRIPTION "The user-specified name of this MBean instance.  This name is included as one of the key properties in the MBean's javax.management.ObjectName:  Name=user-specified-name "
      ::= { httpProxyEntry 10  }
   
   
   httpProxyMaxRetries OBJECT-TYPE
      SYNTAX      Integer32
      MAX-ACCESS  read-only
      STATUS      current
      DESCRIPTION "The max retries after which the server will be marked dead. "
      ::= { httpProxyEntry 11  }
   
   
   httpProxyTags OBJECT-TYPE
      SYNTAX      OCTET STRING
      MAX-ACCESS  read-only
      STATUS      current
      DESCRIPTION "Return all tags on this Configuration MBean "
      ::= { httpProxyEntry 12  }
   
   
   jdbcStoreTable OBJECT-TYPE
      SYNTAX      SEQUENCE OF JdbcStoreEntry
      MAX-ACCESS  not-accessible
      STATUS      current
      DESCRIPTION "Defines an instance of the persistent store that stores its persistent records in a JDBC-accessible database. It may be used by JMS and by other subsystems. "
      ::= { wls 950  }
      
   
   jdbcStoreEntry OBJECT-TYPE
      SYNTAX      JdbcStoreEntry
      MAX-ACCESS  not-accessible
      STATUS      current
      DESCRIPTION "Generated SNMP Table Entry."
      INDEX { jdbcStoreIndex}
      ::= { jdbcStoreTable 1 }
      
   JdbcStoreEntry ::=
      SEQUENCE
      {
         jdbcStoreIndex       OCTET STRING,
         jdbcStoreObjectName  OCTET STRING,
         jdbcStoreType        OCTET STRING,
         jdbcStoreDeploymentOrder Integer32,
         jdbcStoreDeletesPerBatchMaximum Integer32,
         jdbcStoreLogicalName OCTET STRING,
         jdbcStoreXAResourceName OCTET STRING,
         jdbcStoreDeletesPerStatementMaximum Integer32,
         jdbcStoreInsertsPerBatchMaximum Integer32,
         jdbcStoreName        OCTET STRING,
         jdbcStoreCreateTableDDLFile OCTET STRING,
         jdbcStorePrefixName  OCTET STRING,
         jdbcStoreWorkerPreferredBatchSize INTEGER,
         jdbcStoreWorkerCount INTEGER,
         jdbcStoreThreeStepThreshold INTEGER,
         jdbcStoreOraclePiggybackCommitEnabled OCTET STRING,
         jdbcStorePartialClusterStabilityDelaySeconds Counter64,
         jdbcStoreRestartInPlace OCTET STRING,
         jdbcStoreNumberOfRestartAttempts INTEGER,
         jdbcStoreSecondsBetweenRestarts INTEGER,
         jdbcStoreDistributionPolicy OCTET STRING,
         jdbcStoreTags        OCTET STRING,
         jdbcStoreMigrationPolicy OCTET STRING,
         jdbcStoreReconnectRetryPeriodMillis INTEGER,
         jdbcStoreFailbackDelaySeconds Counter64,
         jdbcStoreInitialBootDelaySeconds Counter64,
         jdbcStoreReconnectRetryIntervalMillis INTEGER,
         jdbcStoreConnectionCachingPolicy OCTET STRING,
         jdbcStoreFailOverLimit INTEGER
      }
      
   
   jdbcStoreIndex OBJECT-TYPE
      SYNTAX      OCTET STRING
      MAX-ACCESS  not-accessible
      STATUS      current
      DESCRIPTION "Index column"
      ::= { jdbcStoreEntry 1  }
   
   
   jdbcStoreObjectName OBJECT-TYPE
      SYNTAX      OCTET STRING
      MAX-ACCESS  read-only
      STATUS      current
      DESCRIPTION "ObjectName column"
      ::= { jdbcStoreEntry 2  }
   
   
   jdbcStoreType OBJECT-TYPE
      SYNTAX      OCTET STRING
      MAX-ACCESS  read-only
      STATUS      current
      DESCRIPTION "Returns the type of the MBean. "
      ::= { jdbcStoreEntry 3  }
   
   
   jdbcStoreDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { jdbcStoreEntry 4  }
   
   
   jdbcStoreDeletesPerBatchMaximum OBJECT-TYPE
      SYNTAX      Integer32
      MAX-ACCESS  read-only
      STATUS      current
      DESCRIPTION "The maximum number of table rows that are deleted per database call.    When possible, a JDBC store uses JDBC 3.0 batching to batch concurrent client requests.    Both the maximum batch size for concurrent inserts and for concurrent writes are configurable.    To disable JDBC 3.0 batching, set the maximum batch size to 1.    The maximum batch size has no effect on the maximum number of concurrent client requests.   "
      ::= { jdbcStoreEntry 5  }
   
   
   jdbcStoreLogicalName OBJECT-TYPE
      SYNTAX      OCTET STRING
      MAX-ACCESS  read-only
      STATUS      current
      DESCRIPTION "The name used by subsystems to refer to different stores on different servers using the same name.  For example, an EJB that uses the timer service may refer to its store using the logical name, and this name may be valid on multiple servers in the same cluster, even if each server has a store with a different physical name.  Multiple stores in the same domain or the same cluster may share the same logical name. However, a given logical name may not be assigned to more than one store on the same server. "
      ::= { jdbcStoreEntry 6  }
   
   
   jdbcStoreXAResourceName OBJECT-TYPE
      SYNTAX      OCTET STRING
      MAX-ACCESS  read-only
      STATUS      current
      DESCRIPTION "Overrides the name of the XAResource that this store registers with JTA.  You should not normally set this attribute. Its purpose is to allow the name of the XAResource to be overridden when a store has been upgraded from an older release and the store contained prepared transactions. The generated name should be used in all other cases. "
      ::= { jdbcStoreEntry 7  }
   
   
   jdbcStoreDeletesPerStatementMaximum OBJECT-TYPE
      SYNTAX      Integer32
      MAX-ACCESS  read-only
      STATUS      current
      DESCRIPTION "The maximum number of table rows that are deleted per database call.    Applies only when a JDBC store does not use JDBC 3.0 batching to batch concurrent client requests.    The maximum deletes per statement has no effect on the maximum number of concurrent client requests.    For some databases, the JDBC store may choose a lower value than the one configured.   "
      ::= { jdbcStoreEntry 8  }
   
   
   jdbcStoreInsertsPerBatchMaximum OBJECT-TYPE
      SYNTAX      Integer32
      MAX-ACCESS  read-only
      STATUS      current
      DESCRIPTION "The maximum number of table rows that are inserted per database call.    When possible, a JDBC store uses JDBC 3.0 batching to batch concurrent client requests.    Both the maximum batch size for concurrent inserts and for concurrent writes are configurable.    To disable JDBC 3.0 batching, set the maximum batch size to 1.    The maximum batch size has no effect on the maximum number of concurrent client requests.   "
      ::= { jdbcStoreEntry 9  }
   
   
   jdbcStoreName OBJECT-TYPE
      SYNTAX      OCTET STRING
      MAX-ACCESS  read-only
      STATUS      current
      DESCRIPTION "The user-specified name of this MBean instance.  This name is included as one of the key properties in the MBean's javax.management.ObjectName:  Name=user-specified-name "
      ::= { jdbcStoreEntry 10  }
   
   
   jdbcStoreCreateTableDDLFile OBJECT-TYPE
      SYNTAX      OCTET STRING
      MAX-ACCESS  read-only
      STATUS      current
      DESCRIPTION "Specifies the DDL (Data Definition Language) file to use for creating the JDBC store's backing table.    This field is ignored when the JDBC store's backing table, WLStore, already exists.    If a DDL file is not specified and the JDBC store detects that a backing table doesn't already exist, the JDBC store automatically creates the table by executing a preconfigured DDL file that is specific to the database vendor. These preconfigured files are located in the  weblogic\store\io\jdbc\ddl directory of the MIDDLEWARE_HOME\modules\com.bea.core.store.jdbc_x.x.x.x.jar file.    If a DDL file is specified and the JDBC store detects that a backing table doesn't already exist, then the JDBC store searches for the DDL file in the file path first, and then if the file is not found, it searches for it in the CLASSPATH. Once found, the SQL within the DDL file is executed to create the JDBC store's database table. If the DDL file is not found and the backing table doesn't already exist, the JDBC store will fail to boot.   "
      ::= { jdbcStoreEntry 11  }
   
   
   jdbcStorePrefixName OBJECT-TYPE
      SYNTAX      OCTET STRING
      MAX-ACCESS  read-only
      STATUS      current
      DESCRIPTION "The prefix for the JDBC store's database table (WLStore), in the following format: [[[catalog.]schema.]prefix].  Each period symbol in the [[catalog.]schema.]prefix format is significant, where schema generally corresponds to username in many databases. When no prefix is specified, the JDBC store table name is simply WLStore and the database implicitly determines the schema according to the JDBC connection's user. As a best practice, you should always configure a prefix for the JDBC WLStore table name.  For specific guidelines about using JDBC store prefixes, refer to the 'Using the WebLogic Store' section of Designing and Configuring WebLogic Server Environments'. "
      ::= { jdbcStoreEntry 12  }
   
   
   jdbcStoreWorkerPreferredBatchSize OBJECT-TYPE
      SYNTAX      INTEGER
      MAX-ACCESS  read-only
      STATUS      current
      DESCRIPTION "Specifies the batch size when the Worker Count attribute is configured to a value greater than 1. Used to configure the workload the JDBC store incrementally puts on each worker thread. The workload consists of IO requests which are grouped and pushed to each JDBC worker thread for processing. If the IO request is very large (for example 1M), then tune this attribute to a smaller value. "
      ::= { jdbcStoreEntry 13  }
   
   
   jdbcStoreWorkerCount OBJECT-TYPE
      SYNTAX      INTEGER
      MAX-ACCESS  read-only
      STATUS      current
      DESCRIPTION "The number of JDBC store worker threads to process the workerload.  A value of 1 indicates a single thread is used (the default). A value greater than 1 indicates that multiple threads are used. For Oracle databases, Oracle recommends users rebuild the primary key index into a reverse index for the JDBC Store table when the worker count is greater than 1. For non-Oracle databases, refer to the database provider's documentation for help with indexing.  "
      ::= { jdbcStoreEntry 14  }
   
   
   jdbcStoreThreeStepThreshold OBJECT-TYPE
      SYNTAX      INTEGER
      MAX-ACCESS  read-only
      STATUS      current
      DESCRIPTION "Specifies the threshold, in bytes, when the JDBC store uses 3 steps (insert, select, populate) instead of 1 step (insert) to populate an Oracle Blob data type.  Applies only to Oracle databases where a Blob data type is used instead of the default Long Raw data type for record data.  The default value is 200000. "
      ::= { jdbcStoreEntry 15  }
   
   
   jdbcStoreOraclePiggybackCommitEnabled OBJECT-TYPE
      SYNTAX      OCTET STRING
      MAX-ACCESS  read-only
      STATUS      current
      DESCRIPTION "Enables committing a batch of INSERT or DELETE operations with the last operation of the transaction instead of issuing a separate commit call to database server which saves a server round trip. This feature benefits applications that have many transactions of a small number of operations or small messages. "
      ::= { jdbcStoreEntry 16  }
   
   
   jdbcStorePartialClusterStabilityDelaySeconds OBJECT-TYPE
      SYNTAX      Counter64
      MAX-ACCESS  read-only
      STATUS      current
      DESCRIPTION "Specifies the amount of time, in seconds, to delay before a partially started cluster starts all cluster-targeted JMS artifact instances that are configured with a Migration Policy of Always or On-Failure.   Before this timeout expires or all servers are running, a cluster starts a subset of such instances based on the total number of servers running and the configured cluster size. Once the timeout expires or all servers have started, the system considers the cluster stable and starts any remaining services.  This delay ensures that services are balanced across a cluster even if the servers are started sequentially. It is ignored after a cluster is fully started (stable) or when individual servers are started.   A value > 0 specifies the time, in seconds, to delay before a partially started cluster starts dynamically configured services. A value of 0 specifies no delay.  "
      ::= { jdbcStoreEntry 17  }
   
   
   jdbcStoreRestartInPlace OBJECT-TYPE
      SYNTAX      OCTET STRING
      MAX-ACCESS  read-only
      STATUS      current
      DESCRIPTION " Enables a periodic automatic in-place restart of failed cluster-targeted or standalone-server-targeted JMS artifact instance(s) running on healthy WebLogic Server instances. See the migratable target settings for in-place restarts of migratable-targeted JMS artifacts. When the Restart In Place setting is configured on a store, it applies to all JMS artifacts that reference the store.    If the Migration Policy of the JMS artifact is set to Off, Restart In Place is disabled by default.  If the Migration Policy of the JMS artifact is set to On-Failure or Always, Restart In Place is enabled by default.  This attribute is not used by WebLogic messaging bridges which automatically restart internal connections as needed.  For a JMS artifact that is cluster-targeted and the Migration Policy is set to On-Failure or Always, if restart fails after the configured maximum retry attempts, it will migrate to a different server within the cluster.    "
      ::= { jdbcStoreEntry 18  }
   
   
   jdbcStoreNumberOfRestartAttempts OBJECT-TYPE
      SYNTAX      INTEGER
      MAX-ACCESS  read-only
      STATUS      current
      DESCRIPTION "Specifies the maximum number of restart attempts.   A value > 0 specifies the maximum number of restart attempts. A value of 0 specifies the same behavior as setting {@link #getRestartInPlace} to false. A value of -1 means infinite retry restart until it either starts or the server instance shuts down.  "
      ::= { jdbcStoreEntry 19  }
   
   
   jdbcStoreSecondsBetweenRestarts OBJECT-TYPE
      SYNTAX      INTEGER
      MAX-ACCESS  read-only
      STATUS      current
      DESCRIPTION "Specifies the amount of time, in seconds, to wait in between attempts to restart a failed service instance. "
      ::= { jdbcStoreEntry 20  }
   
   
   jdbcStoreDistributionPolicy OBJECT-TYPE
      SYNTAX      OCTET STRING
      MAX-ACCESS  read-only
      STATUS      current
      DESCRIPTION "Specifies how the instances of a configured JMS artifact are named and distributed when cluster-targeted.  A JMS artifact is cluster-targeted when its target is directly set to a cluster, or when it is scoped to a resource group and the resource group is in turn targeted to a cluster.  When this setting is configured on a store, it applies to all JMS artifacts that reference the store.  Valid options:   Distributed Creates an instance on each server JVM in a cluster. Required for all SAF agents and for cluster-targeted or resource-group-scoped JMS servers that host distributed destinations.    Singleton Creates a single instance on a single server JVM within a cluster. Required for cluster-targeted or resource-group-scoped JMS servers that host standalone (non-distributed) destinations and for cluster-targeted or resource-group-scoped path services.  The Migration Policy must be On-Failure or Always when using this option with a JMS server, On-Failure when using this option with a messaging bridge, and Always when using this option with a path service.    Instance Naming Note:   The DistributionPolicy determines the instance name suffix for cluster-targeted JMS artifacts.  The suffix for a cluster-targeted Singleton is -01 and for a cluster-targeted Distributed is @ClusterMemberName.    Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   If you cannot cluster-target a bridge and still need singleton behavior in a configured cluster, you can target the bridge to a migratable target and configure the Migration Policy on the migratable target to Exactly-Once.   "
      ::= { jdbcStoreEntry 21  }
   
   
   jdbcStoreTags OBJECT-TYPE
      SYNTAX      OCTET STRING
      MAX-ACCESS  read-only
      STATUS      current
      DESCRIPTION "Return all tags on this Configuration MBean "
      ::= { jdbcStoreEntry 22  }
   
   
   jdbcStoreMigrationPolicy OBJECT-TYPE
      SYNTAX      OCTET STRING
      MAX-ACCESS  read-only
      STATUS      current
      DESCRIPTION "Controls migration and restart behavior of cluster-targeted JMS service artifact instances. When this setting is configured on a cluster-targeted store, it applies to all JMS artifacts that reference the store. See the migratable target settings for enabling migration and restart on migratable-targeted JMS artifacts.  Off Disables migration support for cluster-targeted JMS service objects, and changes the default for Restart In Place to false. If you want a restart to be enabled when the Migration Policy is Off, then Restart In Place must be explicitly configured to true. This policy cannot be combined with the Singleton Migration Policy.  On-Failure Enables automatic migration and restart of instances on the failure of a subsystem Service or WebLogic Server instance, including automatic fail-back and load balancing of instances.   Always Provides the same behavior as On-Failure and automatically migrates instances even in the event of a graceful shutdown or a partial cluster start.   Note: Cluster leasing must be configured for On-Failure and Always.  Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   A Migration Policy of Always is not recommended for bridges.   If you cannot cluster-target a bridge and still need singleton behavior in a configured cluster, you can target the bridge to a migratable target and configure the Migration Policy on the migratable target to Exactly-Once.   "
      ::= { jdbcStoreEntry 23  }
   
   
   jdbcStoreReconnectRetryPeriodMillis OBJECT-TYPE
      SYNTAX      INTEGER
      MAX-ACCESS  read-only
      STATUS      current
      DESCRIPTION "Returns the length of time in milliseconds during which the persistent store will attempt to re-establish a connection to the database.  Successive reconnection attempts will be attempted after a fixed delay that is specified by the reconnection retry interval.  The reconnection period applies to JDBC connections regardless of the database that is used for the JDBC store.  The default value is 1000 "
      ::= { jdbcStoreEntry 24  }
   
   
   jdbcStoreFailbackDelaySeconds OBJECT-TYPE
      SYNTAX      Counter64
      MAX-ACCESS  read-only
      STATUS      current
      DESCRIPTION "Specifies the amount of time, in seconds, to delay before failing a cluster-targeted JMS artifact instance back to its preferred server after the preferred server failed and was restarted.  This delay allows time for the system to stabilize and dependent services to be restarted, preventing a system failure during a reboot.   A value > 0 specifies the time, in seconds, to delay before failing a JMS artifact back to its user preferred server. A value of 0 indicates that the instance would never failback. A value of -1 indicates that there is no delay and the instance would failback immediately.   Note: This setting only applies when the JMS artifact is cluster-targeted and the Migration Policy is set to On-Failure or Always. "
      ::= { jdbcStoreEntry 25  }
   
   
   jdbcStoreInitialBootDelaySeconds OBJECT-TYPE
      SYNTAX      Counter64
      MAX-ACCESS  read-only
      STATUS      current
      DESCRIPTION "Specifies the amount of time, in seconds, to delay before starting a cluster-targeted JMS instance on a newly booted WebLogic Server instance. When this setting is configured on a store, it applies to all JMS artifacts that reference the store.  This allows time for the system to stabilize and dependent services to be restarted, preventing a system failure during a reboot.   A value > 0 is the time, in seconds, to delay before before loading resources after a failure and restart. A value of 0 specifies no delay.  Note: This setting only applies when the JMS artifact is cluster-targeted and the Migration Policy is set to On-Failure or Always. "
      ::= { jdbcStoreEntry 26  }
   
   
   jdbcStoreReconnectRetryIntervalMillis OBJECT-TYPE
      SYNTAX      INTEGER
      MAX-ACCESS  read-only
      STATUS      current
      DESCRIPTION "The length of time in milliseconds between reconnection attempts during the reconnection retry period.  The reconnection interval applies to JDBC connections regardless of the database that is used for the JDBC store.  The default value is 200 milliseconds "
      ::= { jdbcStoreEntry 27  }
   
   
   jdbcStoreConnectionCachingPolicy OBJECT-TYPE
      SYNTAX      OCTET STRING
      MAX-ACCESS  read-only
      STATUS      current
      DESCRIPTION "Advanced use only: gets the connection caching policy for the JDBC store.  The return values will be one of:  JMSConstants.JDBCSTORE_CONNECTION_CACHING_POLICY_DEFAULT (&quot;DEFAULT&quot;) JMSConstants.JDBCSTORE_CONNECTION_CACHING_POLICY_MINIMAL (&quot;MINIMAL&quot;) JMSConstants.JDBCSTORE_CONNECTION_CACHING_POLICY_NONE (&quot;NONE&quot;)   IMPORTANT: See the below for additional usage information, particularly regarding NONE  DEFAULT The default mode of operation for the JDBC store.  The JDBC store will open two connections to the database and it will keep these connections open for the life of the store. In addition, if the worker count for the store is two or more, then it will open one connection for each of the workers and those connections will also stay open for the life of the JDBC store.  If the worker count is 3 then the JDBC store will use 5 database connections.  If the worker count is the default of 1 then the JDBC store will use just 2 connections.The DEFAULT setting is the recommended setting to be used when the database backing the JDBC store is not constrained with respect to the number of open connections.  MINIMAL The JDBC store will open one connection to the database and it will keep that connection open for the life of the store. In addition, if the worker count for the store is two or more, then it will open one connection for each of the workers and those connections will also stay open for the life of the JDBC store. If the worker count is 3 then the JDBC store will use 4 database connections. If the worker count is the default of 1 then the JDBC store will use just 1 connection. The MINIMAL setting may result in a slight reduction of through-put for low concurrency messaging scenarios in comparison to DEFAULT.  NONE The NONE connection caching policy is for 'advanced usage only'. The JDBC store will open one connection to the database on an as-needed basis to perform I/O and it will release that connection when the operation is complete. The NONE value is not compatible with a configured worker count of 2 or more and will result in a configuration validation exception. The NONE setting may result in a slight reduction of through-put for low concurrency messaging scenarios in comparison to DEFAULT or MINIMAL.  NOTE: It is strongly recommended that a JDBC store be configured with a dedicated data source when the store is configured with the NONE connection caching policy.  A store that shares a data source with other non-store components or applications runs the risk of failing due to dead-locks.  Please note that a JDBC store will require more than one connection when first started. As such, a data source should be configured to grow and shrink so that the JDBC store can initialize. "
      ::= { jdbcStoreEntry 28  }
   
   
   jdbcStoreFailOverLimit OBJECT-TYPE
      SYNTAX      INTEGER
      MAX-ACCESS  read-only
      STATUS      current
      DESCRIPTION "Specify a limit for the number of cluster-targeted JMS artifact instances that can fail over to a particular JVM.  This can be used to prevent too many instances from starting on a server, avoiding a system failure when starting too few servers of a formerly large cluster.  A typical limit value should allow all instances to run in the smallest desired cluster size, which means (smallest-cluster-size * (limit + 1)) should equal or exceed the total number of instances.    A value of -1 means there is no fail over limit (unlimited). A value of 0 prevents any fail overs of cluster-targeted JMS artifact instances, so no more than 1 instance will run per server (this is an instance that has not failed over). A value of 1 allows one fail-over instance on each server, so no more than two instances will run per server (one failed over instance plus an instance that has not failed over).   Note: This setting only applies when the JMS artifact is cluster-targeted and the Migration Policy is set to On-Failure or Always. "
      ::= { jdbcStoreEntry 29  }
   
   
   jdbcSystemResourceTable OBJECT-TYPE
      SYNTAX      SEQUENCE OF JdbcSystemResourceEntry
      MAX-ACCESS  not-accessible
      STATUS      current
      DESCRIPTION "This bean defines a system-level JDBC resource.  It links a separate descriptor that specifies the definition. "
      ::= { wls 955  }
      
   
   jdbcSystemResourceEntry OBJECT-TYPE
      SYNTAX      JdbcSystemResourceEntry
      MAX-ACCESS  not-accessible
      STATUS      current
      DESCRIPTION "Generated SNMP Table Entry."
      INDEX { jdbcSystemResourceIndex}
      ::= { jdbcSystemResourceTable 1 }
      
   JdbcSystemResourceEntry ::=
      SEQUENCE
      {
         jdbcSystemResourceIndex OCTET STRING,
         jdbcSystemResourceObjectName OCTET STRING,
         jdbcSystemResourceType OCTET STRING,
         jdbcSystemResourceCompatibilityName OCTET STRING,
         jdbcSystemResourceDeploymentOrder Integer32,
         jdbcSystemResourceDeploymentPrincipalName OCTET STRING,
         jdbcSystemResourceDescriptorFileName OCTET STRING,
         jdbcSystemResourceModuleType OCTET STRING,
         jdbcSystemResourceName OCTET STRING,
         jdbcSystemResourceSourcePath OCTET STRING,
         jdbcSystemResourceTags OCTET STRING
      }
      
   
   jdbcSystemResourceIndex OBJECT-TYPE
      SYNTAX      OCTET STRING
      MAX-ACCESS  not-accessible
      STATUS      current
      DESCRIPTION "Index column"
      ::= { jdbcSystemResourceEntry 1  }
   
   
   jdbcSystemResourceObjectName OBJECT-TYPE
      SYNTAX      OCTET STRING
      MAX-ACCESS  read-only
      STATUS      current
      DESCRIPTION "ObjectName column"
      ::= { jdbcSystemResourceEntry 2  }
   
   
   jdbcSystemResourceType OBJECT-TYPE
      SYNTAX      OCTET STRING
      MAX-ACCESS  read-only
      STATUS      current
      DESCRIPTION "Returns the type of the MBean. "
      ::= { jdbcSystemResourceEntry 3  }
   
   
   jdbcSystemResourceCompatibilityName OBJECT-TYPE
      SYNTAX      OCTET STRING
      MAX-ACCESS  read-only
      STATUS      current
      DESCRIPTION " This is only set for beans created as a result of conversion from an 8.1 application configured using ApplicationMBean and ComponentMBean.  Standalone modules in 8.1 have both an ApplicationMBean name and ComponentMBean name. This attribute stores the name of the latter, to be used when the server creates the transient ComponentMBean for backward compatibility. "
      ::= { jdbcSystemResourceEntry 4  }
   
   
   jdbcSystemResourceDeploymentOrder OBJECT-TYPE
      SYNTAX      Integer32
      MAX-ACCESS  read-only
      STATUS      current
      DESCRIPTION "An integer value that indicates when this unit is deployed, relative to other deployable units on a server, during startup.  Units with lower values are deployed before those with higher values. "
      ::= { jdbcSystemResourceEntry 5  }
   
   
   jdbcSystemResourceDeploymentPrincipalName OBJECT-TYPE
      SYNTAX      OCTET STRING
      MAX-ACCESS  read-only
      STATUS      current
      DESCRIPTION "A string value that indicates the principal that should be used when deploying the file or archive during startup and shutdown. This principal will be used to set the current subject when calling out into application code for interfaces such as ApplicationLifecycleListener. If no principal name is specified, then the anonymous principal will be used. "
      ::= { jdbcSystemResourceEntry 6  }
   
   
   jdbcSystemResourceDescriptorFileName OBJECT-TYPE
      SYNTAX      OCTET STRING
      MAX-ACCESS  read-only
      STATUS      current
      DESCRIPTION "The name of the file containing this configuration.  This is a relative name rooted at DOMAIN_DIR/config.  By default the file resides in the jdbc subdirectory and derives its name from the bean name using the following pattern:  &lt;beanName&gt;.xml  Note that this is a read-only property that can only be set when the bean is created. "
      ::= { jdbcSystemResourceEntry 7  }
   
   
   jdbcSystemResourceModuleType OBJECT-TYPE
      SYNTAX      OCTET STRING
      MAX-ACCESS  read-only
      STATUS      current
      DESCRIPTION "The values match those defined by jsr88. This attribute may move to another MBean. "
      ::= { jdbcSystemResourceEntry 8  }
   
   
   jdbcSystemResourceName OBJECT-TYPE
      SYNTAX      OCTET STRING
      MAX-ACCESS  read-only
      STATUS      current
      DESCRIPTION "The user-specified name of this MBean instance.  This name is included as one of the key properties in the MBean's javax.management.ObjectName:  Name=user-specified-name "
      ::= { jdbcSystemResourceEntry 9  }
   
   
   jdbcSystemResourceSourcePath OBJECT-TYPE
      SYNTAX      OCTET STRING
      MAX-ACCESS  read-only
      STATUS      current
      DESCRIPTION " "
      ::= { jdbcSystemResourceEntry 10  }
   
   
   jdbcSystemResourceTags OBJECT-TYPE
      SYNTAX      OCTET STRING
      MAX-ACCESS  read-only
      STATUS      current
      DESCRIPTION "Return all tags on this Configuration MBean "
      ::= { jdbcSystemResourceEntry 11  }
   
   
   jmsInteropModuleTable OBJECT-TYPE
      SYNTAX      SEQUENCE OF JmsInteropModuleEntry
      MAX-ACCESS  not-accessible
      STATUS      current
      DESCRIPTION "This bean defines a system-level JMS resource.  It links a separate descriptor that specifies the definition. "
      ::= { wls 960  }
      
   
   jmsInteropModuleEntry OBJECT-TYPE
      SYNTAX      JmsInteropModuleEntry
      MAX-ACCESS  not-accessible
      STATUS      current
      DESCRIPTION "Generated SNMP Table Entry."
      INDEX { jmsInteropModuleIndex}
      ::= { jmsInteropModuleTable 1 }
      
   JmsInteropModuleEntry ::=
      SEQUENCE
      {
         jmsInteropModuleIndex OCTET STRING,
         jmsInteropModuleObjectName OCTET STRING,
         jmsInteropModuleType OCTET STRING,
         jmsInteropModuleCompatibilityName OCTET STRING,
         jmsInteropModuleDeploymentOrder Integer32,
         jmsInteropModuleDeploymentPrincipalName OCTET STRING,
         jmsInteropModuleDescriptorFileName OCTET STRING,
         jmsInteropModuleModuleType OCTET STRING,
         jmsInteropModuleName OCTET STRING,
         jmsInteropModuleSourcePath OCTET STRING,
         jmsInteropModuleTags OCTET STRING
      }
      
   
   jmsInteropModuleIndex OBJECT-TYPE
      SYNTAX      OCTET STRING
      MAX-ACCESS  not-accessible
      STATUS      current
      DESCRIPTION "Index column"
      ::= { jmsInteropModuleEntry 1  }
   
   
   jmsInteropModuleObjectName OBJECT-TYPE
      SYNTAX      OCTET STRING
      MAX-ACCESS  read-only
      STATUS      current
      DESCRIPTION "ObjectName column"
      ::= { jmsInteropModuleEntry 2  }
   
   
   jmsInteropModuleType OBJECT-TYPE
      SYNTAX      OCTET STRING
      MAX-ACCESS  read-only
      STATUS      current
      DESCRIPTION "Returns the type of the MBean. "
      ::= { jmsInteropModuleEntry 3  }
   
   
   jmsInteropModuleCompatibilityName OBJECT-TYPE
      SYNTAX      OCTET STRING
      MAX-ACCESS  read-only
      STATUS      current
      DESCRIPTION " This is only set for beans created as a result of conversion from an 8.1 application configured using ApplicationMBean and ComponentMBean.  Standalone modules in 8.1 have both an ApplicationMBean name and ComponentMBean name. This attribute stores the name of the latter, to be used when the server creates the transient ComponentMBean for backward compatibility. "
      ::= { jmsInteropModuleEntry 4  }
   
   
   jmsInteropModuleDeploymentOrder OBJECT-TYPE
      SYNTAX      Integer32
      MAX-ACCESS  read-only
      STATUS      current
      DESCRIPTION "An integer value that indicates when this unit is deployed, relative to other deployable units on a server, during startup.  Units with lower values are deployed before those with higher values. "
      ::= { jmsInteropModuleEntry 5  }
   
   
   jmsInteropModuleDeploymentPrincipalName OBJECT-TYPE
      SYNTAX      OCTET STRING
      MAX-ACCESS  read-only
      STATUS      current
      DESCRIPTION "A string value that indicates the principal that should be used when deploying the file or archive during startup and shutdown. This principal will be used to set the current subject when calling out into application code for interfaces such as ApplicationLifecycleListener. If no principal name is specified, then the anonymous principal will be used. "
      ::= { jmsInteropModuleEntry 6  }
   
   
   jmsInteropModuleDescriptorFileName OBJECT-TYPE
      SYNTAX      OCTET STRING
      MAX-ACCESS  read-only
      STATUS      current
      DESCRIPTION "The name of the file that contains the module configuration. By default the file resides in the DOMAIN_DIR/config/jms directory. The module file derives its name from the bean name using the following pattern:  &lt;beanName&gt;.xml  Note that this is a read-only property that can only be set when the bean is created. "
      ::= { jmsInteropModuleEntry 7  }
   
   
   jmsInteropModuleModuleType OBJECT-TYPE
      SYNTAX      OCTET STRING
      MAX-ACCESS  read-only
      STATUS      current
      DESCRIPTION "The values match those defined by jsr88. This attribute may move to another MBean. "
      ::= { jmsInteropModuleEntry 8  }
   
   
   jmsInteropModuleName OBJECT-TYPE
      SYNTAX      OCTET STRING
      MAX-ACCESS  read-only
      STATUS      current
      DESCRIPTION "The user-specified name of this MBean instance.  This name is included as one of the key properties in the MBean's javax.management.ObjectName:  Name=user-specified-name "
      ::= { jmsInteropModuleEntry 9  }
   
   
   jmsInteropModuleSourcePath OBJECT-TYPE
      SYNTAX      OCTET STRING
      MAX-ACCESS  read-only
      STATUS      current
      DESCRIPTION " "
      ::= { jmsInteropModuleEntry 10  }
   
   
   jmsInteropModuleTags OBJECT-TYPE
      SYNTAX      OCTET STRING
      MAX-ACCESS  read-only
      STATUS      current
      DESCRIPTION "Return all tags on this Configuration MBean "
      ::= { jmsInteropModuleEntry 11  }
   
   
   jmsMessageLogFileTable OBJECT-TYPE
      SYNTAX      SEQUENCE OF JmsMessageLogFileEntry
      MAX-ACCESS  not-accessible
      STATUS      current
      DESCRIPTION "This defines the configuration aspects of the logs for a jms server. "
      ::= { wls 965  }
      
   
   jmsMessageLogFileEntry OBJECT-TYPE
      SYNTAX      JmsMessageLogFileEntry
      MAX-ACCESS  not-accessible
      STATUS      current
      DESCRIPTION "Generated SNMP Table Entry."
      INDEX { jmsMessageLogFileIndex}
      ::= { jmsMessageLogFileTable 1 }
      
   JmsMessageLogFileEntry ::=
      SEQUENCE
      {
         jmsMessageLogFileIndex OCTET STRING,
         jmsMessageLogFileObjectName OCTET STRING,
         jmsMessageLogFileType OCTET STRING,
         jmsMessageLogFileNumberOfFilesLimited OCTET STRING,
         jmsMessageLogFileFileTimeSpan Integer32,
         jmsMessageLogFileRotationType OCTET STRING,
         jmsMessageLogFileFileCount Integer32,
         jmsMessageLogFileFileName OCTET STRING,
         jmsMessageLogFileFileMinSize Integer32,
         jmsMessageLogFileBufferSizeKB Integer32,
         jmsMessageLogFileDateFormatPattern OCTET STRING,
         jmsMessageLogFileRotationTime OCTET STRING,
         jmsMessageLogFileRotateLogOnStartup OCTET STRING,
         jmsMessageLogFileName OCTET STRING,
         jmsMessageLogFileLogFileRotationDir OCTET STRING,
         jmsMessageLogFileTags OCTET STRING
      }
      
   
   jmsMessageLogFileIndex OBJECT-TYPE
      SYNTAX      OCTET STRING
      MAX-ACCESS  not-accessible
      STATUS      current
      DESCRIPTION "Index column"
      ::= { jmsMessageLogFileEntry 1  }
   
   
   jmsMessageLogFileObjectName OBJECT-TYPE
      SYNTAX      OCTET STRING
      MAX-ACCESS  read-only
      STATUS      current
      DESCRIPTION "ObjectName column"
      ::= { jmsMessageLogFileEntry 2  }
   
   
   jmsMessageLogFileType OBJECT-TYPE
      SYNTAX      OCTET STRING
      MAX-ACCESS  read-only
      STATUS      current
      DESCRIPTION "Returns the type of the MBean. "
      ::= { jmsMessageLogFileEntry 3  }
   
   
   jmsMessageLogFileNumberOfFilesLimited OBJECT-TYPE
      SYNTAX      OCTET STRING
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require. "
      ::= { jmsMessageLogFileEntry 4  }
   
   
   jmsMessageLogFileFileTimeSpan OBJECT-TYPE
      SYNTAX      Integer32
      MAX-ACCESS  read-only
      STATUS      current
      DESCRIPTION "The interval (in hours) at which the server saves old log messages to another file. (Requires that you specify a file rotation type of TIME.) "
      ::= { jmsMessageLogFileEntry 5  }
   
   
   jmsMessageLogFileRotationType OBJECT-TYPE
      SYNTAX      OCTET STRING
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as SERVER_NAME.lognnnnn.  TIME At each time interval that you specify in TimeSpan, the server renames the file as SERVER_NAME.lognnnnn.   After the server renames a file, subsequent messages accumulate in a new file with the name that you specified as the log file name. "
      ::= { jmsMessageLogFileEntry 6  }
   
   
   jmsMessageLogFileFileCount OBJECT-TYPE
      SYNTAX      Integer32
      MAX-ACCESS  read-only
      STATUS      current
      DESCRIPTION "The maximum number of log files that the server creates when it rotates the log. This number does not include the file that the server uses to store current messages. (Requires that you enable Number of Files Limited.) "
      ::= { jmsMessageLogFileEntry 7  }
   
   
   jmsMessageLogFileFileName OBJECT-TYPE
      SYNTAX      OCTET STRING
      MAX-ACCESS  read-only
      STATUS      current
      DESCRIPTION "The name of the file that stores current JMS server log messages. Usually it is a computed value based on the name of the parent of this MBean. For example, for a JMS server log, it is jmsserverName.log.  However, if the name of the parent cannot be obtained, the file name is weblogic.log. If you specify a relative pathname, it is interpreted as relative to the server's root directory.  To include a time and date stamp in the file name when the log file is rotated, add java.text.SimpleDateFormat variables to the file name. Surround each variable with percentage (%) characters.  For example, if the file name is defined to be myjmsserver_%yyyy%_%MM%_%dd%_%hh%_%mm%.log, the log file will be named myserver_yyyy_mm_dd_hh_mm.log.  When the log file is rotated, the rotated file name contains the date stamp. For example, if the log file is rotated on 2 April, 2005 at 10:05 AM, the log file that contains the old messages will be named myserver_2005_04_02_10_05.log.  If you do not include a time and date stamp, the rotated log files are numbered in order of creation. For example, myjmsserver.log00007. "
      ::= { jmsMessageLogFileEntry 8  }
   
   
   jmsMessageLogFileFileMinSize OBJECT-TYPE
      SYNTAX      Integer32
      MAX-ACCESS  read-only
      STATUS      current
      DESCRIPTION "The size (1 - 2097150 kilobytes) that triggers the server to move log messages to a separate file. The default is 500 kilobytes. After the log file reaches the specified minimum size, the next time the server checks the file size, it will rename the current log file as SERVER_NAME.lognnnnn and create a new one to store subsequent messages. (Requires that you specify a file rotation type of Size.) "
      ::= { jmsMessageLogFileEntry 9  }
   
   
   jmsMessageLogFileBufferSizeKB OBJECT-TYPE
      SYNTAX      Integer32
      MAX-ACCESS  read-only
      STATUS      current
      DESCRIPTION "Gets the underlying log buffer size in kilobytes "
      ::= { jmsMessageLogFileEntry 10  }
   
   
   jmsMessageLogFileDateFormatPattern OBJECT-TYPE
      SYNTAX      OCTET STRING
      MAX-ACCESS  read-only
      STATUS      current
      DESCRIPTION "The date format pattern used for rendering dates in the  log. The DateFormatPattern string conforms to the specification of the java.text.SimpleDateFormat class. "
      ::= { jmsMessageLogFileEntry 11  }
   
   
   jmsMessageLogFileRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  Note that WebLogic Server sets a threshold size limit of 500 MB before it forces a hard rotation to prevent excessive log file growth.  Use the following format: H:mm, where  H is Hour in day (0-23) mm is the minute in hour  "
      ::= { jmsMessageLogFileEntry 12  }
   
   
   jmsMessageLogFileRotateLogOnStartup OBJECT-TYPE
      SYNTAX      OCTET STRING
      MAX-ACCESS  read-only
      STATUS      current
      DESCRIPTION "Specifies whether a server rotates its log file during its startup cycle. The default value in production mode is false. "
      ::= { jmsMessageLogFileEntry 13  }
   
   
   jmsMessageLogFileName OBJECT-TYPE
      SYNTAX      OCTET STRING
      MAX-ACCESS  read-only
      STATUS      current
      DESCRIPTION "The user-specified name of this MBean instance.  This name is included as one of the key properties in the MBean's javax.management.ObjectName:  Name=user-specified-name "
      ::= { jmsMessageLogFileEntry 14  }
   
   
   jmsMessageLogFileLogFileRotationDir OBJECT-TYPE
      SYNTAX      OCTET STRING
      MAX-ACCESS  read-only
      STATUS      current
      DESCRIPTION "The directory where the rotated log files will be stored. By default the rotated files are stored in the same directory where the log file is stored. "
      ::= { jmsMessageLogFileEntry 15  }
   
   
   jmsMessageLogFileTags OBJECT-TYPE
      SYNTAX      OCTET STRING
      MAX-ACCESS  read-only
      STATUS      current
      DESCRIPTION "Return all tags on this Configuration MBean "
      ::= { jmsMessageLogFileEntry 16  }
   
   
   jmsSAFMessageLogFileTable OBJECT-TYPE
      SYNTAX      SEQUENCE OF JmsSAFMessageLogFileEntry
      MAX-ACCESS  not-accessible
      STATUS      current
      DESCRIPTION "This defines the configuration aspects of the logs for a jms server. "
      ::= { wls 970  }
      
   
   jmsSAFMessageLogFileEntry OBJECT-TYPE
      SYNTAX      JmsSAFMessageLogFileEntry
      MAX-ACCESS  not-accessible
      STATUS      current
      DESCRIPTION "Generated SNMP Table Entry."
      INDEX { jmsSAFMessageLogFileIndex}
      ::= { jmsSAFMessageLogFileTable 1 }
      
   JmsSAFMessageLogFileEntry ::=
      SEQUENCE
      {
         jmsSAFMessageLogFileIndex OCTET STRING,
         jmsSAFMessageLogFileObjectName OCTET STRING,
         jmsSAFMessageLogFileType OCTET STRING,
         jmsSAFMessageLogFileNumberOfFilesLimited OCTET STRING,
         jmsSAFMessageLogFileFileTimeSpan Integer32,
         jmsSAFMessageLogFileRotationType OCTET STRING,
         jmsSAFMessageLogFileFileCount Integer32,
         jmsSAFMessageLogFileFileName OCTET STRING,
         jmsSAFMessageLogFileFileMinSize Integer32,
         jmsSAFMessageLogFileBufferSizeKB Integer32,
         jmsSAFMessageLogFileDateFormatPattern OCTET STRING,
         jmsSAFMessageLogFileRotationTime OCTET STRING,
         jmsSAFMessageLogFileRotateLogOnStartup OCTET STRING,
         jmsSAFMessageLogFileName OCTET STRING,
         jmsSAFMessageLogFileLogFileRotationDir OCTET STRING,
         jmsSAFMessageLogFileTags OCTET STRING
      }
      
   
   jmsSAFMessageLogFileIndex OBJECT-TYPE
      SYNTAX      OCTET STRING
      MAX-ACCESS  not-accessible
      STATUS      current
      DESCRIPTION "Index column"
      ::= { jmsSAFMessageLogFileEntry 1  }
   
   
   jmsSAFMessageLogFileObjectName OBJECT-TYPE
      SYNTAX      OCTET STRING
      MAX-ACCESS  read-only
      STATUS      current
      DESCRIPTION "ObjectName column"
      ::= { jmsSAFMessageLogFileEntry 2  }
   
   
   jmsSAFMessageLogFileType OBJECT-TYPE
      SYNTAX      OCTET STRING
      MAX-ACCESS  read-only
      STATUS      current
      DESCRIPTION "Returns the type of the MBean. "
      ::= { jmsSAFMessageLogFileEntry 3  }
   
   
   jmsSAFMessageLogFileNumberOfFilesLimited OBJECT-TYPE
      SYNTAX      OCTET STRING
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require. "
      ::= { jmsSAFMessageLogFileEntry 4  }
   
   
   jmsSAFMessageLogFileFileTimeSpan OBJECT-TYPE
      SYNTAX      Integer32
      MAX-ACCESS  read-only
      STATUS      current
      DESCRIPTION "The interval (in hours) at which the server saves old log messages to another file. (Requires that you specify a file rotation type of TIME.) "
      ::= { jmsSAFMessageLogFileEntry 5  }
   
   
   jmsSAFMessageLogFileRotationType OBJECT-TYPE
      SYNTAX      OCTET STRING
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as SERVER_NAME.lognnnnn.  TIME At each time interval that you specify in TimeSpan, the server renames the file as SERVER_NAME.lognnnnn.   After the server renames a file, subsequent messages accumulate in a new file with the name that you specified as the log file name. "
      ::= { jmsSAFMessageLogFileEntry 6  }
   
   
   jmsSAFMessageLogFileFileCount OBJECT-TYPE
      SYNTAX      Integer32
      MAX-ACCESS  read-only
      STATUS      current
      DESCRIPTION "The maximum number of log files that the server creates when it rotates the log. This number does not include the file that the server uses to store current messages. (Requires that you enable Number of Files Limited.) "
      ::= { jmsSAFMessageLogFileEntry 7  }
   
   
   jmsSAFMessageLogFileFileName OBJECT-TYPE
      SYNTAX      OCTET STRING
      MAX-ACCESS  read-only
      STATUS      current
      DESCRIPTION " "
      ::= { jmsSAFMessageLogFileEntry 8  }
   
   
   jmsSAFMessageLogFileFileMinSize OBJECT-TYPE
      SYNTAX      Integer32
      MAX-ACCESS  read-only
      STATUS      current
      DESCRIPTION "The size (1 - 2097150 kilobytes) that triggers the server to move log messages to a separate file. The default is 500 kilobytes. After the log file reaches the specified minimum size, the next time the server checks the file size, it will rename the current log file as SERVER_NAME.lognnnnn and create a new one to store subsequent messages. (Requires that you specify a file rotation type of Size.) "
      ::= { jmsSAFMessageLogFileEntry 9  }
   
   
   jmsSAFMessageLogFileBufferSizeKB OBJECT-TYPE
      SYNTAX      Integer32
      MAX-ACCESS  read-only
      STATUS      current
      DESCRIPTION "Gets the underlying log buffer size in kilobytes "
      ::= { jmsSAFMessageLogFileEntry 10  }
   
   
   jmsSAFMessageLogFileDateFormatPattern OBJECT-TYPE
      SYNTAX      OCTET STRING
      MAX-ACCESS  read-only
      STATUS      current
      DESCRIPTION "The date format pattern used for rendering dates in the  log. The DateFormatPattern string conforms to the specification of the java.text.SimpleDateFormat class. "
      ::= { jmsSAFMessageLogFileEntry 11  }
   
   
   jmsSAFMessageLogFileRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  Note that WebLogic Server sets a threshold size limit of 500 MB before it forces a hard rotation to prevent excessive log file growth.  Use the following format: H:mm, where  H is Hour in day (0-23) mm is the minute in hour  "
      ::= { jmsSAFMessageLogFileEntry 12  }
   
   
   jmsSAFMessageLogFileRotateLogOnStartup OBJECT-TYPE
      SYNTAX      OCTET STRING
      MAX-ACCESS  read-only
      STATUS      current
      DESCRIPTION "Specifies whether a server rotates its log file during its startup cycle. The default value in production mode is false. "
      ::= { jmsSAFMessageLogFileEntry 13  }
   
   
   jmsSAFMessageLogFileName OBJECT-TYPE
      SYNTAX      OCTET STRING
      MAX-ACCESS  read-only
      STATUS      current
      DESCRIPTION "The user-specified name of this MBean instance.  This name is included as one of the key properties in the MBean's javax.management.ObjectName:  Name=user-specified-name "
      ::= { jmsSAFMessageLogFileEntry 14  }
   
   
   jmsSAFMessageLogFileLogFileRotationDir OBJECT-TYPE
      SYNTAX      OCTET STRING
      MAX-ACCESS  read-only
      STATUS      current
      DESCRIPTION "The directory where the rotated log files will be stored. By default the rotated files are stored in the same directory where the log file is stored. "
      ::= { jmsSAFMessageLogFileEntry 15  }
   
   
   jmsSAFMessageLogFileTags OBJECT-TYPE
      SYNTAX      OCTET STRING
      MAX-ACCESS  read-only
      STATUS      current
      DESCRIPTION "Return all tags on this Configuration MBean "
      ::= { jmsSAFMessageLogFileEntry 16  }
   
   
   jmxTable OBJECT-TYPE
      SYNTAX      SEQUENCE OF JmxEntry
      MAX-ACCESS  not-accessible
      STATUS      current
      DESCRIPTION "Controls which JMX agents are initialized in the current WebLogic Server domain. Each JMX agent supports specific functions such as monitoring run-time statistics or modifying the domain's configuration. "
      ::= { wls 975  }
      
   
   jmxEntry OBJECT-TYPE
      SYNTAX      JmxEntry
      MAX-ACCESS  not-accessible
      STATUS      current
      DESCRIPTION "Generated SNMP Table Entry."
      INDEX { jmxIndex}
      ::= { jmxTable 1 }
      
   JmxEntry ::=
      SEQUENCE
      {
         jmxIndex             OCTET STRING,
         jmxObjectName        OCTET STRING,
         jmxType              OCTET STRING,
         jmxCompatibilityMBeanServerEnabled OCTET STRING,
         jmxManagementEJBEnabled OCTET STRING,
         jmxPlatformMBeanServerEnabled OCTET STRING,
         jmxInvocationTimeoutSeconds Integer32,
         jmxRuntimeMBeanServerEnabled OCTET STRING,
         jmxDomainMBeanServerEnabled OCTET STRING,
         jmxName              OCTET STRING,
         jmxEditMBeanServerEnabled OCTET STRING,
         jmxPlatformMBeanServerUsed OCTET STRING,
         jmxManagedServerNotificationsEnabled OCTET STRING,
         jmxTags              OCTET STRING,
         jmxManagementAppletCreateEnabled OCTET STRING
      }
      
   
   jmxIndex OBJECT-TYPE
      SYNTAX      OCTET STRING
      MAX-ACCESS  not-accessible
      STATUS      current
      DESCRIPTION "Index column"
      ::= { jmxEntry 1  }
   
   
   jmxObjectName OBJECT-TYPE
      SYNTAX      OCTET STRING
      MAX-ACCESS  read-only
      STATUS      current
      DESCRIPTION "ObjectName column"
      ::= { jmxEntry 2  }
   
   
   jmxType OBJECT-TYPE
      SYNTAX      OCTET STRING
      MAX-ACCESS  read-only
      STATUS      current
      DESCRIPTION "Returns the type of the MBean. "
      ::= { jmxEntry 3  }
   
   
   jmxCompatibilityMBeanServerEnabled OBJECT-TYPE
      SYNTAX      OCTET STRING
      MAX-ACCESS  read-only
      STATUS      current
      DESCRIPTION "Enables JMX clients to use the deprecated MBeanHome interface. Prior to 9.0, WebLogic Server supported a typed API layer over its JMX layer. Your JMX application classes could import type-safe interfaces for WebLogic Server MBeans, retrieve a reference to the MBeans through the weblogic.management.MBeanHome interface, and invoke the MBean methods directly. "
      ::= { jmxEntry 4  }
   
   
   jmxManagementEJBEnabled OBJECT-TYPE
      SYNTAX      OCTET STRING
      MAX-ACCESS  read-only
      STATUS      current
      DESCRIPTION "Enables access to the Management EJB (MEJB), which is part of the Java EE Management APIs (JSR-77).  The Management API specification provides a standardized management data model for common resources on Java EE Web application servers.  The MEJB provides access to Java EE Managed Objects (JMOs), which describe the common Java EE resources. If you set this attribute to false, WebLogic Server does not register the MEJB in the JNDI tree, and effectively disables the Java EE Management APIs for the domain. "
      ::= { jmxEntry 5  }
   
   
   jmxPlatformMBeanServerEnabled OBJECT-TYPE
      SYNTAX      OCTET STRING
      MAX-ACCESS  read-only
      STATUS      current
      DESCRIPTION "Specifies whether each server instance initializes the JDK's platform MBean server. Enabling it, along with isPlatformMBeanServerUsed, causes WebLogic Server to use the platform MBean server as its Runtime MBean Server.  As of JDK 1.5, JVMs provide a platform MBean server that local processes can instantiate. There can be only one instance of the platform MBean server for each JVM. When a process instantiates this MBean server, the JVM creates several platform MXBeans that provide monitoring data for the JVM itself.  If you set this attribute to true, each WebLogic Server instance invokes the method java.lang.management.ManagementFactory.getPlatformMBeanServer() and thus causes the initialization of the JVM's MXBeans. "
      ::= { jmxEntry 6  }
   
   
   jmxInvocationTimeoutSeconds OBJECT-TYPE
      SYNTAX      Integer32
      MAX-ACCESS  read-only
      STATUS      current
      DESCRIPTION "The number of seconds that internal WebLogic Server processes wait to connect to an MBean server, invoke an MBean server method, and return the results of the invocation. If the MBean server method does not complete (return) within the timeout period, WebLogic Server abandons its invocation attempt. Some internal management processes within WebLogic Server require a server instance to connect to MBean servers in other WebLogic Server instances and invoke an MBean server method. The timeout period prevents the internal process from locking up if an MBean server cannot successfully return a method invocation. A value of 0 (zero) prevents the method invocation from timing out. With such a value, the internal process will wait indefinitely until the MBean server's method returns.  "
      ::= { jmxEntry 7  }
   
   
   jmxRuntimeMBeanServerEnabled OBJECT-TYPE
      SYNTAX      OCTET STRING
      MAX-ACCESS  read-only
      STATUS      current
      DESCRIPTION "Specifies whether each server instance in the domain initializes its Runtime MBean Server, which provides access to a server's run-time MBeans and read-only configuration MBeans.  The Administration Console and the WebLogic Scripting Tool use this MBean server for some (but not all) of their read operations.  If RuntimeMBeanServerEnabled is true, each server starts its Runtime MBean Server during the server's startup cycle. If this attribute is false, no server instance in the domain will start its Runtime MBean Server. "
      ::= { jmxEntry 8  }
   
   
   jmxDomainMBeanServerEnabled OBJECT-TYPE
      SYNTAX      OCTET STRING
      MAX-ACCESS  read-only
      STATUS      current
      DESCRIPTION "Specifies whether the Administration Server initializes the Domain MBean Server, which provides federated access to all run-time MBeans and read-only configuration MBeans in the domain. Through it, JMX clients can access all MBeans in a domain through a single connection.  The Administration Console and the WebLogic Scripting Tool use this MBean server for many (but not all) of their read operations.  This MBean server exists only on the Administration Server. The Administration Server initializes it the first time a JMX client requests a connection to it. If you set this attribute to false, the Administration Server will not start this MBean server and JMX clients cannot connect to it.  While this MBean server is instantiated lazily (only when requested), once it is instantiated it does use some memory and network traffic. Disabling this MBean server can conserve a minimal amount of resources, but the trade off is that JMX clients must maintain separate connections for each WebLogic Server's Runtime MBean Server. "
      ::= { jmxEntry 9  }
   
   
   jmxName OBJECT-TYPE
      SYNTAX      OCTET STRING
      MAX-ACCESS  read-only
      STATUS      current
      DESCRIPTION "The user-specified name of this MBean instance.  This name is included as one of the key properties in the MBean's javax.management.ObjectName:  Name=user-specified-name "
      ::= { jmxEntry 10  }
   
   
   jmxEditMBeanServerEnabled OBJECT-TYPE
      SYNTAX      OCTET STRING
      MAX-ACCESS  read-only
      STATUS      current
      DESCRIPTION "Specifies whether the Administration Server initializes the Edit MBean Server, which contains the hierarchy of MBeans used to make modifications to the domain's configuration. All JMX clients, including utilities such as the Administration Console and the WebLogic Scripting Tool, use the Edit MBean Server to modify a domain's configuration.  This MBean server exists only on the Administration Server. By default, when the Administration Server starts, it starts the Edit MBean Server. If you set the EditMBeanServerEnabled attribute to false, the Administration Server will not start this MBean server. If you disable this MBean server, JMX clients cannot modify the domain's configuration. You can, however, modify the domain configuration through the offline editing feature of WebLogic Scripting Tool.   Note:   Disabling the Edit MBean Server is not sufficient to prevent changes to a domain configuration. Because the WebLogic Server deployment service does not use JMX, the Administration Console and WLST can deploy or undeploy applications even if you have disabled the Edit MBean Server.   "
      ::= { jmxEntry 11  }
   
   
   jmxPlatformMBeanServerUsed OBJECT-TYPE
      SYNTAX      OCTET STRING
      MAX-ACCESS  read-only
      STATUS      current
      DESCRIPTION "Specifies whether WebLogic Server will use the platform MBean server for its Runtime MBean Server. Previously, WebLogic Server used the platform MBean server by default if it was enabled. This attribute provides a separation between enabling the platform MBean server and using it for WebLogic Server MBeans. The default value for this attribute is based on the DomainVersion attribute of the DomainMBean. If the domain version is prior to 10.3.3.0, then the default value of this attribute is false and the platform MBean server is not used. If the domain version is 10.3.3.0 or higher, then the default value of this attribute is true and the platform MBean server is used.  In this case, the server's Runtime MBean Server uses the MBeanServer returned by java.lang.management.ManagementFactory.getPlatformMBeanServer() method as its MBean Server. This makes it possible to access the WebLogic Server MBeans and the JVM platform MXBeans from a single MBean server. In addition, if you enable the Runtime MBean Server to be the Platform MBean Server, local processes in the JVM can directly access this MBean server through the MBeanServer interface that java.lang.management.ManagementFactory.getPlatformMBeanServer() returns. "
      ::= { jmxEntry 12  }
   
   
   jmxManagedServerNotificationsEnabled OBJECT-TYPE
      SYNTAX      OCTET STRING
      MAX-ACCESS  read-only
      STATUS      current
      DESCRIPTION "Specifies whether the WebLogic Server Domain Runtime MBean Server will support notifications from the federated Runtime MBean Servers on the managed and administration servers. Supporting notifications requires a significant amount of memory resources. A list of ObjectNames is maintained for each MBean from the Runtime MBean Servers. If notifications are not required for this domain, then disabling them will save on CPU and memory resources. This is particularly critical if there are large numbers of runtime MBeans and/or large numbers of servers. "
      ::= { jmxEntry 13  }
   
   
   jmxTags OBJECT-TYPE
      SYNTAX      OCTET STRING
      MAX-ACCESS  read-only
      STATUS      current
      DESCRIPTION "Return all tags on this Configuration MBean "
      ::= { jmxEntry 14  }
   
   
   jmxManagementAppletCreateEnabled OBJECT-TYPE
      SYNTAX      OCTET STRING
      MAX-ACCESS  read-only
      STATUS      current
      DESCRIPTION "Specifies whether the WebLogic Server MBean Servers will support creation of management applet (MLet) MBeans.  MLet MBeans allow a user to upload the MBean implementation from a remote server and should only be enabled if the environment and security manager restrict access to trusted JMX clients. "
      ::= { jmxEntry 15  }
   
   
   jtaMigratableTargetTable OBJECT-TYPE
      SYNTAX      SEQUENCE OF JtaMigratableTargetEntry
      MAX-ACCESS  not-accessible
      STATUS      current
      DESCRIPTION "The target that is used internally to register the JTA recovery manager to the Migration Manager. "
      ::= { wls 980  }
      
   
   jtaMigratableTargetEntry OBJECT-TYPE
      SYNTAX      JtaMigratableTargetEntry
      MAX-ACCESS  not-accessible
      STATUS      current
      DESCRIPTION "Generated SNMP Table Entry."
      INDEX { jtaMigratableTargetIndex}
      ::= { jtaMigratableTargetTable 1 }
      
   JtaMigratableTargetEntry ::=
      SEQUENCE
      {
         jtaMigratableTargetIndex OCTET STRING,
         jtaMigratableTargetObjectName OCTET STRING,
         jtaMigratableTargetType OCTET STRING,
         jtaMigratableTargetPostScript OCTET STRING,
         jtaMigratableTargetMillisToSleepBetweenAttempts Integer32,
         jtaMigratableTargetNonLocalPostAllowed OCTET STRING,
         jtaMigratableTargetSecondsBetweenRestarts Integer32,
         jtaMigratableTargetPostScriptFailureFatal OCTET STRING,
         jtaMigratableTargetPreScript OCTET STRING,
         jtaMigratableTargetMigrationPolicy OCTET STRING,
         jtaMigratableTargetRestartOnFailure OCTET STRING,
         jtaMigratableTargetStrictOwnershipCheck OCTET STRING,
         jtaMigratableTargetName OCTET STRING,
         jtaMigratableTargetAdditionalMigrationAttempts Integer32,
         jtaMigratableTargetNumberOfRestartAttempts Integer32,
         jtaMigratableTargetCritical OCTET STRING,
         jtaMigratableTargetTags OCTET STRING
      }
      
   
   jtaMigratableTargetIndex OBJECT-TYPE
      SYNTAX      OCTET STRING
      MAX-ACCESS  not-accessible
      STATUS      current
      DESCRIPTION "Index column"
      ::= { jtaMigratableTargetEntry 1  }
   
   
   jtaMigratableTargetObjectName OBJECT-TYPE
      SYNTAX      OCTET STRING
      MAX-ACCESS  read-only
      STATUS      current
      DESCRIPTION "ObjectName column"
      ::= { jtaMigratableTargetEntry 2  }
   
   
   jtaMigratableTargetType OBJECT-TYPE
      SYNTAX      OCTET STRING
      MAX-ACCESS  read-only
      STATUS      current
      DESCRIPTION "Returns the type of the MBean. "
      ::= { jtaMigratableTargetEntry 3  }
   
   
   jtaMigratableTargetPostScript OBJECT-TYPE
      SYNTAX      OCTET STRING
      MAX-ACCESS  read-only
      STATUS      current
      DESCRIPTION "Specifies the path to the post-migration script to run after a migratable target is fully deactivated. The script must be in the MIDDLEWARE_HOME/user_projects/domains/mydomain/bin/service_migration directory.  After the migratable target is deactivated, if there is a script specified, and Node Manager is available, then the script will run. Specifying a script without an available Node Manager will result in an error upon migration. "
      ::= { jtaMigratableTargetEntry 4  }
   
   
   jtaMigratableTargetMillisToSleepBetweenAttempts OBJECT-TYPE
      SYNTAX      Integer32
      MAX-ACCESS  read-only
      STATUS      current
      DESCRIPTION "Controls how long of a pause there should be between the migration attempts described in getAdditionalMigrationAttempts(). Note that this delay only happens when the service has failed to come up on every server. It does not cause any sort of delay between attempts to migrate otherwise. "
      ::= { jtaMigratableTargetEntry 5  }
   
   
   jtaMigratableTargetNonLocalPostAllowed OBJECT-TYPE
      SYNTAX      OCTET STRING
      MAX-ACCESS  read-only
      STATUS      current
      DESCRIPTION "Specifies whether or not the post-deactivation script is allowed to run on a different machine.  Normally, when auto migration occurs, the post-deactivation script will be run on the service's current location, and the pre-activation script on the service's new location. If the current location is unreachable for some reason, this value will be checked to see if it is safe to run it on the service's new machine.  This is useful if the post-deactivation script controls access to a networked resource and does not need any data from the current machine. "
      ::= { jtaMigratableTargetEntry 6  }
   
   
   jtaMigratableTargetSecondsBetweenRestarts OBJECT-TYPE
      SYNTAX      Integer32
      MAX-ACCESS  read-only
      STATUS      current
      DESCRIPTION "Specifies how many seconds to wait in between attempts to restart the failed service. "
      ::= { jtaMigratableTargetEntry 7  }
   
   
   jtaMigratableTargetPostScriptFailureFatal OBJECT-TYPE
      SYNTAX      OCTET STRING
      MAX-ACCESS  read-only
      STATUS      current
      DESCRIPTION "Specifies whether or not a failure during execution of the post-deactivation script is fatal to the migration.  If it is fatal, the migratable target will not be automatically migrated until an administrator manually migrates it to a server, thus reactivating it.  Note: Enabling this value will result in weakening the exactly-once guarantee. It is provided to prevent more dangerous data corruption if the post-deactivation script fails. Also if this value is enabled, then the script may be called more than once by the migration framework after the Migratable Target is deactivated or the server or machine hosting the Migratable Target crashed or is network partitioned. The script is expected not to return different exit values when invoked multiple times in such scenarios. "
      ::= { jtaMigratableTargetEntry 8  }
   
   
   jtaMigratableTargetPreScript OBJECT-TYPE
      SYNTAX      OCTET STRING
      MAX-ACCESS  read-only
      STATUS      current
      DESCRIPTION "Specifies the path to the pre-migration script to run before a migratable target is actually activated. The script must be in the MIDDLEWARE_HOME/user_projects/domains/mydomain/bin/service_migration directory.  Before the migratable target is activated, if there is a script specified, and Node Manager is available, then the script will run. Specifying a script without an available Node Manager will result in an error upon migration.  If the script fails or cannot be found, migration will not proceed on the current server, and will be tried on the next suitable server. This could be the next server in the candidate server list, or in the cluster, if there is no candidate server list. "
      ::= { jtaMigratableTargetEntry 9  }
   
   
   jtaMigratableTargetMigrationPolicy OBJECT-TYPE
      SYNTAX      OCTET STRING
      MAX-ACCESS  read-only
      STATUS      current
      DESCRIPTION "Defines the type of migration policy to use for the services hosted by this migratable target. Valid options are:  Manual Service Migration Only Indicates that no automatic migration of services hosted by this migratable target will occur. Auto-Migrate Failure-Recovery Services Indicates that the services hosted by this migratable target will only start if the migratable target's User Preferred Server (UPS) is started. If an administrator manually shuts down the UPS, either gracefully or forcibly, then a failure-recovery service will not migrate. However, if the UPS fails due to an internal error, then the service will be migrated to another candidate server. If such a candidate server is unavailable (due to either a manual shutdown or an internal failure), then the migration framework will first attempt to reactivate the service on its UPS server. If the UPS server is not available at that time, then the service will be migrated to another candidate server. Auto-Migrate Shutdown-Recovery Services Indicates that the services hosted by this migratable target will migrate to one of the candidate servers, if server is administratively shut down (either gracefully or forcibly). Once recovery is done, service is migrated back to failed server.  "
      ::= { jtaMigratableTargetEntry 10  }
   
   
   jtaMigratableTargetRestartOnFailure OBJECT-TYPE
      SYNTAX      OCTET STRING
      MAX-ACCESS  read-only
      STATUS      current
      DESCRIPTION "Specifies whether or not a failed service will first be deactivated and reactivated in place, instead of being migrated.  The number of restart attempts is controlled by {@link #getNumberOfRestartAttempts}. Once these restart attempts are exhausted, the service will migrate. A restarting migratable target will deactivate all services on it in order, then reactivate them all. "
      ::= { jtaMigratableTargetEntry 11  }
   
   
   jtaMigratableTargetStrictOwnershipCheck OBJECT-TYPE
      SYNTAX      OCTET STRING
      MAX-ACCESS  read-only
      STATUS      current
      DESCRIPTION "Whether continue to boot if cannot find the current owner of TRS to do failback. This attribute is only meaningful for servers in cluster.   If true: server will fail to boot under this situation. If false: server will continue to boot without trying to do failback. "
      ::= { jtaMigratableTargetEntry 12  }
   
   
   jtaMigratableTargetName OBJECT-TYPE
      SYNTAX      OCTET STRING
      MAX-ACCESS  read-only
      STATUS      current
      DESCRIPTION "The user-specified name of this MBean instance.  This name is included as one of the key properties in the MBean's javax.management.ObjectName:  Name=user-specified-name "
      ::= { jtaMigratableTargetEntry 13  }
   
   
   jtaMigratableTargetAdditionalMigrationAttempts OBJECT-TYPE
      SYNTAX      Integer32
      MAX-ACCESS  read-only
      STATUS      current
      DESCRIPTION "A migratable service could fail to come up on every possible configured server. This attribute controls how many further attempts, after the service has failed on every server at least once, should be tried. Note that each attempt specified here indicates another full circuit of migrations amongst all the configured servers. So for a 3-server cluster, and a value of 2, a total of 4 additional migrations will be attempted. (the original server is never a valid destination) "
      ::= { jtaMigratableTargetEntry 14  }
   
   
   jtaMigratableTargetNumberOfRestartAttempts OBJECT-TYPE
      SYNTAX      Integer32
      MAX-ACCESS  read-only
      STATUS      current
      DESCRIPTION "Specifies how many restart attempts to make before migrating the failed service.  Note that these are consecutive attempts. If the value is set to 6, and the service restart fails 5 times before succeeding, but then fails again later, it will not instantly migrate. Each failure gets its own count of restart attempts.  A value of 0 is identical to setting {@link #getRestartOnFailure} to false. A value of -1 indicates the service should  never be migrated; instead, it will be restarted until it either works or the server shuts down. "
      ::= { jtaMigratableTargetEntry 15  }
   
   
   jtaMigratableTargetCritical OBJECT-TYPE
      SYNTAX      OCTET STRING
      MAX-ACCESS  read-only
      STATUS      current
      DESCRIPTION "Returns true if the MigratableTarget is critical to the overall health of the WLS Server "
      ::= { jtaMigratableTargetEntry 16  }
   
   
   jtaMigratableTargetTags OBJECT-TYPE
      SYNTAX      OCTET STRING
      MAX-ACCESS  read-only
      STATUS      current
      DESCRIPTION "Return all tags on this Configuration MBean "
      ::= { jtaMigratableTargetEntry 17  }
   
   
   joltConnectionPoolTable OBJECT-TYPE
      SYNTAX      SEQUENCE OF JoltConnectionPoolEntry
      MAX-ACCESS  not-accessible
      STATUS      current
      DESCRIPTION "This bean defines a Jolt connection pool. "
      ::= { wls 985  }
      
   
   joltConnectionPoolEntry OBJECT-TYPE
      SYNTAX      JoltConnectionPoolEntry
      MAX-ACCESS  not-accessible
      STATUS      current
      DESCRIPTION "Generated SNMP Table Entry."
      INDEX { joltConnectionPoolIndex}
      ::= { joltConnectionPoolTable 1 }
      
   JoltConnectionPoolEntry ::=
      SEQUENCE
      {
         joltConnectionPoolIndex OCTET STRING,
         joltConnectionPoolObjectName OCTET STRING,
         joltConnectionPoolType OCTET STRING,
         joltConnectionPoolMinimumPoolSize Integer32,
         joltConnectionPoolMaximumPoolSize Integer32,
         joltConnectionPoolName OCTET STRING,
         joltConnectionPoolUserName OCTET STRING,
         joltConnectionPoolDeploymentOrder Integer32,
         joltConnectionPoolRecvTimeout Integer32,
         joltConnectionPoolSecurityContextEnabled OCTET STRING,
         joltConnectionPoolTrustStoreName OCTET STRING,
         joltConnectionPoolUserRole OCTET STRING,
         joltConnectionPoolKeyStoreName OCTET STRING,
         joltConnectionPoolFailoverAddresses OCTET STRING,
         joltConnectionPoolPrimaryAddresses OCTET STRING,
         joltConnectionPoolTags OCTET STRING
      }
      
   
   joltConnectionPoolIndex OBJECT-TYPE
      SYNTAX      OCTET STRING
      MAX-ACCESS  not-accessible
      STATUS      current
      DESCRIPTION "Index column"
      ::= { joltConnectionPoolEntry 1  }
   
   
   joltConnectionPoolObjectName OBJECT-TYPE
      SYNTAX      OCTET STRING
      MAX-ACCESS  read-only
      STATUS      current
      DESCRIPTION "ObjectName column"
      ::= { joltConnectionPoolEntry 2  }
   
   
   joltConnectionPoolType OBJECT-TYPE
      SYNTAX      OCTET STRING
      MAX-ACCESS  read-only
      STATUS      current
      DESCRIPTION "Returns the type of the MBean. "
      ::= { joltConnectionPoolEntry 3  }
   
   
   joltConnectionPoolMinimumPoolSize OBJECT-TYPE
      SYNTAX      Integer32
      MAX-ACCESS  read-only
      STATUS      current
      DESCRIPTION "The minimum number of connections to be added to this Jolt connection pool when WebLogic Server starts. "
      ::= { joltConnectionPoolEntry 4  }
   
   
   joltConnectionPoolMaximumPoolSize OBJECT-TYPE
      SYNTAX      Integer32
      MAX-ACCESS  read-only
      STATUS      current
      DESCRIPTION "The maximum number of connections that can be made from this Jolt connection pool. "
      ::= { joltConnectionPoolEntry 5  }
   
   
   joltConnectionPoolName OBJECT-TYPE
      SYNTAX      OCTET STRING
      MAX-ACCESS  read-only
      STATUS      current
      DESCRIPTION "The user-specified name of this MBean instance.  This name is included as one of the key properties in the MBean's javax.management.ObjectName:  Name=user-specified-name "
      ::= { joltConnectionPoolEntry 6  }
   
   
   joltConnectionPoolUserName OBJECT-TYPE
      SYNTAX      OCTET STRING
      MAX-ACCESS  read-only
      STATUS      current
      DESCRIPTION "A user name that applications specify to connect to this Jolt connection pool. If Security Context is enabled, this name must be the name of an authorized Tuxedo user. (Specifying a Tuxedo user name is required if the Tuxedo authentication level is USER_AUTH.) "
      ::= { joltConnectionPoolEntry 7  }
   
   
   joltConnectionPoolDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { joltConnectionPoolEntry 8  }
   
   
   joltConnectionPoolRecvTimeout OBJECT-TYPE
      SYNTAX      Integer32
      MAX-ACCESS  read-only
      STATUS      current
      DESCRIPTION "The number of seconds the client waits to receive a response before timing out. "
      ::= { joltConnectionPoolEntry 9  }
   
   
   joltConnectionPoolSecurityContextEnabled OBJECT-TYPE
      SYNTAX      OCTET STRING
      MAX-ACCESS  read-only
      STATUS      current
      DESCRIPTION "Indicates whether this Jolt connection pool passes the connection pool's security context (user name, password and other information) from the WebLogic Server user to the Tuxedo domain.  If you enable the connection pool to pass the security context, you must start the Jolt Service Handler (JSH) with the -a option. When the JSH gets a message with the caller's identity, it calls impersonate_user() to get the appkey for the user. JSH caches the appkey, so the next time the caller makes a request, the appkey is retrieved from the cache and the request is forwarded to the service. A cache is maintained by each JSH, which means that there will be a cache maintained for all the session pools connected to the same JSH.  You must enable Security Context if Tuxedo requires secured connections. "
      ::= { joltConnectionPoolEntry 10  }
   
   
   joltConnectionPoolTrustStoreName OBJECT-TYPE
      SYNTAX      OCTET STRING
      MAX-ACCESS  read-only
      STATUS      current
      DESCRIPTION "The path and file name of the keystore containing the trust certificates. "
      ::= { joltConnectionPoolEntry 11  }
   
   
   joltConnectionPoolUserRole OBJECT-TYPE
      SYNTAX      OCTET STRING
      MAX-ACCESS  read-only
      STATUS      current
      DESCRIPTION "The Tuxedo user role for this Jolt connection pool. (This is required only when the security level in the Tuxedo domain is USER_AUTH, ACL, or MANDATORY_ACL). "
      ::= { joltConnectionPoolEntry 12  }
   
   
   joltConnectionPoolKeyStoreName OBJECT-TYPE
      SYNTAX      OCTET STRING
      MAX-ACCESS  read-only
      STATUS      current
      DESCRIPTION "The path and file name of the keystore containing the private key used in SSL mutual authentication. "
      ::= { joltConnectionPoolEntry 13  }
   
   
   joltConnectionPoolFailoverAddresses OBJECT-TYPE
      SYNTAX      OCTET STRING
      MAX-ACCESS  read-only
      STATUS      current
      DESCRIPTION "The list of Jolt Server Listeners (JSLs) addresses that is used if the connection pool cannot estabilish connections to the Primary Addresses, or if the primary connections fail.  The format of each address is: //hostname:port. Multiple addresses should be separated by commas.  These JSLs need not reside on the same host as the primary JSLs. "
      ::= { joltConnectionPoolEntry 14  }
   
   
   joltConnectionPoolPrimaryAddresses OBJECT-TYPE
      SYNTAX      OCTET STRING
      MAX-ACCESS  read-only
      STATUS      current
      DESCRIPTION "The list of addresses for the primary Jolt Server Listeners (JSLs) on the Tuxedo system.  The format of each address is: //hostname:port. Multiple addresses should be separated by commas. "
      ::= { joltConnectionPoolEntry 15  }
   
   
   joltConnectionPoolTags OBJECT-TYPE
      SYNTAX      OCTET STRING
      MAX-ACCESS  read-only
      STATUS      current
      DESCRIPTION "Return all tags on this Configuration MBean "
      ::= { joltConnectionPoolEntry 16  }
   
   
   logFilterTable OBJECT-TYPE
      SYNTAX      SEQUENCE OF LogFilterEntry
      MAX-ACCESS  not-accessible
      STATUS      current
      DESCRIPTION "This MBean represents a filter to qualify log messages which are selected by the specified filter expression criteria. A message must meet all the specified criteria to qualify the filter. Multiple instances of this MBean can be defined, if needed. If there are multiple instances, a message must qualify at least one filter to qualify for the log file. "
      ::= { wls 990  }
      
   
   logFilterEntry OBJECT-TYPE
      SYNTAX      LogFilterEntry
      MAX-ACCESS  not-accessible
      STATUS      current
      DESCRIPTION "Generated SNMP Table Entry."
      INDEX { logFilterIndex}
      ::= { logFilterTable 1 }
      
   LogFilterEntry ::=
      SEQUENCE
      {
         logFilterIndex       OCTET STRING,
         logFilterObjectName  OCTET STRING,
         logFilterType        OCTET STRING,
         logFilterFilterExpression OCTET STRING,
         logFilterName        OCTET STRING,
         logFilterTags        OCTET STRING
      }
      
   
   logFilterIndex OBJECT-TYPE
      SYNTAX      OCTET STRING
      MAX-ACCESS  not-accessible
      STATUS      current
      DESCRIPTION "Index column"
      ::= { logFilterEntry 1  }
   
   
   logFilterObjectName OBJECT-TYPE
      SYNTAX      OCTET STRING
      MAX-ACCESS  read-only
      STATUS      current
      DESCRIPTION "ObjectName column"
      ::= { logFilterEntry 2  }
   
   
   logFilterType OBJECT-TYPE
      SYNTAX      OCTET STRING
      MAX-ACCESS  read-only
      STATUS      current
      DESCRIPTION "Returns the type of the MBean. "
      ::= { logFilterEntry 3  }
   
   
   logFilterFilterExpression OBJECT-TYPE
      SYNTAX      OCTET STRING
      MAX-ACCESS  read-only
      STATUS      current
      DESCRIPTION "The filter expression to be evaluated for qualifying log messages.  The filter expression is specified as a string in the query language. The query language supports Boolean operators: AND, OR, and NOT, and relational operators. You can use the following column names (message attributes) in a query to filter data going to a log destination: RECORDID, DATE, SEVERITY, SUBSYSTEM, MACHINE, SERVER, THREAD, USERID, TXID, CONTEXTID, TIMESTAMP, MSGID, and MESSAGE. "
      ::= { logFilterEntry 4  }
   
   
   logFilterName OBJECT-TYPE
      SYNTAX      OCTET STRING
      MAX-ACCESS  read-only
      STATUS      current
      DESCRIPTION "The user-specified name of this MBean instance.  This name is included as one of the key properties in the MBean's javax.management.ObjectName:  Name=user-specified-name "
      ::= { logFilterEntry 5  }
   
   
   logFilterTags OBJECT-TYPE
      SYNTAX      OCTET STRING
      MAX-ACCESS  read-only
      STATUS      current
      DESCRIPTION "Return all tags on this Configuration MBean "
      ::= { logFilterEntry 6  }
   
   
   mailSessionTable OBJECT-TYPE
      SYNTAX      SEQUENCE OF MailSessionEntry
      MAX-ACCESS  not-accessible
      STATUS      current
      DESCRIPTION "Facilitates using the JavaMail APIs, which provide applications and other Java EE modules with access to Internet Message Access Protocol (IMAP)- and Simple Mail Transfer Protocol (SMTP)-capable mail servers on your network or the Internet.  In the reference implementation of JavaMail, applications must instantiate javax.mail.Session objects, which designate mail hosts, transport and store protocols, and a default mail user for connecting to a mail server. In WebLogic Server, you create a mail session, which configures a javax.mail.Session object and registers it in the WebLogic Server JNDI tree. Applications access the mail session through JNDI instead of instantiating their own javax.mail.Session object. "
      ::= { wls 995  }
      
   
   mailSessionEntry OBJECT-TYPE
      SYNTAX      MailSessionEntry
      MAX-ACCESS  not-accessible
      STATUS      current
      DESCRIPTION "Generated SNMP Table Entry."
      INDEX { mailSessionIndex}
      ::= { mailSessionTable 1 }
      
   MailSessionEntry ::=
      SEQUENCE
      {
         mailSessionIndex     OCTET STRING,
         mailSessionObjectName OCTET STRING,
         mailSessionType      OCTET STRING,
         mailSessionDeploymentOrder Integer32,
         mailSessionJNDIName  OCTET STRING,
         mailSessionName      OCTET STRING,
         mailSessionSessionUsername OCTET STRING,
         mailSessionTags      OCTET STRING
      }
      
   
   mailSessionIndex OBJECT-TYPE
      SYNTAX      OCTET STRING
      MAX-ACCESS  not-accessible
      STATUS      current
      DESCRIPTION "Index column"
      ::= { mailSessionEntry 1  }
   
   
   mailSessionObjectName OBJECT-TYPE
      SYNTAX      OCTET STRING
      MAX-ACCESS  read-only
      STATUS      current
      DESCRIPTION "ObjectName column"
      ::= { mailSessionEntry 2  }
   
   
   mailSessionType OBJECT-TYPE
      SYNTAX      OCTET STRING
      MAX-ACCESS  read-only
      STATUS      current
      DESCRIPTION "Returns the type of the MBean. "
      ::= { mailSessionEntry 3  }
   
   
   mailSessionDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { mailSessionEntry 4  }
   
   
   mailSessionJNDIName OBJECT-TYPE
      SYNTAX      OCTET STRING
      MAX-ACCESS  read-only
      STATUS      current
      DESCRIPTION "The JNDI Name associated with this resource. "
      ::= { mailSessionEntry 5  }
   
   
   mailSessionName OBJECT-TYPE
      SYNTAX      OCTET STRING
      MAX-ACCESS  read-only
      STATUS      current
      DESCRIPTION "jmsserverjmshat on The user-specified name of this MBean instance.  This name is included as one of the key properties in the MBean's javax.management.ObjectName:  Name=user-specified-name "
      ::= { mailSessionEntry 6  }
   
   
   mailSessionSessionUsername OBJECT-TYPE
      SYNTAX      OCTET STRING
      MAX-ACCESS  read-only
      STATUS      current
      DESCRIPTION " Returns the username to be used to create an authenticated JavaMail Session, using a JavaMail Authenticator instance; if this is not set, it will be assumed that the Session is not to be authenticated.  "
      ::= { mailSessionEntry 7  }
   
   
   mailSessionTags OBJECT-TYPE
      SYNTAX      OCTET STRING
      MAX-ACCESS  read-only
      STATUS      current
      DESCRIPTION "Return all tags on this Configuration MBean "
      ::= { mailSessionEntry 8  }
   
   
   maxThreadsConstraintTable OBJECT-TYPE
      SYNTAX      SEQUENCE OF MaxThreadsConstraintEntry
      MAX-ACCESS  not-accessible
      STATUS      current
      DESCRIPTION "This MBean defines the max number of concurrent threads that can execute requests sharing this max constraint.  MaxThreadsConstraint can be used to tell the server that the requests are constrained by an external resource like a database and allocating more threads that the external resource limit is not going to help since the extra threads are just going to wait.  "
      ::= { wls 1000  }
      
   
   maxThreadsConstraintEntry OBJECT-TYPE
      SYNTAX      MaxThreadsConstraintEntry
      MAX-ACCESS  not-accessible
      STATUS      current
      DESCRIPTION "Generated SNMP Table Entry."
      INDEX { maxThreadsConstraintIndex}
      ::= { maxThreadsConstraintTable 1 }
      
   MaxThreadsConstraintEntry ::=
      SEQUENCE
      {
         maxThreadsConstraintIndex OCTET STRING,
         maxThreadsConstraintObjectName OCTET STRING,
         maxThreadsConstraintType OCTET STRING,
         maxThreadsConstraintDeploymentOrder Integer32,
         maxThreadsConstraintCount Integer32,
         maxThreadsConstraintName OCTET STRING,
         maxThreadsConstraintConnectionPoolName OCTET STRING,
         maxThreadsConstraintQueueSize INTEGER,
         maxThreadsConstraintTags OCTET STRING
      }
      
   
   maxThreadsConstraintIndex OBJECT-TYPE
      SYNTAX      OCTET STRING
      MAX-ACCESS  not-accessible
      STATUS      current
      DESCRIPTION "Index column"
      ::= { maxThreadsConstraintEntry 1  }
   
   
   maxThreadsConstraintObjectName OBJECT-TYPE
      SYNTAX      OCTET STRING
      MAX-ACCESS  read-only
      STATUS      current
      DESCRIPTION "ObjectName column"
      ::= { maxThreadsConstraintEntry 2  }
   
   
   maxThreadsConstraintType OBJECT-TYPE
      SYNTAX      OCTET STRING
      MAX-ACCESS  read-only
      STATUS      current
      DESCRIPTION "Returns the type of the MBean. "
      ::= { maxThreadsConstraintEntry 3  }
   
   
   maxThreadsConstraintDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { maxThreadsConstraintEntry 4  }
   
   
   maxThreadsConstraintCount OBJECT-TYPE
      SYNTAX      Integer32
      MAX-ACCESS  read-only
      STATUS      current
      DESCRIPTION "Maximum number of concurrent threads that can execute requests sharing this constraint.  A count of 0 or -1 is treated as if the constraint is not present. This means that no constraint is enforced for these two values. A count > 0 can be dynamically changed to 0 to indicate that constraint enforcement is no longer needed.  "
      ::= { maxThreadsConstraintEntry 5  }
   
   
   maxThreadsConstraintName OBJECT-TYPE
      SYNTAX      OCTET STRING
      MAX-ACCESS  read-only
      STATUS      current
      DESCRIPTION "The user-specified name of this MBean instance.  This name is included as one of the key properties in the MBean's javax.management.ObjectName:  Name=user-specified-name "
      ::= { maxThreadsConstraintEntry 6  }
   
   
   maxThreadsConstraintConnectionPoolName OBJECT-TYPE
      SYNTAX      OCTET STRING
      MAX-ACCESS  read-only
      STATUS      current
      DESCRIPTION "Name of the connection pool whose size is taken as the max constraint.  This can be the name of a JDBC data source. The max capacity of the data source is used as the constraint.  "
      ::= { maxThreadsConstraintEntry 7  }
   
   
   maxThreadsConstraintQueueSize OBJECT-TYPE
      SYNTAX      INTEGER
      MAX-ACCESS  read-only
      STATUS      current
      DESCRIPTION "Desired size of the MaxThreadsConstraint queue for requests pending execution. "
      ::= { maxThreadsConstraintEntry 8  }
   
   
   maxThreadsConstraintTags OBJECT-TYPE
      SYNTAX      OCTET STRING
      MAX-ACCESS  read-only
      STATUS      current
      DESCRIPTION "Return all tags on this Configuration MBean "
      ::= { maxThreadsConstraintEntry 9  }
   
   
   minThreadsConstraintTable OBJECT-TYPE
      SYNTAX      SEQUENCE OF MinThreadsConstraintEntry
      MAX-ACCESS  not-accessible
      STATUS      current
      DESCRIPTION "This MBean defines the minimum number of concurrent threads that should allocated to this constraint provided there are enough pending requests.   Multiple WorkManagers can share a common MinThreadsConstraint. MinThreadsConstraint perform their own bookkeeping and demand a thread when the constraint is not met and there are enough requests.    MinThreadsConstraint should be used to tell the WebLogic Server that a certain number of minimum threads are necessary to prevent server to server deadlocks. Although the server is self-tuning, specifying MinThreadsConstraint ensures that the server guarantees minimum threads to avoid the distributed deadlocks.  "
      ::= { wls 1010  }
      
   
   minThreadsConstraintEntry OBJECT-TYPE
      SYNTAX      MinThreadsConstraintEntry
      MAX-ACCESS  not-accessible
      STATUS      current
      DESCRIPTION "Generated SNMP Table Entry."
      INDEX { minThreadsConstraintIndex}
      ::= { minThreadsConstraintTable 1 }
      
   MinThreadsConstraintEntry ::=
      SEQUENCE
      {
         minThreadsConstraintIndex OCTET STRING,
         minThreadsConstraintObjectName OCTET STRING,
         minThreadsConstraintType OCTET STRING,
         minThreadsConstraintDeploymentOrder Integer32,
         minThreadsConstraintCount Integer32,
         minThreadsConstraintName OCTET STRING,
         minThreadsConstraintTags OCTET STRING
      }
      
   
   minThreadsConstraintIndex OBJECT-TYPE
      SYNTAX      OCTET STRING
      MAX-ACCESS  not-accessible
      STATUS      current
      DESCRIPTION "Index column"
      ::= { minThreadsConstraintEntry 1  }
   
   
   minThreadsConstraintObjectName OBJECT-TYPE
      SYNTAX      OCTET STRING
      MAX-ACCESS  read-only
      STATUS      current
      DESCRIPTION "ObjectName column"
      ::= { minThreadsConstraintEntry 2  }
   
   
   minThreadsConstraintType OBJECT-TYPE
      SYNTAX      OCTET STRING
      MAX-ACCESS  read-only
      STATUS      current
      DESCRIPTION "Returns the type of the MBean. "
      ::= { minThreadsConstraintEntry 3  }
   
   
   minThreadsConstraintDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { minThreadsConstraintEntry 4  }
   
   
   minThreadsConstraintCount OBJECT-TYPE
      SYNTAX      Integer32
      MAX-ACCESS  read-only
      STATUS      current
      DESCRIPTION "Minimum number of concurrent threads executing requests that share this constraint.  A count of 0 or -1 is treated as if the constraint is not present. This means that the constraint is ignored for these two values. A count > 0 can be dynamically changed to 0 to indicate that constraint enforcement is no longer needed.  "
      ::= { minThreadsConstraintEntry 5  }
   
   
   minThreadsConstraintName OBJECT-TYPE
      SYNTAX      OCTET STRING
      MAX-ACCESS  read-only
      STATUS      current
      DESCRIPTION "The user-specified name of this MBean instance.  This name is included as one of the key properties in the MBean's javax.management.ObjectName:  Name=user-specified-name "
      ::= { minThreadsConstraintEntry 6  }
   
   
   minThreadsConstraintTags OBJECT-TYPE
      SYNTAX      OCTET STRING
      MAX-ACCESS  read-only
      STATUS      current
      DESCRIPTION "Return all tags on this Configuration MBean "
      ::= { minThreadsConstraintEntry 7  }
   
   
   overloadProtectionTable OBJECT-TYPE
      SYNTAX      SEQUENCE OF OverloadProtectionEntry
      MAX-ACCESS  not-accessible
      STATUS      current
      DESCRIPTION "This Mbean has attributes concerning server overload protection. "
      ::= { wls 1015  }
      
   
   overloadProtectionEntry OBJECT-TYPE
      SYNTAX      OverloadProtectionEntry
      MAX-ACCESS  not-accessible
      STATUS      current
      DESCRIPTION "Generated SNMP Table Entry."
      INDEX { overloadProtectionIndex}
      ::= { overloadProtectionTable 1 }
      
   OverloadProtectionEntry ::=
      SEQUENCE
      {
         overloadProtectionIndex OCTET STRING,
         overloadProtectionObjectName OCTET STRING,
         overloadProtectionType OCTET STRING,
         overloadProtectionSharedCapacityForWorkManagers Integer32,
         overloadProtectionFreeMemoryPercentLowThreshold Integer32,
         overloadProtectionFailureAction OCTET STRING,
         overloadProtectionFreeMemoryPercentHighThreshold Integer32,
         overloadProtectionName OCTET STRING,
         overloadProtectionPanicAction OCTET STRING,
         overloadProtectionTags OCTET STRING
      }
      
   
   overloadProtectionIndex OBJECT-TYPE
      SYNTAX      OCTET STRING
      MAX-ACCESS  not-accessible
      STATUS      current
      DESCRIPTION "Index column"
      ::= { overloadProtectionEntry 1  }
   
   
   overloadProtectionObjectName OBJECT-TYPE
      SYNTAX      OCTET STRING
      MAX-ACCESS  read-only
      STATUS      current
      DESCRIPTION "ObjectName column"
      ::= { overloadProtectionEntry 2  }
   
   
   overloadProtectionType OBJECT-TYPE
      SYNTAX      OCTET STRING
      MAX-ACCESS  read-only
      STATUS      current
      DESCRIPTION "Returns the type of the MBean. "
      ::= { overloadProtectionEntry 3  }
   
   
   overloadProtectionSharedCapacityForWorkManagers OBJECT-TYPE
      SYNTAX      Integer32
      MAX-ACCESS  read-only
      STATUS      current
      DESCRIPTION "Total number of requests that can be present in the server. This includes requests that are enqueued and those under execution.  The server performs a differentiated denial of service on reaching the shared capacity. A request with higher priority will be accepted in place of a lower priority request already in the queue. The lower priority request is kept waiting in the queue till all high priority requests are executed. Further enqueues of the low priority requests are rejected right away.  "
      ::= { overloadProtectionEntry 4  }
   
   
   overloadProtectionFreeMemoryPercentLowThreshold OBJECT-TYPE
      SYNTAX      Integer32
      MAX-ACCESS  read-only
      STATUS      current
      DESCRIPTION "Percentage free memory below which the server is considered overloaded. WorkManagers perform overloadAction once the server is marked as overloaded. "
      ::= { overloadProtectionEntry 5  }
   
   
   overloadProtectionFailureAction OBJECT-TYPE
      SYNTAX      OCTET STRING
      MAX-ACCESS  read-only
      STATUS      current
      DESCRIPTION "Enable automatic forceshutdown of the server on failed state. The server self-health monitoring detects fatal failures and mark the server as failed. The server can be restarted using NodeManager or a HA agent. "
      ::= { overloadProtectionEntry 6  }
   
   
   overloadProtectionFreeMemoryPercentHighThreshold OBJECT-TYPE
      SYNTAX      Integer32
      MAX-ACCESS  read-only
      STATUS      current
      DESCRIPTION "Percentage free memory after which the server overload condition is cleared. WorkManagers stop performing overloadActions and start regular execution once the overload condition is cleared. "
      ::= { overloadProtectionEntry 7  }
   
   
   overloadProtectionName OBJECT-TYPE
      SYNTAX      OCTET STRING
      MAX-ACCESS  read-only
      STATUS      current
      DESCRIPTION "The user-specified name of this MBean instance.  This name is included as one of the key properties in the MBean's javax.management.ObjectName:  Name=user-specified-name "
      ::= { overloadProtectionEntry 8  }
   
   
   overloadProtectionPanicAction OBJECT-TYPE
      SYNTAX      OCTET STRING
      MAX-ACCESS  read-only
      STATUS      current
      DESCRIPTION "Exit the server process when the kernel encounters a panic condition like an unhandled OOME. An unhandled OOME could lead to inconsistent state and a server restart is advisable if backed by node manager or a HA agent. "
      ::= { overloadProtectionEntry 9  }
   
   
   overloadProtectionTags OBJECT-TYPE
      SYNTAX      OCTET STRING
      MAX-ACCESS  read-only
      STATUS      current
      DESCRIPTION "Return all tags on this Configuration MBean "
      ::= { overloadProtectionEntry 10  }
   
   
   pathServiceTable OBJECT-TYPE
      SYNTAX      SEQUENCE OF PathServiceEntry
      MAX-ACCESS  not-accessible
      STATUS      current
      DESCRIPTION "This class represents a path service. "
      ::= { wls 1020  }
      
   
   pathServiceEntry OBJECT-TYPE
      SYNTAX      PathServiceEntry
      MAX-ACCESS  not-accessible
      STATUS      current
      DESCRIPTION "Generated SNMP Table Entry."
      INDEX { pathServiceIndex}
      ::= { pathServiceTable 1 }
      
   PathServiceEntry ::=
      SEQUENCE
      {
         pathServiceIndex     OCTET STRING,
         pathServiceObjectName OCTET STRING,
         pathServiceType      OCTET STRING,
         pathServiceDeploymentOrder Integer32,
         pathServiceName      OCTET STRING,
         pathServiceTags      OCTET STRING
      }
      
   
   pathServiceIndex OBJECT-TYPE
      SYNTAX      OCTET STRING
      MAX-ACCESS  not-accessible
      STATUS      current
      DESCRIPTION "Index column"
      ::= { pathServiceEntry 1  }
   
   
   pathServiceObjectName OBJECT-TYPE
      SYNTAX      OCTET STRING
      MAX-ACCESS  read-only
      STATUS      current
      DESCRIPTION "ObjectName column"
      ::= { pathServiceEntry 2  }
   
   
   pathServiceType OBJECT-TYPE
      SYNTAX      OCTET STRING
      MAX-ACCESS  read-only
      STATUS      current
      DESCRIPTION "Returns the type of the MBean. "
      ::= { pathServiceEntry 3  }
   
   
   pathServiceDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { pathServiceEntry 4  }
   
   
   pathServiceName OBJECT-TYPE
      SYNTAX      OCTET STRING
      MAX-ACCESS  read-only
      STATUS      current
      DESCRIPTION "The user-specified name of this MBean instance.  This name is included as one of the key properties in the MBean's javax.management.ObjectName:  Name=user-specified-name "
      ::= { pathServiceEntry 5  }
   
   
   pathServiceTags OBJECT-TYPE
      SYNTAX      OCTET STRING
      MAX-ACCESS  read-only
      STATUS      current
      DESCRIPTION "Return all tags on this Configuration MBean "
      ::= { pathServiceEntry 6  }
   
   
   remoteSAFContextTable OBJECT-TYPE
      SYNTAX      SEQUENCE OF RemoteSAFContextEntry
      MAX-ACCESS  not-accessible
      STATUS      current
      DESCRIPTION "Fake RemoteSAFContextMBean"
      ::= { wls 1025  }
      
   
   remoteSAFContextEntry OBJECT-TYPE
      SYNTAX      RemoteSAFContextEntry
      MAX-ACCESS  not-accessible
      STATUS      current
      DESCRIPTION "Generated SNMP Table Entry."
      INDEX { remoteSAFContextIndex}
      ::= { remoteSAFContextTable 1 }
      
   RemoteSAFContextEntry ::=
      SEQUENCE
      {
         remoteSAFContextIndex OCTET STRING,
         remoteSAFContextObjectName OCTET STRING,
         remoteSAFContextType OCTET STRING,
         remoteSAFContextProtocol OCTET STRING,
         remoteSAFContextUrl  OCTET STRING,
         remoteSAFContextPassword OCTET STRING,
         remoteSAFContextJndiInitialContextFactory OCTET STRING,
         remoteSAFContextName OCTET STRING,
         remoteSAFContextJndiProperty OCTET STRING,
         remoteSAFContextUsername OCTET STRING,
         remoteSAFContextTags OCTET STRING
      }
      
   
   remoteSAFContextIndex OBJECT-TYPE
      SYNTAX      OCTET STRING
      MAX-ACCESS  not-accessible
      STATUS      current
      DESCRIPTION "Index column"
      ::= { remoteSAFContextEntry 1  }
   
   
   remoteSAFContextObjectName OBJECT-TYPE
      SYNTAX      OCTET STRING
      MAX-ACCESS  read-only
      STATUS      current
      DESCRIPTION "ObjectName column"
      ::= { remoteSAFContextEntry 2  }
   
   
   remoteSAFContextType OBJECT-TYPE
      SYNTAX      OCTET STRING
      MAX-ACCESS  read-only
      STATUS      current
      DESCRIPTION "Returns the type of the MBean."
      ::= { remoteSAFContextEntry 3  }
   
   
   remoteSAFContextProtocol OBJECT-TYPE
      SYNTAX      OCTET STRING
      MAX-ACCESS  read-only
      STATUS      current
      DESCRIPTION "Protocol"
      ::= { remoteSAFContextEntry 4  }
   
   
   remoteSAFContextUrl OBJECT-TYPE
      SYNTAX      OCTET STRING
      MAX-ACCESS  read-only
      STATUS      current
      DESCRIPTION "URL"
      ::= { remoteSAFContextEntry 5  }
   
   
   remoteSAFContextPassword OBJECT-TYPE
      SYNTAX      OCTET STRING
      MAX-ACCESS  read-only
      STATUS      current
      DESCRIPTION "Password"
      ::= { remoteSAFContextEntry 6  }
   
   
   remoteSAFContextJndiInitialContextFactory OBJECT-TYPE
      SYNTAX      OCTET STRING
      MAX-ACCESS  read-only
      STATUS      current
      DESCRIPTION "JndiInitialContextFactory"
      ::= { remoteSAFContextEntry 7  }
   
   
   remoteSAFContextName OBJECT-TYPE
      SYNTAX      OCTET STRING
      MAX-ACCESS  read-only
      STATUS      current
      DESCRIPTION "The user-specified name of this MBean instance.  This name is included as one of the key properties in the MBean's javax.management.ObjectName:  Name=user-specified-name"
      ::= { remoteSAFContextEntry 8  }
   
   
   remoteSAFContextJndiProperty OBJECT-TYPE
      SYNTAX      OCTET STRING
      MAX-ACCESS  read-only
      STATUS      current
      DESCRIPTION "JndiProperty"
      ::= { remoteSAFContextEntry 9  }
   
   
   remoteSAFContextUsername OBJECT-TYPE
      SYNTAX      OCTET STRING
      MAX-ACCESS  read-only
      STATUS      current
      DESCRIPTION "UserName"
      ::= { remoteSAFContextEntry 10  }
   
   
   remoteSAFContextTags OBJECT-TYPE
      SYNTAX      OCTET STRING
      MAX-ACCESS  read-only
      STATUS      current
      DESCRIPTION "Return all tags on this Configuration MBean"
      ::= { remoteSAFContextEntry 11  }
   
   
   responseTimeRequestClassTable OBJECT-TYPE
      SYNTAX      SEQUENCE OF ResponseTimeRequestClassEntry
      MAX-ACCESS  not-accessible
      STATUS      current
      DESCRIPTION "This MBean defines the response time goal for this request class.   Response time goals can be used to differentiate request classes. We do not try to meet a response time goal for an individual request. Rather we compute a tolerable waiting time for a request class by subtracting the observed average thread use time. Then we schedule requests so that the average wait for each request class is in proportion to their tolerable waiting time. For example, consider we only have two request classes, A and B, with response time goals 2000ms and 5000ms, respectively, where the time an individual request uses a thread is much smaller. During a period in which both request classes are sufficiently requested, say, zero think time and more clients than threads, we schedule to keep the average response time in the ratio 2:5 so that it is a common fraction or multiple of the stated goal.  "
      ::= { wls 1030  }
      
   
   responseTimeRequestClassEntry OBJECT-TYPE
      SYNTAX      ResponseTimeRequestClassEntry
      MAX-ACCESS  not-accessible
      STATUS      current
      DESCRIPTION "Generated SNMP Table Entry."
      INDEX { responseTimeRequestClassIndex}
      ::= { responseTimeRequestClassTable 1 }
      
   ResponseTimeRequestClassEntry ::=
      SEQUENCE
      {
         responseTimeRequestClassIndex OCTET STRING,
         responseTimeRequestClassObjectName OCTET STRING,
         responseTimeRequestClassType OCTET STRING,
         responseTimeRequestClassDeploymentOrder Integer32,
         responseTimeRequestClassGoalMs Integer32,
         responseTimeRequestClassName OCTET STRING,
         responseTimeRequestClassTags OCTET STRING
      }
      
   
   responseTimeRequestClassIndex OBJECT-TYPE
      SYNTAX      OCTET STRING
      MAX-ACCESS  not-accessible
      STATUS      current
      DESCRIPTION "Index column"
      ::= { responseTimeRequestClassEntry 1  }
   
   
   responseTimeRequestClassObjectName OBJECT-TYPE
      SYNTAX      OCTET STRING
      MAX-ACCESS  read-only
      STATUS      current
      DESCRIPTION "ObjectName column"
      ::= { responseTimeRequestClassEntry 2  }
   
   
   responseTimeRequestClassType OBJECT-TYPE
      SYNTAX      OCTET STRING
      MAX-ACCESS  read-only
      STATUS      current
      DESCRIPTION "Returns the type of the MBean. "
      ::= { responseTimeRequestClassEntry 3  }
   
   
   responseTimeRequestClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { responseTimeRequestClassEntry 4  }
   
   
   responseTimeRequestClassGoalMs OBJECT-TYPE
      SYNTAX      Integer32
      MAX-ACCESS  read-only
      STATUS      current
      DESCRIPTION " A response time goal in milliseconds.   You can either define a response time goal or keep the -1 default value, which acts as a placeholder for the response time goal. By doing so, you have not defined the response time goal at run time but can define one later.  "
      ::= { responseTimeRequestClassEntry 5  }
   
   
   responseTimeRequestClassName OBJECT-TYPE
      SYNTAX      OCTET STRING
      MAX-ACCESS  read-only
      STATUS      current
      DESCRIPTION "The user-specified name of this MBean instance.  This name is included as one of the key properties in the MBean's javax.management.ObjectName:  Name=user-specified-name "
      ::= { responseTimeRequestClassEntry 6  }
   
   
   responseTimeRequestClassTags OBJECT-TYPE
      SYNTAX      OCTET STRING
      MAX-ACCESS  read-only
      STATUS      current
      DESCRIPTION "Return all tags on this Configuration MBean "
      ::= { responseTimeRequestClassEntry 7  }
   
   
   safAgentTable OBJECT-TYPE
      SYNTAX      SEQUENCE OF SafAgentEntry
      MAX-ACCESS  not-accessible
      STATUS      current
      DESCRIPTION "This class represents a Store-and-Forward (SAF) agent. A SAF sending agent takes care of storing messages to a persistent storage, forwarding messages to the receiving side, and re-transmitting messages when acknowledgements do not come back in time. A SAF receiving agent takes care of detecting and eliminating duplicate messages sent by the receiving agent, and deliver messages to the final endpoint. "
      ::= { wls 1035  }
      
   
   safAgentEntry OBJECT-TYPE
      SYNTAX      SafAgentEntry
      MAX-ACCESS  not-accessible
      STATUS      current
      DESCRIPTION "Generated SNMP Table Entry."
      INDEX { safAgentIndex}
      ::= { safAgentTable 1 }
      
   SafAgentEntry ::=
      SEQUENCE
      {
         safAgentIndex        OCTET STRING,
         safAgentObjectName   OCTET STRING,
         safAgentType         OCTET STRING,
         safAgentForwardingPausedAtStartup OCTET STRING,
         safAgentDefaultRetryDelayMultiplier OCTET STRING,
         safAgentLoggingEnabled OCTET STRING,
         safAgentBytesThresholdHigh Counter64,
         safAgentWindowInterval Counter64,
         safAgentBytesMaximum Counter64,
         safAgentServiceType  OCTET STRING,
         safAgentMessagesThresholdLow Counter64,
         safAgentMessagesThresholdHigh Counter64,
         safAgentIncomingPausedAtStartup OCTET STRING,
         safAgentReceivingPausedAtStartup OCTET STRING,
         safAgentMessagesMaximum Counter64,
         safAgentName         OCTET STRING,
         safAgentConversationIdleTimeMaximum Counter64,
         safAgentDefaultRetryDelayMaximum Counter64,
         safAgentMaximumMessageSize Integer32,
         safAgentAcknowledgeInterval Counter64,
         safAgentDeploymentOrder Integer32,
         safAgentMessageBufferSize Counter64,
         safAgentWindowSize   Integer32,
         safAgentDefaultTimeToLive Counter64,
         safAgentPagingDirectory OCTET STRING,
         safAgentBytesThresholdLow Counter64,
         safAgentDefaultRetryDelayBase Counter64,
         safAgentMessageCompressionOptions OCTET STRING,
         safAgentPagingMessageCompressionEnabled OCTET STRING,
         safAgentStoreMessageCompressionEnabled OCTET STRING,
         safAgentTags         OCTET STRING
      }
      
   
   safAgentIndex OBJECT-TYPE
      SYNTAX      OCTET STRING
      MAX-ACCESS  not-accessible
      STATUS      current
      DESCRIPTION "Index column"
      ::= { safAgentEntry 1  }
   
   
   safAgentObjectName OBJECT-TYPE
      SYNTAX      OCTET STRING
      MAX-ACCESS  read-only
      STATUS      current
      DESCRIPTION "ObjectName column"
      ::= { safAgentEntry 2  }
   
   
   safAgentType OBJECT-TYPE
      SYNTAX      OCTET STRING
      MAX-ACCESS  read-only
      STATUS      current
      DESCRIPTION "Returns the type of the MBean. "
      ::= { safAgentEntry 3  }
   
   
   safAgentForwardingPausedAtStartup OBJECT-TYPE
      SYNTAX      OCTET STRING
      MAX-ACCESS  read-only
      STATUS      current
      DESCRIPTION "Specifies whether the agent is paused for forwarding messages at the startup time.  When enabled, the sending agent forwards messages. Otherwise, the sending agent does not forward any messages.  If the value is changed and activated, you need to restart any servers to which the MBean is targeted before the value will take effect (even though you do not get a warning in the Console that the server needs to be restarted). "
      ::= { safAgentEntry 4  }
   
   
   safAgentDefaultRetryDelayMultiplier OBJECT-TYPE
      SYNTAX      OCTET STRING
      MAX-ACCESS  read-only
      STATUS      current
      DESCRIPTION "The factor used to multiply the previous delay time to calculate the next delay time to be used.    Applies only to agents with sending capability.    Updating DefaultRetryDelayMuliplier causes connections starting after the update to use the new value.    Range of Values: &gt;= 1. "
      ::= { safAgentEntry 5  }
   
   
   safAgentLoggingEnabled OBJECT-TYPE
      SYNTAX      OCTET STRING
      MAX-ACCESS  read-only
      STATUS      current
      DESCRIPTION "Specifies whether a message is logged in the server log file when a message fails to be forwarded.    If selected, this applies to messages that fail to be forwarded and delivered to the final destination when there is no error handling in a SAF application or the application's error handling fails.    Applies only to agents with receiving capability.    Updating LoggingEnabled causes connections starting after the update to use the new value.   "
      ::= { safAgentEntry 6  }
   
   
   safAgentBytesThresholdHigh OBJECT-TYPE
      SYNTAX      Counter64
      MAX-ACCESS  read-only
      STATUS      current
      DESCRIPTION "The upper threshold value that triggers events based on the number of bytes stored in the SAF agent.    The default value of -1  disables the events for this SAF agent.     Applies only to agents with sending capability.    Updating BytesThresholdHigh affects only new requests.    If the number of bytes exceeds this threshold, the triggered events are:   Log Messages: A message is logged on the server indicating a high threshold condition.   Flow Control: The agent becomes armed and instructs producers to begin decreasing their message flow.     Range of Values: &lt;= BytesMaximum; &gt;= BytesThresholdLow "
      ::= { safAgentEntry 7  }
   
   
   safAgentWindowInterval OBJECT-TYPE
      SYNTAX      Counter64
      MAX-ACCESS  read-only
      STATUS      current
      DESCRIPTION "The maximum amount of time, in milliseconds, that a JMS sending agent waits before forwarding messages in a single batch. For a distributed queue or topic, WindowInterval setting is ignored.  A sending agent waits to forward the message batch until either: (A) the source destination message count is greater than or equal to the configured Window Size; (B) it has waited a specified Window Interval, whichever comes first. "
      ::= { safAgentEntry 8  }
   
   
   safAgentBytesMaximum OBJECT-TYPE
      SYNTAX      Counter64
      MAX-ACCESS  read-only
      STATUS      current
      DESCRIPTION "The maximum bytes quota (total amount of bytes) that can be stored in this SAF agent.    The default value of -1 specifies that there is no WebLogic-imposed limit on the number of bytes that can be stored. However, excessive bytes volume can cause memory saturation, so this value should correspond to the total amount of available system memory relative to the rest of your application load.    Applies only to agents with sending capability.    Updating BytesMaximum affects only new requests.    Range of Values: &gt;= BytesThresholdHigh "
      ::= { safAgentEntry 9  }
   
   
   safAgentServiceType OBJECT-TYPE
      SYNTAX      OCTET STRING
      MAX-ACCESS  read-only
      STATUS      current
      DESCRIPTION "The type of service that this SAF agent provides. JMS requires only a Sending agent on the sending side for messages. Whereas, Web Services Reliable Messaging requires both a Sending and Receiving agent for messages.  Sending-only Configures an agent that stores messages in persistent storage, forwards messages to the receiving side, and re-transmits messages when acknowledgements do not come back in time. Receiving-only Configures an agent that detects and eliminates duplicate messages sent by a receiving agent, and delivers messages to the final destination. Both Configures an agent that has sending and receiving agent functionality.    If the value is changed and activated, you need to restart any servers to which the MBean is targeted before the value will take effect (even though you do not get a warning in the Console that the server needs to be restarted). "
      ::= { safAgentEntry 10  }
   
   
   safAgentMessagesThresholdLow OBJECT-TYPE
      SYNTAX      Counter64
      MAX-ACCESS  read-only
      STATUS      current
      DESCRIPTION "The low threshold that triggers events based on the number of messages stored in the SAF agent.    The default value of -1 disables the events for this SAF agent.     Applies only to agents with sending capability.    Updating MessagesThresholdLow affects only new requests.    If the number of messages falls below this threshold, the triggered events are:   Log Messages: A message is logged on the server indicating that the threshold condition has cleared.   Flow Control: The agent becomes disarmed and instructs producers to begin increasing their message flow.     Range of Values: &lt;= MessagesThresholdHigh. "
      ::= { safAgentEntry 11  }
   
   
   safAgentMessagesThresholdHigh OBJECT-TYPE
      SYNTAX      Counter64
      MAX-ACCESS  read-only
      STATUS      current
      DESCRIPTION "The upper threshold that triggers events based on the number of messages stored in the SAF agent.    The default value of -1 disables the events for this SAF agent.     Applies only to agents with sending capability.    Updating MessagesThresholdHigh affects only new requests.    If the number of messages exceeds this threshold, the triggered events are:   Log Messages: A message is logged on the server indicating a high threshold condition.   Flow Control: The agent becomes armed and instructs producers to begin decreasing their message flow.     Range of Values: &lt;= MessagesMaximum; &gt;= MessagesThresholdLow "
      ::= { safAgentEntry 12  }
   
   
   safAgentIncomingPausedAtStartup OBJECT-TYPE
      SYNTAX      OCTET STRING
      MAX-ACCESS  read-only
      STATUS      current
      DESCRIPTION "Specifies whether the agent is paused for incoming messages at startup time.  When enabled, the sending agent accepts new messages. Otherwise, the sending agent does not accept any new messages.  If the value is changed and activated, you need to restart any servers to which the MBean is targeted before the value will take effect (even though you do not get a warning in the Console that the server needs to be restarted). "
      ::= { safAgentEntry 13  }
   
   
   safAgentReceivingPausedAtStartup OBJECT-TYPE
      SYNTAX      OCTET STRING
      MAX-ACCESS  read-only
      STATUS      current
      DESCRIPTION "Specifies whether the agent is paused for receiving messages at the startup time.  When enabled, the sending agent receives messages. Otherwise, the sending agent does not receive any messages.  If the value is changed and activated, you need to restart any servers to which the MBean is targeted before the value will take effect (even though you do not get a warning in the Console that the server needs to be restarted). "
      ::= { safAgentEntry 14  }
   
   
   safAgentMessagesMaximum OBJECT-TYPE
      SYNTAX      Counter64
      MAX-ACCESS  read-only
      STATUS      current
      DESCRIPTION "The maximum message quota (total amount of messages) that can be stored in this SAF agent.    The default value of -1 specifies that the server instance has no limit on the number of messages that can be stored. However, excessive message volume can cause memory saturation, so this value should correspond to the total amount of available system memory relative to the rest of your application load.    Applies only to sending agents.    Updating the maximum message quota resets the message count so that only requests arriving after the update are charged against the new quota.    Range of Values: &gt;= MessagesThresholdHigh "
      ::= { safAgentEntry 15  }
   
   
   safAgentName OBJECT-TYPE
      SYNTAX      OCTET STRING
      MAX-ACCESS  read-only
      STATUS      current
      DESCRIPTION "The user-specified name of this MBean instance.  This name is included as one of the key properties in the MBean's javax.management.ObjectName:  Name=user-specified-name "
      ::= { safAgentEntry 16  }
   
   
   safAgentConversationIdleTimeMaximum OBJECT-TYPE
      SYNTAX      Counter64
      MAX-ACCESS  read-only
      STATUS      current
      DESCRIPTION "The maximum amount of time allowed, in milliseconds, before a sending side releases the resources used by a conversation.    If there is no activity for a conversation for the specified amount of time, the sending agent releases all resources for that conversation and notifies the receiving agent to do the same.    A value of 0 specifies that resources for a conversation are not released unless the application explicitly closes the conversation.    Updating ConversationIdleTimeMaximum causes connections starting after the update to use the new value.   "
      ::= { safAgentEntry 17  }
   
   
   safAgentDefaultRetryDelayMaximum OBJECT-TYPE
      SYNTAX      Counter64
      MAX-ACCESS  read-only
      STATUS      current
      DESCRIPTION "The maximum amount of time, in milliseconds, between two successive delivery retry attempts.    Applies only to agents with sending capability.    Updating DefaultRetryDelayMaximum causes connections starting after the update to use the new value.    Range of Values: &gt; = RetryDelayBase if RetryDelayMultiplier is not 1.0.  "
      ::= { safAgentEntry 18  }
   
   
   safAgentMaximumMessageSize OBJECT-TYPE
      SYNTAX      Integer32
      MAX-ACCESS  read-only
      STATUS      current
      DESCRIPTION "The maximum number of bytes allowed in individual messages on this SAF agent.    The message size includes the message body, any user-defined properties, and the user-defined JMS header fields: JMSCorrelationID and JMSType.    Producers sending messages that exceed the configured maximum message size for the SAF agent will receive a ResourceAllocationException.    The maximum message size is only enforced for the initial production of a message. Messages that are redirected to an error destination or forwarded to a member of a distributed destination are not checked for size. For instance, if a destination and its corresponding error destination are configured with a maximum message size of 128K bytes and 64K bytes, respectively, a message of 96K bytes could be redirected to the error destination (even though it exceeds the 64K byte maximum), but a producer could not directly send the 96K byte message to the error destination.    Applies only to agents with sending capability.    Updating MaximumMessageSize affects only incoming messages; stored messages are not affected.   "
      ::= { safAgentEntry 19  }
   
   
   safAgentAcknowledgeInterval OBJECT-TYPE
      SYNTAX      Counter64
      MAX-ACCESS  read-only
      STATUS      current
      DESCRIPTION "The maximum interval between two successive acknowledgements sent by the receiving side.    Applies only to agents with receiving capability.    A value of -1 specifies that there is no time limit between successive acknowledgement.    Updating AcknowlegeInterval causes connections starting after the update to use the new value.   "
      ::= { safAgentEntry 20  }
   
   
   safAgentDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { safAgentEntry 21  }
   
   
   safAgentMessageBufferSize OBJECT-TYPE
      SYNTAX      Counter64
      MAX-ACCESS  read-only
      STATUS      current
      DESCRIPTION "The amount of memory used to store message bodies in memory before they are paged out to disk.   A value of -1 (the default) specifies that the server will automatically determine a size based on the maximum heap size of the JVM. This default will be set to either one-third the maximum heap size, or 512 megabytes, whichever is smaller.    The larger the buffer, the more memory JMS will consume when many messages are waiting on queues or topics. Once the buffer is surpassed, JMS may write message bodies to the directory specified by PagingDirectory in an effort to reduce memory usage below this buffer.    Surpassing the buffer size does not stop the JMS server from accepting new messages. It is still possible to run out of memory if messages are arriving faster than they can be written to disk. Users with high messaging loads who wish to support the highest possible availability should consider setting a quota or setting a threshold and enabling flow control.    Applies only to agents with sending capability.    Paging is always supported.     Updating the memory size resets the message count so that only requests arriving after the update are charged against the new memory size.   "
      ::= { safAgentEntry 22  }
   
   
   safAgentWindowSize OBJECT-TYPE
      SYNTAX      Integer32
      MAX-ACCESS  read-only
      STATUS      current
      DESCRIPTION "For JMS messages, the number of messages in a batch. A sending agent waits to forward a message batch until the source destination message count is greater than or equal to this value. For a distributed queue or topic, WindowSize setting is ignored and always internally set to 1 message. For WSRM, the maximum number of unacknowledged messages allowed between a source destination and a target destination during a conversation. "
      ::= { safAgentEntry 23  }
   
   
   safAgentDefaultTimeToLive OBJECT-TYPE
      SYNTAX      Counter64
      MAX-ACCESS  read-only
      STATUS      current
      DESCRIPTION "The default amount of time, in milliseconds, that the agent guarantees to reliably send messages.    A value of 0 means the agent guarantees to reliably send messages for the duration of the conversation.    Updating DefaultTimeToLive causes conversations starting after the update to use the new value.   "
      ::= { safAgentEntry 24  }
   
   
   safAgentPagingDirectory OBJECT-TYPE
      SYNTAX      OCTET STRING
      MAX-ACCESS  read-only
      STATUS      current
      DESCRIPTION " Specifies where message bodies are written when the size of the message bodies in the JMS server exceeds the message buffer size. If unspecified, messages are written to the tmp directory in the host WebLogic Server instance's directory. For example, domainName/servers/servername/tmp.     For best performance, this directory should not be the same as the directory used by the SAF agent's persistent store.    Applies only to agents with sending capability.    If the value is changed and activated, you need to restart any servers to which the MBean is targeted before the value will take effect (even though you do not get a warning in the Console that the server needs to be restarted). "
      ::= { safAgentEntry 25  }
   
   
   safAgentBytesThresholdLow OBJECT-TYPE
      SYNTAX      Counter64
      MAX-ACCESS  read-only
      STATUS      current
      DESCRIPTION "The lower threshold that triggers events based on the number of bytes stored in the SAF agent.    The default value of -1  disables the events for this SAF agent.     Applies only to agents with sending capability.    Updating BytesThresholdLow affects only new requests.    If the number of bytes falls below this threshold, the triggered events are:   Log Messages: A message is logged on the server indicating that the threshold condition has cleared.   Flow Control: The agent becomes disarmed and instructs producers to begin increasing their message flow.     Range of Values: &lt;= BytesThresholdHigh "
      ::= { safAgentEntry 26  }
   
   
   safAgentDefaultRetryDelayBase OBJECT-TYPE
      SYNTAX      Counter64
      MAX-ACCESS  read-only
      STATUS      current
      DESCRIPTION "The amount of time, in milliseconds, between the original delivery attempt and the first retry.    If RetryDelayMultiplier is set to 1, this defines the interval between any two successive retry attempts.    Applies only to agents with sending capability.    Updating DefaultRetryDelayBase causes connections starting after the update to use the new value.    Range of Values: &lt;= RetryDelayMaximum if RetryDelayMultiplier is not 1.0.  "
      ::= { safAgentEntry 27  }
   
   
   safAgentMessageCompressionOptions OBJECT-TYPE
      SYNTAX      OCTET STRING
      MAX-ACCESS  read-only
      STATUS      current
      DESCRIPTION "Specifies the type of message compression used when JMS message body compression is enabled for Persistent Stores and JMS Paging Stores.  Use GZIP_DEFAULT_COMPRESSION to enable message compression using the JDK GZIP API with DEFAULT_COMPRESSION level. Use GZIP_BEST_COMPRESSION to enable message compression using the JDK GZIP API with BEST_COMPRESSION level. Use GZIP_BEST_SPEED to enable message compression using the JDK GZIP API with BEST_SPEED level. Use LZF to enable message compression using Open Source LZF.  "
      ::= { safAgentEntry 28  }
   
   
   safAgentPagingMessageCompressionEnabled OBJECT-TYPE
      SYNTAX      OCTET STRING
      MAX-ACCESS  read-only
      STATUS      current
      DESCRIPTION "Enables the JMS paging store to perform message body compression on persistent and non-persistent messages. When false, the default value, no compression is performed. "
      ::= { safAgentEntry 29  }
   
   
   safAgentStoreMessageCompressionEnabled OBJECT-TYPE
      SYNTAX      OCTET STRING
      MAX-ACCESS  read-only
      STATUS      current
      DESCRIPTION "Enables the JMS store to perform message body compression. When set to false, the default value, no compression is performed. "
      ::= { safAgentEntry 30  }
   
   
   safAgentTags OBJECT-TYPE
      SYNTAX      OCTET STRING
      MAX-ACCESS  read-only
      STATUS      current
      DESCRIPTION "Return all tags on this Configuration MBean "
      ::= { safAgentEntry 31  }
   
   
   wlssnmpAgentDeploymentTable OBJECT-TYPE
      SYNTAX      SEQUENCE OF WlssnmpAgentDeploymentEntry
      MAX-ACCESS  not-accessible
      STATUS      current
      DESCRIPTION "This MBean is an SNMP agent that can be targeted to instances of WebLogic Server.  With SNMP, you configure agents to gather and send data about managed resources in response to a request from managers. You can also configure agents to issue unsolicited reports to managers when they detect predefined thresholds or conditions on a managed resource. In a WebLogic Server domain, you can choose a centralized or de-centralized model for SNMP monitoring and communication: In a centralized model, you create an instance of this MBean and target it only to the Administration Server. This agent communicates with all Managed Servers in the domain. SNMP managers communicate only with the SNMP agent on the Administration Server. This model is convenient but introduces performance overhead in WebLogic Server. In addition, if the Administration Server is unavailable, you cannot monitor the domain through SNMP. In a de-centralized model, you create an instance of this MBean and target it to each Managed Server that you want to monitor. (Alternatively, you can create multiple instances of this MBean and target each instance to an individual Managed Server.) Your SNMP manager must communicate with the agents on individual Managed Servers. To support domains that were created with WebLogic Server release 9.2 and earlier, a domain also hosts a singleton SNMP agent whose scope is the entire domain (see {@link SNMPAgentMBean}). SNMPAgentMBean offers the same features as an instance of this MBean (SNMPAgentDeploymentMBean) that you have targeted as described in the centralized model above. However, the underlying implementation of SNMPAgentMBean is different and it will eventually be deprecated. SNMPAgentMBean is overridden if you target an instance of this MBean to the Administration Server. "
      ::= { wls 1040  }
      
   
   wlssnmpAgentDeploymentEntry OBJECT-TYPE
      SYNTAX      WlssnmpAgentDeploymentEntry
      MAX-ACCESS  not-accessible
      STATUS      current
      DESCRIPTION "Generated SNMP Table Entry."
      INDEX { wlssnmpAgentDeploymentIndex}
      ::= { wlssnmpAgentDeploymentTable 1 }
      
   WlssnmpAgentDeploymentEntry ::=
      SEQUENCE
      {
         wlssnmpAgentDeploymentIndex OCTET STRING,
         wlssnmpAgentDeploymentObjectName OCTET STRING,
         wlssnmpAgentDeploymentType OCTET STRING,
         wlssnmpAgentDeploymentCommunityPrefix OCTET STRING,
         wlssnmpAgentDeploymentAuthenticationProtocol OCTET STRING,
         wlssnmpAgentDeploymentSNMPPort Integer32,
         wlssnmpAgentDeploymentSNMPEngineId OCTET STRING,
         wlssnmpAgentDeploymentSNMPAccessForUserMBeansEnabled OCTET STRING,
         wlssnmpAgentDeploymentLocalizedKeyCacheInvalidationInterval Counter64,
         wlssnmpAgentDeploymentEnabled OCTET STRING,
         wlssnmpAgentDeploymentName OCTET STRING,
         wlssnmpAgentDeploymentInformEnabled OCTET STRING,
         wlssnmpAgentDeploymentSendAutomaticTrapsEnabled OCTET STRING,
         wlssnmpAgentDeploymentInformRetryInterval Integer32,
         wlssnmpAgentDeploymentDeploymentOrder Integer32,
         wlssnmpAgentDeploymentPrivacyProtocol OCTET STRING,
         wlssnmpAgentDeploymentMasterAgentXPort Integer32,
         wlssnmpAgentDeploymentSNMPTrapVersion Integer32,
         wlssnmpAgentDeploymentMaxInformRetryCount Integer32,
         wlssnmpAgentDeploymentCommunityBasedAccessEnabled OCTET STRING,
         wlssnmpAgentDeploymentMibDataRefreshInterval INTEGER,
         wlssnmpAgentDeploymentDebugLevel INTEGER,
         wlssnmpAgentDeploymentServerStatusCheckIntervalFactor INTEGER,
         wlssnmpAgentDeploymentTags OCTET STRING,
         wlssnmpAgentDeploymentListenAddress OCTET STRING
      }
      
   
   wlssnmpAgentDeploymentIndex OBJECT-TYPE
      SYNTAX      OCTET STRING
      MAX-ACCESS  not-accessible
      STATUS      current
      DESCRIPTION "Index column"
      ::= { wlssnmpAgentDeploymentEntry 1  }
   
   
   wlssnmpAgentDeploymentObjectName OBJECT-TYPE
      SYNTAX      OCTET STRING
      MAX-ACCESS  read-only
      STATUS      current
      DESCRIPTION "ObjectName column"
      ::= { wlssnmpAgentDeploymentEntry 2  }
   
   
   wlssnmpAgentDeploymentType OBJECT-TYPE
      SYNTAX      OCTET STRING
      MAX-ACCESS  read-only
      STATUS      current
      DESCRIPTION "Returns the type of the MBean. "
      ::= { wlssnmpAgentDeploymentEntry 3  }
   
   
   wlssnmpAgentDeploymentCommunityPrefix OBJECT-TYPE
      SYNTAX      OCTET STRING
      MAX-ACCESS  read-only
      STATUS      current
      DESCRIPTION "The password (community name) that you want this SNMP agent to use to secure SNMPv1 or v2 communication with SNMP managers. Requires you to enable community based access for this agent.  SNMPv3 does not use community names. Instead, it encrypts user names and passwords in its PDUs.   When you use SNMPv1 or v2, there are two community names that are needed when the WebLogic SNMP agent and SNMP managers interact:    The name that you specify in this community prefix. All SNMP managers must send this name when connecting to this SNMP agent.    The community name that the SNMP manager defines. The SNMP agent must send this name when connecting to the manager. (You supply this community name when you configure a trap destination.)    In addition to using the community prefix as a password, an SNMP agent on an Administration Server uses the prefix to qualify requests from SNMP managers. Because the Administration Server can access data for all WebLogic Server instances in a domain, a request that specifies only an attribute name is potentially ambiguous. For example, the attribute serverUptime exists for each WebLogic Server instance in a domain. To clarify requests that you send to SNMP agents on Administration Servers, use the community prefix as follows:    To request the value of an attribute on a specific Managed Server, when you send a request from an SNMP manager, append the name of the server instance to the community prefix: community_prefix@server_name.    To request the value of an attribute for all server instances in a domain, send a community name with the following form: community_prefix    To secure access to the values of the WebLogic attributes when using the SNMPv1 or v2 protocols, it is recommended that you set community prefix to a value other than public or private.  You cannot specify a null (empty) value for the community prefix when SNMP agent is enabled. If you do not want this agent to receive SNMPv1 or v2 requests, disable community based access. "
      ::= { wlssnmpAgentDeploymentEntry 4  }
   
   
   wlssnmpAgentDeploymentAuthenticationProtocol OBJECT-TYPE
      SYNTAX      OCTET STRING
      MAX-ACCESS  read-only
      STATUS      current
      DESCRIPTION "The protocol that this SNMP agent uses to ensure that only authorized users can request or receive information about your WebLogic Server domain. Applicable only with SNMPv3. The protocol also ensures message integrity and prevents masquerading and reordered, delayed, or replayed messages. To use this protocol when receiving requests from SNMP managers, you must configure credential mapping in the WebLogic Server security realm. To use this protocol when sending responses or notifications, you must configure the security level of your trap destinations. If you do not choose an authentication protocol, then the SNMP agent does not authenticate incoming SNMPv3 requests; anyone can use SNMPv3 to retrieve information about your WebLogic Server domain. "
      ::= { wlssnmpAgentDeploymentEntry 5  }
   
   
   wlssnmpAgentDeploymentSNMPPort OBJECT-TYPE
      SYNTAX      Integer32
      MAX-ACCESS  read-only
      STATUS      current
      DESCRIPTION "The port on which you want this SNMP agent to listen for incoming requests from SNMP managers that use the UDP protocol.  SNMP managers can use this port to ping the SNMP agent and request the status of specific attributes.  If you target this SNMP agent to multiple server instances, and if two or more servers are running on the same computer, WebLogic Server will automatically increment this UDP port value by 1 for each agent. WebLogic Server never assigns port 162 because it is the default port that an agent uses to send notifications. In addition, if any port is already in use, WebLogic Server skips the port and assigns the next available port. For example, if you use the default value of this attribute and then target this agent to ManagedServer1 and ManagedServer2, and if both servers are running on the same computer, then the agent on ManagedServer1 will listen on UDP port 161 and the agent on ManagedServer2 will listen on UDP port 163. The incremented port number is not persisted in the domain's configuration; when WebLogic Server increments port numbers, it does so in the order in which servers are started on the same computer. If WebLogic Server re-assigns the UDP port for an SNMP agent, look in the agent's SNMPAgentRuntimeMBean to see the agent's runtime UDP port. SNMP agents can also communicate through the host server's TCP listen port (7001 by default) or through a TCP port that is configured by a custom network channel. "
      ::= { wlssnmpAgentDeploymentEntry 6  }
   
   
   wlssnmpAgentDeploymentSNMPEngineId OBJECT-TYPE
      SYNTAX      OCTET STRING
      MAX-ACCESS  read-only
      STATUS      current
      DESCRIPTION "An identifier for this SNMP agent that is unique amongst all other SNMP agents in the current WebLogic Server domain. If you use SNMPv3 to send messages to this SNMP agent, you must specify the SNMP engine ID when you configure the SNMP manager. For an SNMP agent on an Administration Server, the default value is the name of the WebLogic Server domain. For an agent on a Managed Server, the default is the name of the server. "
      ::= { wlssnmpAgentDeploymentEntry 7  }
   
   
   wlssnmpAgentDeploymentSNMPAccessForUserMBeansEnabled OBJECT-TYPE
      SYNTAX      OCTET STRING
      MAX-ACCESS  read-only
      STATUS      current
      DESCRIPTION "Configures this SNMP agent to provide read-only access to MBean types that you have created and registered (custom MBeans). If you enable this access, when you register a custom MBean in a WebLogic Server MBeanServer, this SNMP agent dynamically updates a runtime MIB module that WebLogic Server maintains for custom MBeans.  For each custom MBean type, WebLogic Server adds a table to the MIB module. For each instance of the custom MBean, it adds a table row. While WebLogic Server does not persist the MIB as a file or other data structure, the OIDs in the MIB remain constant across server sessions. The MIB module for custom MBeans is managed by a subAgent. Its master agent is this WebLogic Server SNMP agent and it communicates with the master agent through the AgentX port. "
      ::= { wlssnmpAgentDeploymentEntry 8  }
   
   
   wlssnmpAgentDeploymentLocalizedKeyCacheInvalidationInterval OBJECT-TYPE
      SYNTAX      Counter64
      MAX-ACCESS  read-only
      STATUS      current
      DESCRIPTION "The number of milliseconds after which WebLogic Server invalidates its cache of SNMP security keys. Setting a high value creates a risk that users whose credentials have been removed can still access SNMP data. An SNMP security key is an encrypted version of an SNMP agent's engine ID and an authentication password or privacy password. WebLogic Server generates one security key for each entry that you create in the SNMP credential map. When a WebLogic Server SNMP agent receives an SNMPv3 request, it compares the key that is in the request with its WebLogic Server keys. If it finds a match, it processes the request. The SNMP agent also encodes these keys in its responses and notifications. (You configure which keys are encoded when you create a trap destination.) Instead of regenerating the keys for each SNMPv3 communication, WebLogic Server caches the keys. To make sure that the cache contains the latest set of SNMP credentials, WebLogic Server periodically invalidates the cache. After the cache is invalidated, the next time an SNMP agent requests credentials, WebLogic Server regenerates the cache. Note that making a change to the credential map does not automatically update the cache. Instead, the cache is updated only after it has been invalidated. For example, if you update a privacy password in an existing entry in the SNMP credential map, the SNMP agent is not aware of the new password until the key cache is invalidated and regenerated. An SNMP user with the old security password can still access WebLogic Server data until the cache is invalidated. You can invalidate a key immediately instead of waiting for this invalidation interval to expire.  "
      ::= { wlssnmpAgentDeploymentEntry 9  }
   
   
   wlssnmpAgentDeploymentEnabled OBJECT-TYPE
      SYNTAX      OCTET STRING
      MAX-ACCESS  read-only
      STATUS      current
      DESCRIPTION "Specifies whether this SNMP agent is enabled. "
      ::= { wlssnmpAgentDeploymentEntry 10  }
   
   
   wlssnmpAgentDeploymentName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpAgentDeploymentEntry 11  }
   
   
   wlssnmpAgentDeploymentInformEnabled OBJECT-TYPE
      SYNTAX      OCTET STRING
      MAX-ACCESS  read-only
      STATUS      current
      DESCRIPTION "Configures this SNMP agent to send notifications as an INFORM instead of a TRAP. Requires you to specify the agent's SNMPTrapVersion as SNMPv2 or SNMPv3. When an agent sends an INFORM notification, it waits for a confirmation response from the SNMP manager. If it does not receive a response, it resends the INFORM notification. "
      ::= { wlssnmpAgentDeploymentEntry 12  }
   
   
   wlssnmpAgentDeploymentSendAutomaticTrapsEnabled OBJECT-TYPE
      SYNTAX      OCTET STRING
      MAX-ACCESS  read-only
      STATUS      current
      DESCRIPTION "Specifies whether this SNMP agent sends automatically generated notifications to SNMP managers.  The SNMP agent generates automatic notifications when any of the following events occur:   The WebLogic Server instance that is hosting the SNMP agent starts. This type of notification (coldStart) has no variable bindings.  A server instance starts or stops. An SNMP agent on a Managed Server generates these notifications only when its host Managed Server starts or stops. An SNMP agent on an Administration Server generates these notifications when any server in the domain starts or stops. These notification types (serverStart and serverShutdown) contain variable bindings to identify the server that started or stopped and the time at which the notification was generated.   "
      ::= { wlssnmpAgentDeploymentEntry 13  }
   
   
   wlssnmpAgentDeploymentInformRetryInterval OBJECT-TYPE
      SYNTAX      Integer32
      MAX-ACCESS  read-only
      STATUS      current
      DESCRIPTION "The number of milliseconds that this SNMP agent will wait for a response to an INFORM notification. If the agent does not receive a response within the specified interval, it will resend the notification. "
      ::= { wlssnmpAgentDeploymentEntry 14  }
   
   
   wlssnmpAgentDeploymentDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { wlssnmpAgentDeploymentEntry 15  }
   
   
   wlssnmpAgentDeploymentPrivacyProtocol OBJECT-TYPE
      SYNTAX      OCTET STRING
      MAX-ACCESS  read-only
      STATUS      current
      DESCRIPTION "The protocol that this SNMP agent uses to encrypt and unencrypt messages. Applicable only with SNMPv3. Requires you to also use an authentication protocol. To use this protocol when sending responses or notifications, you must also configure the security level of your trap destinations. If you do not choose a privacy protocol, then communication between this agent and managers can be viewed (but not altered) by unauthorized users. "
      ::= { wlssnmpAgentDeploymentEntry 16  }
   
   
   wlssnmpAgentDeploymentMasterAgentXPort OBJECT-TYPE
      SYNTAX      Integer32
      MAX-ACCESS  read-only
      STATUS      current
      DESCRIPTION "The port that this SNMP agent uses to communicate with its subagents. The agent uses subagents to provide access to custom MBeans (MBeans that you create and register) and to other software components. WebLogic Server SNMP agents do not enable users to register their own subagents. "
      ::= { wlssnmpAgentDeploymentEntry 17  }
   
   
   wlssnmpAgentDeploymentSNMPTrapVersion OBJECT-TYPE
      SYNTAX      Integer32
      MAX-ACCESS  read-only
      STATUS      current
      DESCRIPTION "The SNMP notification version that this SNMP agent generates. "
      ::= { wlssnmpAgentDeploymentEntry 18  }
   
   
   wlssnmpAgentDeploymentMaxInformRetryCount OBJECT-TYPE
      SYNTAX      Integer32
      MAX-ACCESS  read-only
      STATUS      current
      DESCRIPTION "The maximum number of times that this SNMP agent will resend INFORM notifications for which it has not received a response. "
      ::= { wlssnmpAgentDeploymentEntry 19  }
   
   
   wlssnmpAgentDeploymentCommunityBasedAccessEnabled OBJECT-TYPE
      SYNTAX      OCTET STRING
      MAX-ACCESS  read-only
      STATUS      current
      DESCRIPTION "Specifies whether this SNMP agent supports SNMPv1 and v2. SNMPv1 and v2 use community strings for authentication. If you disable community strings for this SNMP agent, the agent will process only SNMPv3 requests. If an SNMP manager sends a v1 or v2 message, the agent discards the message and returns an error code to the manager. "
      ::= { wlssnmpAgentDeploymentEntry 20  }
   
   
   wlssnmpAgentDeploymentMibDataRefreshInterval OBJECT-TYPE
      SYNTAX      INTEGER
      MAX-ACCESS  read-only
      STATUS      current
      DESCRIPTION "The minimum number of seconds that this SNMP agent caches OIDs before checking if new ones have been added to the Management Information Base (MIB).  A MIB is a database of all objects that can be managed through SNMP. When you create a new WebLogic Server resource, the SNMP agent assigns a unique OID to the resource and adds it to the MIB. For example, when you create a new server, the SNMP agent adds an OID to the MIB.  This attribute is not used by the SNMP Agent anymore. The SNMP Agent retrieves internal notifications about MBean registrations in the WLS MBeanServers. "
      ::= { wlssnmpAgentDeploymentEntry 21  }
   
   
   wlssnmpAgentDeploymentDebugLevel OBJECT-TYPE
      SYNTAX      INTEGER
      MAX-ACCESS  read-only
      STATUS      current
      DESCRIPTION "The minimum severity of debug messages that this SNMP agent generates.  The SNMP agent writes all debug messages to standard out; they are not written to the WebLogic Server log files. Debug messages provide a detailed description of the SNMP agent's actions. For example, the agent outputs a noncritical message each time it generates a notification.  Valid values are:   0  No debug messages.   1  Fatal messages only.   2  Critical and fatal messages.   3  Non-critical, critical, and, fatal messages.   "
      ::= { wlssnmpAgentDeploymentEntry 22  }
   
   
   wlssnmpAgentDeploymentServerStatusCheckIntervalFactor OBJECT-TYPE
      SYNTAX      INTEGER
      MAX-ACCESS  read-only
      STATUS      current
      DESCRIPTION "The multiplier used to calculate the interval at which this SNMP agent checks for newly started or shut down server instances.  You can enable the SNMP agent to automatically generate serverStartup and serverShutdown notifications when servers start or shut down. See {@link SNMPAgentMBean#isSendAutomaticTrapsEnabled}.  This status check value is multiplied by the MIB Data Refresh Interval to determine the interval:  interval = n * MibDataRefreshInterval  The SNMP Agent uses internal notifications to update itself when a server is restarted so there is no need to poll the server for their status.  For the most frequent interval, specify 1 as the multiplier value. "
      ::= { wlssnmpAgentDeploymentEntry 23  }
   
   
   wlssnmpAgentDeploymentTags OBJECT-TYPE
      SYNTAX      OCTET STRING
      MAX-ACCESS  read-only
      STATUS      current
      DESCRIPTION "Return all tags on this Configuration MBean "
      ::= { wlssnmpAgentDeploymentEntry 24  }
   
   
   wlssnmpAgentDeploymentListenAddress OBJECT-TYPE
      SYNTAX      OCTET STRING
      MAX-ACCESS  read-only
      STATUS      current
      DESCRIPTION "The listen address on which you want this SNMP agent to listen for incoming requests from SNMP managers that use the UDP protocol.  If not specified the Server's ListenAddress is used as the ListenAddress for the SNMPAgent. "
      ::= { wlssnmpAgentDeploymentEntry 25  }
   
   
   wlssnmpAttributeChangeTable OBJECT-TYPE
      SYNTAX      SEQUENCE OF WlssnmpAttributeChangeEntry
      MAX-ACCESS  not-accessible
      STATUS      current
      DESCRIPTION "This class describes the settings to receive MBean-attribute change notification. "
      ::= { wls 1045  }
      
   
   wlssnmpAttributeChangeEntry OBJECT-TYPE
      SYNTAX      WlssnmpAttributeChangeEntry
      MAX-ACCESS  not-accessible
      STATUS      current
      DESCRIPTION "Generated SNMP Table Entry."
      INDEX { wlssnmpAttributeChangeIndex}
      ::= { wlssnmpAttributeChangeTable 1 }
      
   WlssnmpAttributeChangeEntry ::=
      SEQUENCE
      {
         wlssnmpAttributeChangeIndex OCTET STRING,
         wlssnmpAttributeChangeObjectName OCTET STRING,
         wlssnmpAttributeChangeType OCTET STRING,
         wlssnmpAttributeChangeAttributeName OCTET STRING,
         wlssnmpAttributeChangeAttributeMBeanName OCTET STRING,
         wlssnmpAttributeChangeAttributeMBeanType OCTET STRING,
         wlssnmpAttributeChangeName OCTET STRING,
         wlssnmpAttributeChangeTags OCTET STRING
      }
      
   
   wlssnmpAttributeChangeIndex OBJECT-TYPE
      SYNTAX      OCTET STRING
      MAX-ACCESS  not-accessible
      STATUS      current
      DESCRIPTION "Index column"
      ::= { wlssnmpAttributeChangeEntry 1  }
   
   
   wlssnmpAttributeChangeObjectName OBJECT-TYPE
      SYNTAX      OCTET STRING
      MAX-ACCESS  read-only
      STATUS      current
      DESCRIPTION "ObjectName column"
      ::= { wlssnmpAttributeChangeEntry 2  }
   
   
   wlssnmpAttributeChangeType OBJECT-TYPE
      SYNTAX      OCTET STRING
      MAX-ACCESS  read-only
      STATUS      current
      DESCRIPTION "Returns the type of the MBean. "
      ::= { wlssnmpAttributeChangeEntry 3  }
   
   
   wlssnmpAttributeChangeAttributeName OBJECT-TYPE
      SYNTAX      OCTET STRING
      MAX-ACCESS  read-only
      STATUS      current
      DESCRIPTION "The name of the attribute that you want to monitor. This attribute must be in the WebLogic Server MIB. "
      ::= { wlssnmpAttributeChangeEntry 4  }
   
   
   wlssnmpAttributeChangeAttributeMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  Do not enter the full JMX object name of the MBean instance. Instead, enter only the value that you provided when you created the instance. To create unique MBean object names, WebLogic Server encodes several name-value pairs into each object name. One of these pairs is Name=name, and this is the value that you enter for MBean Name. For example:  'MedRec:Name=MedRecServer, Type=ServerRuntime'  In the previous example, specify MedRecServer as the name of the MBean instance. "
      ::= { wlssnmpAttributeChangeEntry 5  }
   
   
   wlssnmpAttributeChangeAttributeMBeanType OBJECT-TYPE
      SYNTAX      OCTET STRING
      MAX-ACCESS  read-only
      STATUS      current
      DESCRIPTION "The MBean type that defines the attribute you want to monitor. Do not include the MBean suffix. For example, specify Server to monitor a ServerMBean.  WebLogic Server does not support using Attribute Change notifications to monitor run-time attributes. Runtime MBeans always include the word Runtime in their names. For example, the ServerRuntime MBean provides access to runtime attributes while the Server MBean provides access to configuration attributes. To monitor changes in an MBean that includes Runtime in its name, use a String Monitor, Gauge Monitor, or Counter Monitor. "
      ::= { wlssnmpAttributeChangeEntry 6  }
   
   
   wlssnmpAttributeChangeName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpAttributeChangeEntry 7  }
   
   
   wlssnmpAttributeChangeTags OBJECT-TYPE
      SYNTAX      OCTET STRING
      MAX-ACCESS  read-only
      STATUS      current
      DESCRIPTION "Return all tags on this Configuration MBean "
      ::= { wlssnmpAttributeChangeEntry 8  }
   
   
   wlssnmpCounterMonitorTable OBJECT-TYPE
      SYNTAX      SEQUENCE OF WlssnmpCounterMonitorEntry
      MAX-ACCESS  not-accessible
      STATUS      current
      DESCRIPTION "This class describes the criteria for a Counter-based Monitor. A notification will be generated when this criteria is satisfied. "
      ::= { wls 1050  }
      
   
   wlssnmpCounterMonitorEntry OBJECT-TYPE
      SYNTAX      WlssnmpCounterMonitorEntry
      MAX-ACCESS  not-accessible
      STATUS      current
      DESCRIPTION "Generated SNMP Table Entry."
      INDEX { wlssnmpCounterMonitorIndex}
      ::= { wlssnmpCounterMonitorTable 1 }
      
   WlssnmpCounterMonitorEntry ::=
      SEQUENCE
      {
         wlssnmpCounterMonitorIndex OCTET STRING,
         wlssnmpCounterMonitorObjectName OCTET STRING,
         wlssnmpCounterMonitorType OCTET STRING,
         wlssnmpCounterMonitorMonitoredAttributeName OCTET STRING,
         wlssnmpCounterMonitorMonitoredMBeanType OCTET STRING,
         wlssnmpCounterMonitorOffset Integer32,
         wlssnmpCounterMonitorModulus Integer32,
         wlssnmpCounterMonitorName OCTET STRING,
         wlssnmpCounterMonitorPollingInterval Integer32,
         wlssnmpCounterMonitorThreshold Integer32,
         wlssnmpCounterMonitorMonitoredMBeanName OCTET STRING,
         wlssnmpCounterMonitorTags OCTET STRING
      }
      
   
   wlssnmpCounterMonitorIndex OBJECT-TYPE
      SYNTAX      OCTET STRING
      MAX-ACCESS  not-accessible
      STATUS      current
      DESCRIPTION "Index column"
      ::= { wlssnmpCounterMonitorEntry 1  }
   
   
   wlssnmpCounterMonitorObjectName OBJECT-TYPE
      SYNTAX      OCTET STRING
      MAX-ACCESS  read-only
      STATUS      current
      DESCRIPTION "ObjectName column"
      ::= { wlssnmpCounterMonitorEntry 2  }
   
   
   wlssnmpCounterMonitorType OBJECT-TYPE
      SYNTAX      OCTET STRING
      MAX-ACCESS  read-only
      STATUS      current
      DESCRIPTION "Returns the type of the MBean. "
      ::= { wlssnmpCounterMonitorEntry 3  }
   
   
   wlssnmpCounterMonitorMonitoredAttributeName OBJECT-TYPE
      SYNTAX      OCTET STRING
      MAX-ACCESS  read-only
      STATUS      current
      DESCRIPTION "The name of an MBean attribute to monitor. This attribute must be in the WebLogic Server MIB. "
      ::= { wlssnmpCounterMonitorEntry 4  }
   
   
   wlssnmpCounterMonitorMonitoredMBeanType OBJECT-TYPE
      SYNTAX      OCTET STRING
      MAX-ACCESS  read-only
      STATUS      current
      DESCRIPTION "The MBean type that defines the attribute you want to monitor. Do not include the MBean suffix. For example, ServerRuntime. "
      ::= { wlssnmpCounterMonitorEntry 5  }
   
   
   wlssnmpCounterMonitorOffset OBJECT-TYPE
      SYNTAX      Integer32
      MAX-ACCESS  read-only
      STATUS      current
      DESCRIPTION "A value to be added to the threshold value each time the observed value equals or exceeds the threshold. "
      ::= { wlssnmpCounterMonitorEntry 6  }
   
   
   wlssnmpCounterMonitorModulus OBJECT-TYPE
      SYNTAX      Integer32
      MAX-ACCESS  read-only
      STATUS      current
      DESCRIPTION "A value to be subtracted from the threshold value when the threshold value is crossed.  If Modulus is 0, a notification is generated each time the agent polls the monitored attribute and its value still exceeds or equals the threshold value.  If Modulus is larger than 0, the value of the modulus is subtracted from the threshold each time the threshold is crossed. "
      ::= { wlssnmpCounterMonitorEntry 7  }
   
   
   wlssnmpCounterMonitorName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpCounterMonitorEntry 8  }
   
   
   wlssnmpCounterMonitorPollingInterval OBJECT-TYPE
      SYNTAX      Integer32
      MAX-ACCESS  read-only
      STATUS      current
      DESCRIPTION "The frequency (in seconds) that WebLogic Server checks the attribute value. "
      ::= { wlssnmpCounterMonitorEntry 9  }
   
   
   wlssnmpCounterMonitorThreshold OBJECT-TYPE
      SYNTAX      Integer32
      MAX-ACCESS  read-only
      STATUS      current
      DESCRIPTION "Specifies a value that triggers the Counter Monitor to generate a notification.  The monitor generates a notification the first time the observed value transitions from below the threshold to at or above the threshold. While the observed value remains at or above the threshold, the Counter Monitor does not generate additional notifications. If the observed value falls below the threshold and then later equals or exceeds the threshold, the SNMP Counter Monitor will generate a notification every time the threshold is crossed.  You can specify an offset value to cause this threshold value to increase each time the observed value equals or exceeds the threshold. The first time the observed value equals or exceeds the new threshold value, this monitor generates a notification and adds the offset value to the new threshold value.  For example, if you set Threshold to 1000 and Offset to 2000, when the observed attribute equals or exceeds 1000, the Counter Monitor sends a notification and increases the threshold to 3000. When the observed attribute equals or exceeds 3000, the Counter Monitor sends a notification and increases the threshold again to 5000. "
      ::= { wlssnmpCounterMonitorEntry 10  }
   
   
   wlssnmpCounterMonitorMonitoredMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  If you target SNMP agents to individual Managed Servers, make sure that the MBean instance you specify is active on the Managed Servers you have targeted. For example, if you specify MServer1 as the name of a ServerRuntimeMBean instance, this monitor will only function if you target an SNMP agent either to the Administration Server or to a Managed Server named MServer1.  Do not enter the full JMX object name of the MBean instance. Instead, enter only the value of the object name's Name=name name-value pair. To create unique MBean object names, WebLogic Server encodes several name-value pairs into each object name. One of these pairs is Name=name. For example:  'MedRec:Name=MedRecServer, Type=ServerRuntime'  In the previous example, specify MedRecServer as the name of the MBean instance. "
      ::= { wlssnmpCounterMonitorEntry 11  }
   
   
   wlssnmpCounterMonitorTags OBJECT-TYPE
      SYNTAX      OCTET STRING
      MAX-ACCESS  read-only
      STATUS      current
      DESCRIPTION "Return all tags on this Configuration MBean "
      ::= { wlssnmpCounterMonitorEntry 12  }
   
   
   wlssnmpGaugeMonitorTable OBJECT-TYPE
      SYNTAX      SEQUENCE OF WlssnmpGaugeMonitorEntry
      MAX-ACCESS  not-accessible
      STATUS      current
      DESCRIPTION "This class describes the criteria for a Gauge-based Monitor. A notification will be generated when this criteria is satisfied. "
      ::= { wls 1055  }
      
   
   wlssnmpGaugeMonitorEntry OBJECT-TYPE
      SYNTAX      WlssnmpGaugeMonitorEntry
      MAX-ACCESS  not-accessible
      STATUS      current
      DESCRIPTION "Generated SNMP Table Entry."
      INDEX { wlssnmpGaugeMonitorIndex}
      ::= { wlssnmpGaugeMonitorTable 1 }
      
   WlssnmpGaugeMonitorEntry ::=
      SEQUENCE
      {
         wlssnmpGaugeMonitorIndex OCTET STRING,
         wlssnmpGaugeMonitorObjectName OCTET STRING,
         wlssnmpGaugeMonitorType OCTET STRING,
         wlssnmpGaugeMonitorThresholdLow Integer32,
         wlssnmpGaugeMonitorMonitoredAttributeName OCTET STRING,
         wlssnmpGaugeMonitorThresholdHigh Integer32,
         wlssnmpGaugeMonitorMonitoredMBeanType OCTET STRING,
         wlssnmpGaugeMonitorName OCTET STRING,
         wlssnmpGaugeMonitorPollingInterval Integer32,
         wlssnmpGaugeMonitorMonitoredMBeanName OCTET STRING,
         wlssnmpGaugeMonitorTags OCTET STRING
      }
      
   
   wlssnmpGaugeMonitorIndex OBJECT-TYPE
      SYNTAX      OCTET STRING
      MAX-ACCESS  not-accessible
      STATUS      current
      DESCRIPTION "Index column"
      ::= { wlssnmpGaugeMonitorEntry 1  }
   
   
   wlssnmpGaugeMonitorObjectName OBJECT-TYPE
      SYNTAX      OCTET STRING
      MAX-ACCESS  read-only
      STATUS      current
      DESCRIPTION "ObjectName column"
      ::= { wlssnmpGaugeMonitorEntry 2  }
   
   
   wlssnmpGaugeMonitorType OBJECT-TYPE
      SYNTAX      OCTET STRING
      MAX-ACCESS  read-only
      STATUS      current
      DESCRIPTION "Returns the type of the MBean. "
      ::= { wlssnmpGaugeMonitorEntry 3  }
   
   
   wlssnmpGaugeMonitorThresholdLow OBJECT-TYPE
      SYNTAX      Integer32
      MAX-ACCESS  read-only
      STATUS      current
      DESCRIPTION "The low threshold at which a notification should be generated. A notification is generated the first time the monitored value is less than or equal to this value.  Subsequent crossings of the low threshold value do not cause additional notifications unless the attribute value becomes equal to or greater than the high threshold value.  "
      ::= { wlssnmpGaugeMonitorEntry 4  }
   
   
   wlssnmpGaugeMonitorMonitoredAttributeName OBJECT-TYPE
      SYNTAX      OCTET STRING
      MAX-ACCESS  read-only
      STATUS      current
      DESCRIPTION "The name of an MBean attribute to monitor. This attribute must be in the WebLogic Server MIB. "
      ::= { wlssnmpGaugeMonitorEntry 5  }
   
   
   wlssnmpGaugeMonitorThresholdHigh OBJECT-TYPE
      SYNTAX      Integer32
      MAX-ACCESS  read-only
      STATUS      current
      DESCRIPTION "The high threshold at which a notification should be generated. A notification is generated the first time the monitored value is equal to or greater than this value. Subsequent crossings of the high threshold value do not cause additional notifications unless the attribute value becomes equal to or less than the low threshold value. "
      ::= { wlssnmpGaugeMonitorEntry 6  }
   
   
   wlssnmpGaugeMonitorMonitoredMBeanType OBJECT-TYPE
      SYNTAX      OCTET STRING
      MAX-ACCESS  read-only
      STATUS      current
      DESCRIPTION "The MBean type that defines the attribute you want to monitor. Do not include the MBean suffix. For example, ServerRuntime. "
      ::= { wlssnmpGaugeMonitorEntry 7  }
   
   
   wlssnmpGaugeMonitorName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpGaugeMonitorEntry 8  }
   
   
   wlssnmpGaugeMonitorPollingInterval OBJECT-TYPE
      SYNTAX      Integer32
      MAX-ACCESS  read-only
      STATUS      current
      DESCRIPTION "The frequency (in seconds) that WebLogic Server checks the attribute value. "
      ::= { wlssnmpGaugeMonitorEntry 9  }
   
   
   wlssnmpGaugeMonitorMonitoredMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  If you target SNMP agents to individual Managed Servers, make sure that the MBean instance you specify is active on the Managed Servers you have targeted. For example, if you specify MServer1 as the name of a ServerRuntimeMBean instance, this monitor will only function if you target an SNMP agent either to the Administration Server or to a Managed Server named MServer1.  Do not enter the full JMX object name of the MBean instance. Instead, enter only the value of the object name's Name=name name-value pair. To create unique MBean object names, WebLogic Server encodes several name-value pairs into each object name. One of these pairs is Name=name. For example:  'MedRec:Name=MedRecServer, Type=ServerRuntime'  In the previous example, specify MedRecServer as the name of the MBean instance. "
      ::= { wlssnmpGaugeMonitorEntry 10  }
   
   
   wlssnmpGaugeMonitorTags OBJECT-TYPE
      SYNTAX      OCTET STRING
      MAX-ACCESS  read-only
      STATUS      current
      DESCRIPTION "Return all tags on this Configuration MBean "
      ::= { wlssnmpGaugeMonitorEntry 11  }
   
   
   wlssnmpLogFilterTable OBJECT-TYPE
      SYNTAX      SEQUENCE OF WlssnmpLogFilterEntry
      MAX-ACCESS  not-accessible
      STATUS      current
      DESCRIPTION "This MBean represents a filter to qualify log messages which are logged to the server logfile. A message must qualify criteria specified as a filter in order to generate a notification. Multiple instances of this MBean can be defined, if needed. If there are multiple instances, a message must qualify atleast one filter to qualify for the server logfile. "
      ::= { wls 1060  }
      
   
   wlssnmpLogFilterEntry OBJECT-TYPE
      SYNTAX      WlssnmpLogFilterEntry
      MAX-ACCESS  not-accessible
      STATUS      current
      DESCRIPTION "Generated SNMP Table Entry."
      INDEX { wlssnmpLogFilterIndex}
      ::= { wlssnmpLogFilterTable 1 }
      
   WlssnmpLogFilterEntry ::=
      SEQUENCE
      {
         wlssnmpLogFilterIndex OCTET STRING,
         wlssnmpLogFilterObjectName OCTET STRING,
         wlssnmpLogFilterType OCTET STRING,
         wlssnmpLogFilterSeverityLevel OCTET STRING,
         wlssnmpLogFilterMessageSubstring OCTET STRING,
         wlssnmpLogFilterName OCTET STRING,
         wlssnmpLogFilterUserIds OCTET STRING,
         wlssnmpLogFilterSubsystemNames OCTET STRING,
         wlssnmpLogFilterMessageIds OCTET STRING,
         wlssnmpLogFilterTags OCTET STRING
      }
      
   
   wlssnmpLogFilterIndex OBJECT-TYPE
      SYNTAX      OCTET STRING
      MAX-ACCESS  not-accessible
      STATUS      current
      DESCRIPTION "Index column"
      ::= { wlssnmpLogFilterEntry 1  }
   
   
   wlssnmpLogFilterObjectName OBJECT-TYPE
      SYNTAX      OCTET STRING
      MAX-ACCESS  read-only
      STATUS      current
      DESCRIPTION "ObjectName column"
      ::= { wlssnmpLogFilterEntry 2  }
   
   
   wlssnmpLogFilterType OBJECT-TYPE
      SYNTAX      OCTET STRING
      MAX-ACCESS  read-only
      STATUS      current
      DESCRIPTION "Returns the type of the MBean. "
      ::= { wlssnmpLogFilterEntry 3  }
   
   
   wlssnmpLogFilterSeverityLevel OBJECT-TYPE
      SYNTAX      OCTET STRING
      MAX-ACCESS  read-only
      STATUS      current
      DESCRIPTION "The minimum severity of a message that causes a WebLogic Server SNMP agent to generate a notification. "
      ::= { wlssnmpLogFilterEntry 4  }
   
   
   wlssnmpLogFilterMessageSubstring OBJECT-TYPE
      SYNTAX      OCTET STRING
      MAX-ACCESS  read-only
      STATUS      current
      DESCRIPTION "A string that is searched for in the message text. Only messages that contain the string are selected. If a string is not specified, all messages are selected. "
      ::= { wlssnmpLogFilterEntry 5  }
   
   
   wlssnmpLogFilterName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpLogFilterEntry 6  }
   
   
   wlssnmpLogFilterUserIds OBJECT-TYPE
      SYNTAX      OCTET STRING
      MAX-ACCESS  read-only
      STATUS      current
      DESCRIPTION "A list of user IDs that causes a WebLogic Server SNMP agent to generate a notification.  Every message includes the user ID from the security context in which the message was generated.  If the user ID field for a message matches one of the user IDs you specify in the filter, WebLogic Server generates a notification.  If this log filter doesn't specify user IDs, WebLogic Server can generate a notification for messages from all user IDs. "
      ::= { wlssnmpLogFilterEntry 7  }
   
   
   wlssnmpLogFilterSubsystemNames OBJECT-TYPE
      SYNTAX      OCTET STRING
      MAX-ACCESS  read-only
      STATUS      current
      DESCRIPTION "A list of subsystems whose messages are selected by this log filter. If none are specified, messages from all subsystems are selected. "
      ::= { wlssnmpLogFilterEntry 8  }
   
   
   wlssnmpLogFilterMessageIds OBJECT-TYPE
      SYNTAX      OCTET STRING
      MAX-ACCESS  read-only
      STATUS      current
      DESCRIPTION "A list of message IDs or ID ranges that cause a WebLogic Server SNMP agent to generate a notification.  If no IDs are specified, this filter selects all message IDs.  Example list: 20,50-100,300 "
      ::= { wlssnmpLogFilterEntry 9  }
   
   
   wlssnmpLogFilterTags OBJECT-TYPE
      SYNTAX      OCTET STRING
      MAX-ACCESS  read-only
      STATUS      current
      DESCRIPTION "Return all tags on this Configuration MBean "
      ::= { wlssnmpLogFilterEntry 10  }
   
   
   wlssnmpProxyTable OBJECT-TYPE
      SYNTAX      SEQUENCE OF WlssnmpProxyEntry
      MAX-ACCESS  not-accessible
      STATUS      current
      DESCRIPTION "This MBean represents an SNMP agent that is proxied by a WebLogic Server SNMP agent. "
      ::= { wls 1065  }
      
   
   wlssnmpProxyEntry OBJECT-TYPE
      SYNTAX      WlssnmpProxyEntry
      MAX-ACCESS  not-accessible
      STATUS      current
      DESCRIPTION "Generated SNMP Table Entry."
      INDEX { wlssnmpProxyIndex}
      ::= { wlssnmpProxyTable 1 }
      
   WlssnmpProxyEntry ::=
      SEQUENCE
      {
         wlssnmpProxyIndex    OCTET STRING,
         wlssnmpProxyObjectName OCTET STRING,
         wlssnmpProxyType     OCTET STRING,
         wlssnmpProxyTimeout  Counter64,
         wlssnmpProxySecurityName OCTET STRING,
         wlssnmpProxyPort     Integer32,
         wlssnmpProxySecurityLevel OCTET STRING,
         wlssnmpProxyOidRoot  OCTET STRING,
         wlssnmpProxyCommunity OCTET STRING,
         wlssnmpProxyName     OCTET STRING,
         wlssnmpProxyTags     OCTET STRING,
         wlssnmpProxyListenAddress OCTET STRING
      }
      
   
   wlssnmpProxyIndex OBJECT-TYPE
      SYNTAX      OCTET STRING
      MAX-ACCESS  not-accessible
      STATUS      current
      DESCRIPTION "Index column"
      ::= { wlssnmpProxyEntry 1  }
   
   
   wlssnmpProxyObjectName OBJECT-TYPE
      SYNTAX      OCTET STRING
      MAX-ACCESS  read-only
      STATUS      current
      DESCRIPTION "ObjectName column"
      ::= { wlssnmpProxyEntry 2  }
   
   
   wlssnmpProxyType OBJECT-TYPE
      SYNTAX      OCTET STRING
      MAX-ACCESS  read-only
      STATUS      current
      DESCRIPTION "Returns the type of the MBean. "
      ::= { wlssnmpProxyEntry 3  }
   
   
   wlssnmpProxyTimeout OBJECT-TYPE
      SYNTAX      Counter64
      MAX-ACCESS  read-only
      STATUS      current
      DESCRIPTION "The number of milliseconds that the WebLogic Server SNMP agent waits for a response to requests that it forwards to this proxy agent.  If the interval elapses without a response, the WebLogic SNMP agent sends an error to the requesting manager. "
      ::= { wlssnmpProxyEntry 4  }
   
   
   wlssnmpProxySecurityName OBJECT-TYPE
      SYNTAX      OCTET STRING
      MAX-ACCESS  read-only
      STATUS      current
      DESCRIPTION "The user name on whose behalf the WebLogic SNMP agent forwards v3 requests.  If not specified, the request is forwarded as a v1 request.  If you specify a security name, you must also specify a security level that is equal to or lower than the security level that is configured for communication between the WebLogic SNMP agent and SNMP managers. For example, if the WebLogic SNMP agent requires incoming SNMPv3 requests to use the authentication protocol but no privacy protocol, the security level for this proxy must be either Authentication Only or None.  Note that if you want to use the authorization  or privacy protocols, you must configure credential mapping in the WebLogic Server security realm.  The WebLogic SNMP agent cannot forward or pass through the credentials that are contained in SNMPv3 requests from SNMP managers. Instead, the agent authenticates and performs other security operations on incoming requests, and then constructs a new request to forward to a proxied agent. "
      ::= { wlssnmpProxyEntry 5  }
   
   
   wlssnmpProxyPort OBJECT-TYPE
      SYNTAX      Integer32
      MAX-ACCESS  read-only
      STATUS      current
      DESCRIPTION "The port number on which this proxied SNMP agent is listening. "
      ::= { wlssnmpProxyEntry 6  }
   
   
   wlssnmpProxySecurityLevel OBJECT-TYPE
      SYNTAX      OCTET STRING
      MAX-ACCESS  read-only
      STATUS      current
      DESCRIPTION "The security level that the proxied SNMP agent expects for the specified security name. "
      ::= { wlssnmpProxyEntry 7  }
   
   
   wlssnmpProxyOidRoot OBJECT-TYPE
      SYNTAX      OCTET STRING
      MAX-ACCESS  read-only
      STATUS      current
      DESCRIPTION "The root of the object identifier (OID) tree that this proxied SNMP agent controls. "
      ::= { wlssnmpProxyEntry 8  }
   
   
   wlssnmpProxyCommunity OBJECT-TYPE
      SYNTAX      OCTET STRING
      MAX-ACCESS  read-only
      STATUS      current
      DESCRIPTION "The community name to be passed on for all SNMPv1 requests to this proxied SNMP agent.  If you specify a security name for this proxied agent, the WebLogic SNMP agent ignores this community name. Instead, the agent encodes the security name in an SNMPv3 request and forwards the SNMPv3 request to this proxied agent. "
      ::= { wlssnmpProxyEntry 9  }
   
   
   wlssnmpProxyName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpProxyEntry 10  }
   
   
   wlssnmpProxyTags OBJECT-TYPE
      SYNTAX      OCTET STRING
      MAX-ACCESS  read-only
      STATUS      current
      DESCRIPTION "Return all tags on this Configuration MBean "
      ::= { wlssnmpProxyEntry 11  }
   
   
   wlssnmpProxyListenAddress OBJECT-TYPE
      SYNTAX      OCTET STRING
      MAX-ACCESS  read-only
      STATUS      current
      DESCRIPTION "The address on which the external SNMP agent for which the WebLogic SNMP Agent is acting as a proxy is listening for incoming requests from SNMP managers that use the UDP protocol.  If not specified the Server's ListenAddress is used as the ListenAddress of the external SNMPAgent. "
      ::= { wlssnmpProxyEntry 12  }
   
   
   wlssnmpStringMonitorTable OBJECT-TYPE
      SYNTAX      SEQUENCE OF WlssnmpStringMonitorEntry
      MAX-ACCESS  not-accessible
      STATUS      current
      DESCRIPTION "This class describes the criteria for a String-based Monitor. A notification is generated when this criteria is satisfied. "
      ::= { wls 1070  }
      
   
   wlssnmpStringMonitorEntry OBJECT-TYPE
      SYNTAX      WlssnmpStringMonitorEntry
      MAX-ACCESS  not-accessible
      STATUS      current
      DESCRIPTION "Generated SNMP Table Entry."
      INDEX { wlssnmpStringMonitorIndex}
      ::= { wlssnmpStringMonitorTable 1 }
      
   WlssnmpStringMonitorEntry ::=
      SEQUENCE
      {
         wlssnmpStringMonitorIndex OCTET STRING,
         wlssnmpStringMonitorObjectName OCTET STRING,
         wlssnmpStringMonitorType OCTET STRING,
         wlssnmpStringMonitorMonitoredAttributeName OCTET STRING,
         wlssnmpStringMonitorMonitoredMBeanType OCTET STRING,
         wlssnmpStringMonitorNotifyDiffer OCTET STRING,
         wlssnmpStringMonitorNotifyMatch OCTET STRING,
         wlssnmpStringMonitorStringToCompare OCTET STRING,
         wlssnmpStringMonitorName OCTET STRING,
         wlssnmpStringMonitorPollingInterval Integer32,
         wlssnmpStringMonitorMonitoredMBeanName OCTET STRING,
         wlssnmpStringMonitorTags OCTET STRING
      }
      
   
   wlssnmpStringMonitorIndex OBJECT-TYPE
      SYNTAX      OCTET STRING
      MAX-ACCESS  not-accessible
      STATUS      current
      DESCRIPTION "Index column"
      ::= { wlssnmpStringMonitorEntry 1  }
   
   
   wlssnmpStringMonitorObjectName OBJECT-TYPE
      SYNTAX      OCTET STRING
      MAX-ACCESS  read-only
      STATUS      current
      DESCRIPTION "ObjectName column"
      ::= { wlssnmpStringMonitorEntry 2  }
   
   
   wlssnmpStringMonitorType OBJECT-TYPE
      SYNTAX      OCTET STRING
      MAX-ACCESS  read-only
      STATUS      current
      DESCRIPTION "Returns the type of the MBean. "
      ::= { wlssnmpStringMonitorEntry 3  }
   
   
   wlssnmpStringMonitorMonitoredAttributeName OBJECT-TYPE
      SYNTAX      OCTET STRING
      MAX-ACCESS  read-only
      STATUS      current
      DESCRIPTION "The name of an MBean attribute to monitor. This attribute must be in the WebLogic Server MIB. "
      ::= { wlssnmpStringMonitorEntry 4  }
   
   
   wlssnmpStringMonitorMonitoredMBeanType OBJECT-TYPE
      SYNTAX      OCTET STRING
      MAX-ACCESS  read-only
      STATUS      current
      DESCRIPTION "The MBean type that defines the attribute you want to monitor. Do not include the MBean suffix. For example, ServerRuntime. "
      ::= { wlssnmpStringMonitorEntry 5  }
   
   
   wlssnmpStringMonitorNotifyDiffer OBJECT-TYPE
      SYNTAX      OCTET STRING
      MAX-ACCESS  read-only
      STATUS      current
      DESCRIPTION "Generates a notification if the value of the monitored attribute and the value of String to Compare are different. "
      ::= { wlssnmpStringMonitorEntry 6  }
   
   
   wlssnmpStringMonitorNotifyMatch OBJECT-TYPE
      SYNTAX      OCTET STRING
      MAX-ACCESS  read-only
      STATUS      current
      DESCRIPTION "Generates a notification if the value of the monitored attribute and the value of String to Compare are the same. "
      ::= { wlssnmpStringMonitorEntry 7  }
   
   
   wlssnmpStringMonitorStringToCompare OBJECT-TYPE
      SYNTAX      OCTET STRING
      MAX-ACCESS  read-only
      STATUS      current
      DESCRIPTION "The string against which the value of the monitored attribute will be compared.  A notification is generated when the criteria specified by Notify Match or Notify Differ is satisfied. "
      ::= { wlssnmpStringMonitorEntry 8  }
   
   
   wlssnmpStringMonitorName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpStringMonitorEntry 9  }
   
   
   wlssnmpStringMonitorPollingInterval OBJECT-TYPE
      SYNTAX      Integer32
      MAX-ACCESS  read-only
      STATUS      current
      DESCRIPTION "The frequency (in seconds) that WebLogic Server checks the attribute value. "
      ::= { wlssnmpStringMonitorEntry 10  }
   
   
   wlssnmpStringMonitorMonitoredMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  If you target SNMP agents to individual Managed Servers, make sure that the MBean instance you specify is active on the Managed Servers you have targeted. For example, if you specify MServer1 as the name of a ServerRuntimeMBean instance, this monitor will only function if you target an SNMP agent either to the Administration Server or to a Managed Server named MServer1.  Do not enter the full JMX object name of the MBean instance. Instead, enter only the value of the object name's Name=name name-value pair. To create unique MBean object names, WebLogic Server encodes several name-value pairs into each object name. One of these pairs is Name=name. For example:  'MedRec:Name=MedRecServer, Type=ServerRuntime'  In the previous example, specify MedRecServer as the name of the MBean instance. "
      ::= { wlssnmpStringMonitorEntry 11  }
   
   
   wlssnmpStringMonitorTags OBJECT-TYPE
      SYNTAX      OCTET STRING
      MAX-ACCESS  read-only
      STATUS      current
      DESCRIPTION "Return all tags on this Configuration MBean "
      ::= { wlssnmpStringMonitorEntry 12  }
   
   
   wlssnmpTrapDestinationTable OBJECT-TYPE
      SYNTAX      SEQUENCE OF WlssnmpTrapDestinationEntry
      MAX-ACCESS  not-accessible
      STATUS      current
      DESCRIPTION "This MBean describes a destination to which an SNMP agent sends SNMP TRAP and INFORM notifications. "
      ::= { wls 1075  }
      
   
   wlssnmpTrapDestinationEntry OBJECT-TYPE
      SYNTAX      WlssnmpTrapDestinationEntry
      MAX-ACCESS  not-accessible
      STATUS      current
      DESCRIPTION "Generated SNMP Table Entry."
      INDEX { wlssnmpTrapDestinationIndex}
      ::= { wlssnmpTrapDestinationTable 1 }
      
   WlssnmpTrapDestinationEntry ::=
      SEQUENCE
      {
         wlssnmpTrapDestinationIndex OCTET STRING,
         wlssnmpTrapDestinationObjectName OCTET STRING,
         wlssnmpTrapDestinationType OCTET STRING,
         wlssnmpTrapDestinationHost OCTET STRING,
         wlssnmpTrapDestinationSecurityName OCTET STRING,
         wlssnmpTrapDestinationPort Integer32,
         wlssnmpTrapDestinationSecurityLevel OCTET STRING,
         wlssnmpTrapDestinationCommunity OCTET STRING,
         wlssnmpTrapDestinationName OCTET STRING,
         wlssnmpTrapDestinationTags OCTET STRING
      }
      
   
   wlssnmpTrapDestinationIndex OBJECT-TYPE
      SYNTAX      OCTET STRING
      MAX-ACCESS  not-accessible
      STATUS      current
      DESCRIPTION "Index column"
      ::= { wlssnmpTrapDestinationEntry 1  }
   
   
   wlssnmpTrapDestinationObjectName OBJECT-TYPE
      SYNTAX      OCTET STRING
      MAX-ACCESS  read-only
      STATUS      current
      DESCRIPTION "ObjectName column"
      ::= { wlssnmpTrapDestinationEntry 2  }
   
   
   wlssnmpTrapDestinationType OBJECT-TYPE
      SYNTAX      OCTET STRING
      MAX-ACCESS  read-only
      STATUS      current
      DESCRIPTION "Returns the type of the MBean. "
      ::= { wlssnmpTrapDestinationEntry 3  }
   
   
   wlssnmpTrapDestinationHost OBJECT-TYPE
      SYNTAX      OCTET STRING
      MAX-ACCESS  read-only
      STATUS      current
      DESCRIPTION "The DNS name or IP address of the computer on which the SNMP manager is running.  The WebLogic SNMP agent sends trap notifications to the host and port that you specify. "
      ::= { wlssnmpTrapDestinationEntry 4  }
   
   
   wlssnmpTrapDestinationSecurityName OBJECT-TYPE
      SYNTAX      OCTET STRING
      MAX-ACCESS  read-only
      STATUS      current
      DESCRIPTION "Specifies the user name that the WebLogic Server SNMP agent encodes into SNMPv3 responses or notifications. Requires you to create a credential map for this user name in the WebLogic Server security realm. The credential map contains an authentication password and an optional privacy password for this user. The user name and passwords must match the credentials required by the SNMP manager that this trap destination represents. "
      ::= { wlssnmpTrapDestinationEntry 5  }
   
   
   wlssnmpTrapDestinationPort OBJECT-TYPE
      SYNTAX      Integer32
      MAX-ACCESS  read-only
      STATUS      current
      DESCRIPTION "The UDP port on which the SNMP manager is listening. "
      ::= { wlssnmpTrapDestinationEntry 6  }
   
   
   wlssnmpTrapDestinationSecurityLevel OBJECT-TYPE
      SYNTAX      OCTET STRING
      MAX-ACCESS  read-only
      STATUS      current
      DESCRIPTION "Specifies the security protocols that the SNMP agent uses when sending SNMPv3 responses or notifications to the SNMP manager that this trap destination represents. Requires you to specify a security name for this trap destination. "
      ::= { wlssnmpTrapDestinationEntry 7  }
   
   
   wlssnmpTrapDestinationCommunity OBJECT-TYPE
      SYNTAX      OCTET STRING
      MAX-ACCESS  read-only
      STATUS      current
      DESCRIPTION "The password (community name) that a WebLogic Server SNMP agent sends to the SNMP manager when the agent generates SNMPv1 or SNMPv2 notifications. The community name that you enter in this trap destination must match the name that the SNMP manager defines. "
      ::= { wlssnmpTrapDestinationEntry 8  }
   
   
   wlssnmpTrapDestinationName OBJECT-TYPE
      SYNTAX      OCTET STRING
      MAX-ACCESS  read-only
      STATUS      current
      DESCRIPTION "The user-specified name of this MBean instance.  This name is included as one of the key properties in the MBean's javax.management.ObjectName:  Name=user-specified-name "
      ::= { wlssnmpTrapDestinationEntry 9  }
   
   
   wlssnmpTrapDestinationTags OBJECT-TYPE
      SYNTAX      OCTET STRING
      MAX-ACCESS  read-only
      STATUS      current
      DESCRIPTION "Return all tags on this Configuration MBean "
      ::= { wlssnmpTrapDestinationEntry 10  }
   
   
   securityConfigurationTable OBJECT-TYPE
      SYNTAX      SEQUENCE OF SecurityConfigurationEntry
      MAX-ACCESS  not-accessible
      STATUS      current
      DESCRIPTION "Provides domain-wide security configuration information. "
      ::= { wls 1080  }
      
   
   securityConfigurationEntry OBJECT-TYPE
      SYNTAX      SecurityConfigurationEntry
      MAX-ACCESS  not-accessible
      STATUS      current
      DESCRIPTION "Generated SNMP Table Entry."
      INDEX { securityConfigurationIndex}
      ::= { securityConfigurationTable 1 }
      
   SecurityConfigurationEntry ::=
      SEQUENCE
      {
         securityConfigurationIndex OCTET STRING,
         securityConfigurationObjectName OCTET STRING,
         securityConfigurationType OCTET STRING,
         securityConfigurationWebAppFilesCaseInsensitive OCTET STRING,
         securityConfigurationCrossDomainSecurityEnabled OCTET STRING,
         securityConfigurationEnforceStrictURLPattern OCTET STRING,
         securityConfigurationConnectionFilter OCTET STRING,
         securityConfigurationConsoleFullDelegationEnabled OCTET STRING,
         securityConfigurationDowngradeUntrustedPrincipals OCTET STRING,
         securityConfigurationName OCTET STRING,
         securityConfigurationConnectionLoggerEnabled OCTET STRING,
         securityConfigurationEnforceValidBasicAuthCredentials OCTET STRING,
         securityConfigurationNodeManagerUsername OCTET STRING,
         securityConfigurationAnonymousAdminLookupEnabled OCTET STRING,
         securityConfigurationCompatibilityConnectionFiltersEnabled OCTET STRING,
         securityConfigurationConnectionFilterRules OCTET STRING,
         securityConfigurationExcludedDomainNames OCTET STRING,
         securityConfigurationClearTextCredentialAccessEnabled OCTET STRING,
         securityConfigurationPrincipalEqualsCaseInsensitive OCTET STRING,
         securityConfigurationPrincipalEqualsCompareDnAndGuid OCTET STRING,
         securityConfigurationUseKSSForDemo OCTET STRING,
         securityConfigurationAdministrativeIdentityDomain OCTET STRING,
         securityConfigurationNonceTimeoutSeconds INTEGER,
         securityConfigurationTags OCTET STRING,
         securityConfigurationIdentityDomainAwareProvidersRequired OCTET STRING,
         securityConfigurationBootAuthenticationRetryCount INTEGER,
         securityConfigurationRemoteAnonymousJNDIEnabled OCTET STRING,
         securityConfigurationBootAuthenticationMaxRetryDelay Counter64
      }
      
   
   securityConfigurationIndex OBJECT-TYPE
      SYNTAX      OCTET STRING
      MAX-ACCESS  not-accessible
      STATUS      current
      DESCRIPTION "Index column"
      ::= { securityConfigurationEntry 1  }
   
   
   securityConfigurationObjectName OBJECT-TYPE
      SYNTAX      OCTET STRING
      MAX-ACCESS  read-only
      STATUS      current
      DESCRIPTION "ObjectName column"
      ::= { securityConfigurationEntry 2  }
   
   
   securityConfigurationType OBJECT-TYPE
      SYNTAX      OCTET STRING
      MAX-ACCESS  read-only
      STATUS      current
      DESCRIPTION "Returns the type of the MBean. "
      ::= { securityConfigurationEntry 3  }
   
   
   securityConfigurationWebAppFilesCaseInsensitive OBJECT-TYPE
      SYNTAX      OCTET STRING
      MAX-ACCESS  read-only
      STATUS      current
      DESCRIPTION "This property defines the case sensitive URL-pattern matching behavior for security constraints, servlets, filters, virtual-hosts, and so on, in the Web application container and external security policies.  Note: This is a Windows-only flag that is provided for backward compatibility when upgrading from pre-9.0 versions of WebLogic Server. On Unix platforms, setting this value to true causes undesired behavior and is not supported.  When the value is set to os, the pattern matching will be case- sensitive on all platforms except the Windows file system.  Note that on non-Windows file systems, WebLogic Server does not enforce case sensitivity and relies on the file system for optimization. As a result, if you have a Windows Samba mount from Unix or Mac OS that has been installed in case-insensitive mode, there is a chance of a security risk. If so, specify case-insensitive lookups by setting this attribute to true.  Note also that this property is used to preserve backward compatibility on Windows file systems only. In prior releases, WebLogic Server was case- insensitive on Windows. As of WebLogic Server 9.0, URL-pattern matching is strictly enforced.  During the upgrade of older domains, the value of this parameter is explicitly set to os by the upgrade plug-in to preserve backward compatibility. "
      ::= { securityConfigurationEntry 4  }
   
   
   securityConfigurationCrossDomainSecurityEnabled OBJECT-TYPE
      SYNTAX      OCTET STRING
      MAX-ACCESS  read-only
      STATUS      current
      DESCRIPTION " Indicates whether or not cross-domain security is enabled. "
      ::= { securityConfigurationEntry 5  }
   
   
   securityConfigurationEnforceStrictURLPattern OBJECT-TYPE
      SYNTAX      OCTET STRING
      MAX-ACCESS  read-only
      STATUS      current
      DESCRIPTION "Whether or not the system should enforce strict URL pattern or not. "
      ::= { securityConfigurationEntry 6  }
   
   
   securityConfigurationConnectionFilter OBJECT-TYPE
      SYNTAX      OCTET STRING
      MAX-ACCESS  read-only
      STATUS      current
      DESCRIPTION "The name of the Java class that implements a connection filter (that is, the weblogic.security.net.ConnectionFilter interface). If no class name is specified, no connection filter will be used.   This attribute replaces the deprecated ConnectionFilter attribute on the SecurityMBean. "
      ::= { securityConfigurationEntry 7  }
   
   
   securityConfigurationConsoleFullDelegationEnabled OBJECT-TYPE
      SYNTAX      OCTET STRING
      MAX-ACCESS  read-only
      STATUS      current
      DESCRIPTION "Indicates whether the console is enabled for fully delegate authorization. "
      ::= { securityConfigurationEntry 8  }
   
   
   securityConfigurationDowngradeUntrustedPrincipals OBJECT-TYPE
      SYNTAX      OCTET STRING
      MAX-ACCESS  read-only
      STATUS      current
      DESCRIPTION "Whether or not to downgrade to anonymous principals that cannot be verified. This is useful for server-server communication between untrusted domains. "
      ::= { securityConfigurationEntry 9  }
   
   
   securityConfigurationName OBJECT-TYPE
      SYNTAX      OCTET STRING
      MAX-ACCESS  read-only
      STATUS      current
      DESCRIPTION "The user-specified name of this MBean instance.  This name is included as one of the key properties in the MBean's javax.management.ObjectName:  Name=user-specified-name "
      ::= { securityConfigurationEntry 10  }
   
   
   securityConfigurationConnectionLoggerEnabled OBJECT-TYPE
      SYNTAX      OCTET STRING
      MAX-ACCESS  read-only
      STATUS      current
      DESCRIPTION "Specifies whether this WebLogic Server domain should log accepted connections.  This attribute can be used by a system administrator to dynamically check the incoming connections in the log file to determine if filtering needs to be performed.   This attribute replaces the deprecated ConnectionLoggerEnabled attribute on the SecurityMBean. "
      ::= { securityConfigurationEntry 11  }
   
   
   securityConfigurationEnforceValidBasicAuthCredentials OBJECT-TYPE
      SYNTAX      OCTET STRING
      MAX-ACCESS  read-only
      STATUS      current
      DESCRIPTION "Whether or not the system should allow requests with invalid Basic Authentication credentials to access unsecure resources. "
      ::= { securityConfigurationEntry 12  }
   
   
   securityConfigurationNodeManagerUsername OBJECT-TYPE
      SYNTAX      OCTET STRING
      MAX-ACCESS  read-only
      STATUS      current
      DESCRIPTION "The user name that the Administration Server uses to communicate with Node Manager when starting, stopping, or restarting Managed Servers.  "
      ::= { securityConfigurationEntry 13  }
   
   
   securityConfigurationAnonymousAdminLookupEnabled OBJECT-TYPE
      SYNTAX      OCTET STRING
      MAX-ACCESS  read-only
      STATUS      current
      DESCRIPTION "Returns true if anonymous JNDI access for Admin MBean home is permitted. This is overridden by the Java property -Dweblogic.management.anonymousAdminLookupEnabled. "
      ::= { securityConfigurationEntry 14  }
   
   
   securityConfigurationCompatibilityConnectionFiltersEnabled OBJECT-TYPE
      SYNTAX      OCTET STRING
      MAX-ACCESS  read-only
      STATUS      current
      DESCRIPTION "Specifies whether this WebLogic Server domain enables compatiblity with previous connection filters.  This attribute changes the protocols names used when filtering needs to be performed. "
      ::= { securityConfigurationEntry 15  }
   
   
   securityConfigurationConnectionFilterRules OBJECT-TYPE
      SYNTAX      OCTET STRING
      MAX-ACCESS  read-only
      STATUS      current
      DESCRIPTION "The rules used by any connection filter that implements the ConnectionFilterRulesListener interface. When using the default implementation and when no rules are specified, all connections are accepted. The default implementation rules are in the format: target localAddress localPort action protocols.   This attribute replaces the deprecated ConnectionFilterRules attribute on the SecurityMBean. "
      ::= { securityConfigurationEntry 16  }
   
   
   securityConfigurationExcludedDomainNames OBJECT-TYPE
      SYNTAX      OCTET STRING
      MAX-ACCESS  read-only
      STATUS      current
      DESCRIPTION " Specifies a list of remote domains for which cross-domain check should not be applied. "
      ::= { securityConfigurationEntry 17  }
   
   
   securityConfigurationClearTextCredentialAccessEnabled OBJECT-TYPE
      SYNTAX      OCTET STRING
      MAX-ACCESS  read-only
      STATUS      current
      DESCRIPTION "Returns true if allow access to credential in clear text. This can be overridden by the system property -Dweblogic.management.clearTextCredentialAccessEnabled "
      ::= { securityConfigurationEntry 18  }
   
   
   securityConfigurationPrincipalEqualsCaseInsensitive OBJECT-TYPE
      SYNTAX      OCTET STRING
      MAX-ACCESS  read-only
      STATUS      current
      DESCRIPTION "Specifies whether the WebLogic Server principal name is compared using a case insensitive match when the equals method for the principal object is performed.  If this attribute is enabled, matches are case insensitive.  Note: Note that principal comparison is not used by the WebLogic Security Service to determine access to protected resources. This attribute is intended for use with JAAS authorization, which may require case insensitive principal matching behavior. "
      ::= { securityConfigurationEntry 19  }
   
   
   securityConfigurationPrincipalEqualsCompareDnAndGuid OBJECT-TYPE
      SYNTAX      OCTET STRING
      MAX-ACCESS  read-only
      STATUS      current
      DESCRIPTION "Specifies whether the GUID and DN data in a WebLogic Server principal object are used when the equals method of that object is invoked.   If enabled, the GUID and DN data (if included among the attributes in a WebLogic Server principal object) and the principal name are compared when this method is invoked. "
      ::= { securityConfigurationEntry 20  }
   
   
   securityConfigurationUseKSSForDemo OBJECT-TYPE
      SYNTAX      OCTET STRING
      MAX-ACCESS  read-only
      STATUS      current
      DESCRIPTION "Determines whether the Demo Identity and Demo Trust key stores should be obtained from the Oracle Key Store Service (KSS).  If enabled, Weblogic Server will request the Demo Identity and Domain Trust key stores from KSS. Subsequent to installation however, the KSS Demo key stores may have been manipulated such that appropriate Demo certificates or keys are not available.  Please verify the following KSS Demo Identity keystore has an X.509 private key and corresponding public identity certificate signed by the Demo Certificate Authority (CA):  KSS Stripe system KSS Key Store demoidentity KSS Private Key Alias DemoIdentity  Please verify the following KSS Domain Trust keystore has a trusted Demo Certificate Authority X.509 certificate:  KSS Stripe system KSS Key Store trust  "
      ::= { securityConfigurationEntry 21  }
   
   
   securityConfigurationAdministrativeIdentityDomain OBJECT-TYPE
      SYNTAX      OCTET STRING
      MAX-ACCESS  read-only
      STATUS      current
      DESCRIPTION "Domain's administrative identity domain. "
      ::= { securityConfigurationEntry 22  }
   
   
   securityConfigurationNonceTimeoutSeconds OBJECT-TYPE
      SYNTAX      INTEGER
      MAX-ACCESS  read-only
      STATUS      current
      DESCRIPTION "Returns the value of the nonce timeout in seconds. "
      ::= { securityConfigurationEntry 23  }
   
   
   securityConfigurationTags OBJECT-TYPE
      SYNTAX      OCTET STRING
      MAX-ACCESS  read-only
      STATUS      current
      DESCRIPTION "Return all tags on this Configuration MBean "
      ::= { securityConfigurationEntry 24  }
   
   
   securityConfigurationIdentityDomainAwareProvidersRequired OBJECT-TYPE
      SYNTAX      OCTET STRING
      MAX-ACCESS  read-only
      STATUS      current
      DESCRIPTION "Returns true if all role mapping, authorization, credential mapping, and audit providers configured in the domain must support the IdentityDomainAwareProviderMBean interface's administrative identity domain. "
      ::= { securityConfigurationEntry 25  }
   
   
   securityConfigurationBootAuthenticationRetryCount OBJECT-TYPE
      SYNTAX      INTEGER
      MAX-ACCESS  read-only
      STATUS      current
      DESCRIPTION "The maximum number of times the boot process will try to authenticate the boot user with the authentication providers. The authentication will be retried only if a failure occurs that indicates the login server is not available. "
      ::= { securityConfigurationEntry 26  }
   
   
   securityConfigurationRemoteAnonymousJNDIEnabled OBJECT-TYPE
      SYNTAX      OCTET STRING
      MAX-ACCESS  read-only
      STATUS      current
      DESCRIPTION "Returns true if remote anonymous JNDI access is permitted for list and modify operations. "
      ::= { securityConfigurationEntry 27  }
   
   
   securityConfigurationBootAuthenticationMaxRetryDelay OBJECT-TYPE
      SYNTAX      Counter64
      MAX-ACCESS  read-only
      STATUS      current
      DESCRIPTION "The maximum length of time, in milliseconds, the boot process will wait before retrying the authentication after a login server not available exception. The boot process will use a backoff algorithm starting at 100 milliseconds increasing on each failure until the delay time reaches the MaxRetryDelay value. "
      ::= { securityConfigurationEntry 28  }
   
   
   selfTuningTable OBJECT-TYPE
      SYNTAX      SEQUENCE OF SelfTuningEntry
      MAX-ACCESS  not-accessible
      STATUS      current
      DESCRIPTION "SelfTuning MBean contains the global work manager component MBeans. "
      ::= { wls 1085  }
      
   
   selfTuningEntry OBJECT-TYPE
      SYNTAX      SelfTuningEntry
      MAX-ACCESS  not-accessible
      STATUS      current
      DESCRIPTION "Generated SNMP Table Entry."
      INDEX { selfTuningIndex}
      ::= { selfTuningTable 1 }
      
   SelfTuningEntry ::=
      SEQUENCE
      {
         selfTuningIndex      OCTET STRING,
         selfTuningObjectName OCTET STRING,
         selfTuningType       OCTET STRING,
         selfTuningName       OCTET STRING,
         selfTuningPartitionFairShare INTEGER,
         selfTuningTags       OCTET STRING
      }
      
   
   selfTuningIndex OBJECT-TYPE
      SYNTAX      OCTET STRING
      MAX-ACCESS  not-accessible
      STATUS      current
      DESCRIPTION "Index column"
      ::= { selfTuningEntry 1  }
   
   
   selfTuningObjectName OBJECT-TYPE
      SYNTAX      OCTET STRING
      MAX-ACCESS  read-only
      STATUS      current
      DESCRIPTION "ObjectName column"
      ::= { selfTuningEntry 2  }
   
   
   selfTuningType OBJECT-TYPE
      SYNTAX      OCTET STRING
      MAX-ACCESS  read-only
      STATUS      current
      DESCRIPTION "Returns the type of the MBean. "
      ::= { selfTuningEntry 3  }
   
   
   selfTuningName OBJECT-TYPE
      SYNTAX      OCTET STRING
      MAX-ACCESS  read-only
      STATUS      current
      DESCRIPTION "The user-specified name of this MBean instance.  This name is included as one of the key properties in the MBean's javax.management.ObjectName:  Name=user-specified-name "
      ::= { selfTuningEntry 4  }
   
   
   selfTuningPartitionFairShare OBJECT-TYPE
      SYNTAX      INTEGER
      MAX-ACCESS  read-only
      STATUS      current
      DESCRIPTION "A desired percentage of thread usage by a partition compared to the thread usage by all partitions. It is recommended that the sum of this value for all the partitions running in a WLS domain add up to 100, but it is not strictly enforced. When they do not add up to 100, WLS assigns thread-usage times to different partitions based on their relative values. This attribute is for use in the global domain only. Use the PartitionWorkManager MBean for specifying partition fair share values for partitions. "
      ::= { selfTuningEntry 5  }
   
   
   selfTuningTags OBJECT-TYPE
      SYNTAX      OCTET STRING
      MAX-ACCESS  read-only
      STATUS      current
      DESCRIPTION "Return all tags on this Configuration MBean "
      ::= { selfTuningEntry 6  }
   
   
   serverDebugTable OBJECT-TYPE
      SYNTAX      SEQUENCE OF ServerDebugEntry
      MAX-ACCESS  not-accessible
      STATUS      current
      DESCRIPTION " Defines the debug attributes that are specific to WebLogic Server.   While all attributes will be supported in adherence with the standard WebLogic Server deprecation policies, the resultant debug content is free to change in both form and content across releases.  "
      ::= { wls 1090  }
      
   
   serverDebugEntry OBJECT-TYPE
      SYNTAX      ServerDebugEntry
      MAX-ACCESS  not-accessible
      STATUS      current
      DESCRIPTION "Generated SNMP Table Entry."
      INDEX { serverDebugIndex}
      ::= { serverDebugTable 1 }
      
   ServerDebugEntry ::=
      SEQUENCE
      {
         serverDebugIndex     OCTET STRING,
         serverDebugObjectName OCTET STRING,
         serverDebugDebugJDBCSQL OCTET STRING,
         serverDebugDebugIIOPConnection OCTET STRING,
         serverDebugDebugJAXPIncludeTime OCTET STRING,
         serverDebugDebugMessagingBridgeRuntime OCTET STRING,
         serverDebugDebugWebAppSecurity OCTET STRING,
         serverDebugDebugMuxerDetail OCTET STRING,
         serverDebugDebugXMLRegistryIncludeLocation OCTET STRING,
         serverDebugDebugJMXRuntime OCTET STRING,
         serverDebugDebugJNDIFactories OCTET STRING,
         serverDebugDebugDiagnosticInstrumentationWeaving OCTET STRING,
         serverDebugDebugJTARecovery OCTET STRING,
         serverDebugClassLoader OCTET STRING,
         serverDebugDebugRADeployment OCTET STRING,
         serverDebugDebugMessagingKernel OCTET STRING,
         serverDebugDebugJTAAPI OCTET STRING,
         serverDebugDebugEjbLocking OCTET STRING,
         serverDebugDebugDescriptor OCTET STRING,
         serverDebugDebugDiagnosticsHarvesterTreeBeanPlugin OCTET STRING,
         serverDebugDebugSAFTransport OCTET STRING,
         serverDebugDebugStoreIOPhysicalVerbose OCTET STRING,
         serverDebugDebugStoreIOPhysical OCTET STRING,
         serverDebugDebugJNDI OCTET STRING,
         serverDebugDebugJTALLR OCTET STRING,
         serverDebugDebugJTARecoveryStackTrace OCTET STRING,
         serverDebugDebugJTATransactionName OCTET STRING,
         serverDebugDebugRAPooling OCTET STRING,
         serverDebugDebugDeploymentServiceTransportHttp OCTET STRING,
         serverDebugDebugDiagnosticCollections OCTET STRING,
         serverDebugDebugJMXCompatibility OCTET STRING,
         serverDebugDebugDRSMessages OCTET STRING,
         serverDebugDebugMessagingBridgeRuntimeVerbose OCTET STRING,
         serverDebugDebugSecurityJACCNonPolicy OCTET STRING,
         serverDebugClassLoaderVerbose OCTET STRING,
         serverDebugDebugXMLEntityCacheUseShortClass OCTET STRING,
         serverDebugDebugJMSWrappers OCTET STRING,
         serverDebugDebugEmbeddedLDAP OCTET STRING,
         serverDebugDebugLeaderElection OCTET STRING,
         serverDebugDebugDiagnosticAccessor OCTET STRING,
         serverDebugDebugDiagnosticWatch OCTET STRING,
         serverDebugDebugJTAJDBC OCTET STRING,
         serverDebugDebugMessagingBridgeStartup OCTET STRING,
         serverDebugDebugXMLRegistryDebugLevel Integer32,
         serverDebugDebugWTCCorbaEx OCTET STRING,
         serverDebugDebugSAFSendingAgent OCTET STRING,
         serverDebugForceGCEachDGCPeriod OCTET STRING,
         serverDebugDebugDiagnosticInstrumentation OCTET STRING,
         serverDebugDebugIIOPReplacer OCTET STRING,
         serverDebugDebugFileDistributionServlet OCTET STRING,
         serverDebugDebugJTAPropagate OCTET STRING,
         serverDebugDebugXMLRegistryIncludeClass OCTET STRING,
         serverDebugDebugXMLEntityCacheDebugLevel Integer32,
         serverDebugDebugJTAHealth OCTET STRING,
         serverDebugDebugEjbSecurity OCTET STRING,
         serverDebugDebugIIOPTransport OCTET STRING,
         serverDebugDebugJDBCRMI OCTET STRING,
         serverDebugDebugJMSCDS OCTET STRING,
         serverDebugDebugXMLEntityCacheDebugName OCTET STRING,
         serverDebugDebugEjbCaching OCTET STRING,
         serverDebugDebugRAXAwork OCTET STRING,
         serverDebugDebugServerMigration OCTET STRING,
         serverDebugDebugEmbeddedLDAPLogToConsole OCTET STRING,
         serverDebugDebugJAXPDebugName OCTET STRING,
         serverDebugDebugRAConnEvents OCTET STRING,
         serverDebugDebugRAXAin OCTET STRING,
         serverDebugDebugJMSConfig OCTET STRING,
         serverDebugClassloaderWebApp OCTET STRING,
         serverDebugDebugJDBCInternal OCTET STRING,
         serverDebugDebugJpaProfile OCTET STRING,
         serverDebugDebugMessagingKernelBoot OCTET STRING,
         serverDebugWebModule OCTET STRING,
         serverDebugDebugReplication OCTET STRING,
         serverDebugDebugFailOver OCTET STRING,
         serverDebugDebugXMLEntityCacheIncludeName OCTET STRING,
         serverDebugDebugSNMPAgent OCTET STRING,
         serverDebugDebugDRSStateTransitions OCTET STRING,
         serverDebugDebugJpaManage OCTET STRING,
         serverDebugDebugJMSCommon OCTET STRING,
         serverDebugDebugJpaRuntime OCTET STRING,
         serverDebugDebugEmbeddedLDAPLogLevel Integer32,
         serverDebugDebugSecurityAdjudicator OCTET STRING,
         serverDebugDebugSAFAdmin OCTET STRING,
         serverDebugDebugEjbPooling OCTET STRING,
         serverDebugDebugWTCtBridgeEx OCTET STRING,
         serverDebugDebugSecuritySAMLLib OCTET STRING,
         serverDebugDebugDiagnosticArchive OCTET STRING,
         serverDebugDebugURLResolution OCTET STRING,
         serverDebugDebugLoadBalancing OCTET STRING,
         serverDebugDebugWebAppModule OCTET STRING,
         serverDebugDebugSecurityService OCTET STRING,
         serverDebugDebugRC4  OCTET STRING,
         serverDebugDebugXMLRegistryIncludeTime OCTET STRING,
         serverDebugDebugJAXPIncludeLocation OCTET STRING,
         serverDebugDebugLoggingConfiguration OCTET STRING,
         serverDebugDebugHttp OCTET STRING,
         serverDebugDebugDiagnosticFileArchive OCTET STRING,
         serverDebugDebugJTAXA OCTET STRING,
         serverDebugDebugIIOPSecurity OCTET STRING,
         serverDebugDebugRAXAout OCTET STRING,
         serverDebugDebugJAXPIncludeName OCTET STRING,
         serverDebugDebugDiagnosticsModule OCTET STRING,
         serverDebugApplicationContainer OCTET STRING,
         serverDebugDebugDeploy OCTET STRING,
         serverDebugDebugDeploymentServiceTransport OCTET STRING,
         serverDebugDebugWTCTDomPdu OCTET STRING,
         serverDebugDebugJTALifecycle OCTET STRING,
         serverDebugDebugJTATLOG OCTET STRING,
         serverDebugDebugRAParsing OCTET STRING,
         serverDebugDebugServerLifeCycle OCTET STRING,
         serverDebugDebugSAFReceivingAgent OCTET STRING,
         serverDebugDebugConnection OCTET STRING,
         serverDebugDebugJMSBoot OCTET STRING,
         serverDebugDebugJMSSAF OCTET STRING,
         serverDebugDebugDiagnosticImage OCTET STRING,
         serverDebugDebugJpaJdbcSchema OCTET STRING,
         serverDebugDebugTunnelingConnection OCTET STRING,
         serverDebugDebugClusterHeartbeats OCTET STRING,
         serverDebugDebugRSA  OCTET STRING,
         serverDebugDebugSecurityEEngine OCTET STRING,
         serverDebugDebugSecurityKeyStore OCTET STRING,
         serverDebugDebugXMLEntityCacheIncludeTime OCTET STRING,
         serverDebugDebugJMSPauseResume OCTET STRING,
         serverDebugDebugLibraries OCTET STRING,
         serverDebugDebugSecurityCredMap OCTET STRING,
         serverDebugDebugConfigurationRuntime OCTET STRING,
         serverDebugDebugDiagnosticLifecycleHandlers OCTET STRING,
         serverDebugDebugConfigurationEdit OCTET STRING,
         serverDebugDebugDiagnosticWlstoreArchive OCTET STRING,
         serverDebugDebugSecurityPasswordPolicy OCTET STRING,
         serverDebugDebugEjbCompilation OCTET STRING,
         serverDebugDebugJpaQuery OCTET STRING,
         serverDebugDebugSSL  OCTET STRING,
         serverDebugDebugRouting OCTET STRING,
         serverDebugDebugJpaDataCache OCTET STRING,
         serverDebugDebugConsensusLeasing OCTET STRING,
         serverDebugDebugDiagnosticInstrumentationEvents OCTET STRING,
         serverDebugDebugStoreIOLogicalBoot OCTET STRING,
         serverDebugDebugEjbSwapping OCTET STRING,
         serverDebugDebugJTANonXA OCTET STRING,
         serverDebugDebugDiagnosticInstrumentationConfig OCTET STRING,
         serverDebugDebugMessaging OCTET STRING,
         serverDebugDebugSecurityCertPath OCTET STRING,
         serverDebugDebugJNDIResolution OCTET STRING,
         serverDebugDebugSNMPProtocolTCP OCTET STRING,
         serverDebugDebugRALocalOut OCTET STRING,
         serverDebugDebugJMXDomain OCTET STRING,
         serverDebugDebugDiagnosticsHarvesterData OCTET STRING,
         serverDebugDebugSecurityRoleMap OCTET STRING,
         serverDebugDebugEjbDeployment OCTET STRING,
         serverDebugDebugSNMPToolkit OCTET STRING,
         serverDebugDebugMuxer OCTET STRING,
         serverDebugMasterDeployer OCTET STRING,
         serverDebugDebugSecuritySAMLCredMap OCTET STRING,
         serverDebugDiagnosticContextDebugMode OCTET STRING,
         serverDebugDebugSecuritySSL OCTET STRING,
         serverDebugDebugDiagnosticJdbcArchive OCTET STRING,
         serverDebugSlaveDeployer OCTET STRING,
         serverDebugDebugJTAXAStackTrace OCTET STRING,
         serverDebugDebugSecurityJACC OCTET STRING,
         serverDebugDebugEjbCmpDeployment OCTET STRING,
         serverDebugType      OCTET STRING,
         serverDebugDebugEmbeddedLDAPWriteOverrideProps OCTET STRING,
         serverDebugDebugSecurityJACCPolicy OCTET STRING,
         serverDebugDebugJMSDispatcher OCTET STRING,
         serverDebugDebugClusterAnnouncements OCTET STRING,
         serverDebugClasspathServlet OCTET STRING,
         serverDebugDebugIIOPTunneling OCTET STRING,
         serverDebugDebugJAXPDebugLevel Integer32,
         serverDebugDebugJ2EEManagement OCTET STRING,
         serverDebugDebugJTAResourceName OCTET STRING,
         serverDebugDebugSecurityEncryptionService OCTET STRING,
         serverDebugDebugJDBCConn OCTET STRING,
         serverDebugDebugDRSUpdateStatus OCTET STRING,
         serverDebugDebugDeploymentServiceStatusUpdates OCTET STRING,
         serverDebugDebugMuxerTimeout OCTET STRING,
         serverDebugDebugSAFStore OCTET STRING,
         serverDebugName      OCTET STRING,
         serverDebugDebugDomainLogHandler OCTET STRING,
         serverDebugDebugWTCConfig OCTET STRING,
         serverDebugDebugJTAGatewayStackTrace OCTET STRING,
         serverDebugDebugMuxerException OCTET STRING,
         serverDebugDebugDRSHeartbeats OCTET STRING,
         serverDebugDebugJTA2PCStackTrace OCTET STRING,
         serverDebugDebugJMSBackEnd OCTET STRING,
         serverDebugDebugXMLEntityCacheIncludeClass OCTET STRING,
         serverDebugDebugCluster OCTET STRING,
         serverDebugDebugJTAResourceHealth OCTET STRING,
         serverDebugDebugRASecurityCtx OCTET STRING,
         serverDebugDebugStoreAdmin OCTET STRING,
         serverDebugClassFinder OCTET STRING,
         serverDebugDebugDeploymentService OCTET STRING,
         serverDebugDebugHttpSessions OCTET STRING,
         serverDebugDebugJMXEdit OCTET STRING,
         serverDebugDebugClusterFragments OCTET STRING,
         serverDebugDebugWTCJatmiEx OCTET STRING,
         serverDebugDebugWTCUData OCTET STRING,
         serverDebugDebugDeploymentServiceInternal OCTET STRING,
         serverDebugDebugSecurityAuditor OCTET STRING,
         serverDebugDebugJpaJdbcSql OCTET STRING,
         serverDebugDebugEjbInvoke OCTET STRING,
         serverDebugDebugRAWork OCTET STRING,
         serverDebugDebugDRSCalls OCTET STRING,
         serverDebugDebugSecurityPredicate OCTET STRING,
         serverDebugDebugXMLRegistryUseShortClass OCTET STRING,
         serverDebugDebugSecurityUserLockout OCTET STRING,
         serverDebugDebugJTANamingStackTrace OCTET STRING,
         serverDebugListenThreadDebug OCTET STRING,
         serverDebugDebugJpaMetaData OCTET STRING,
         serverDebugDebugJTA2PC OCTET STRING,
         serverDebugDebugAppContainer OCTET STRING,
         serverDebugDebugJAXPUseShortClass OCTET STRING,
         serverDebugDebugEventManager OCTET STRING,
         serverDebugDebugJpaEnhance OCTET STRING,
         serverDebugDebugTunnelingConnectionTimeout OCTET STRING,
         serverDebugDebugSecuritySAMLAtn OCTET STRING,
         serverDebugDebugSecurityAtn OCTET STRING,
         serverDebugLogDGCStatistics OCTET STRING,
         serverDebugDebugDiagnosticQuery OCTET STRING,
         serverDebugDebugJMX  OCTET STRING,
         serverDebugDebugXMLRegistryIncludeName OCTET STRING,
         serverDebugDebugDiagnosticInstrumentationWeavingMatches OCTET STRING,
         serverDebugDebugAbbreviation OCTET STRING,
         serverDebugDebugJAXPIncludeClass OCTET STRING,
         serverDebugDebugHttpLogging OCTET STRING,
         serverDebugDebugJpaJdbcJdbc OCTET STRING,
         serverDebugDebugSAFManager OCTET STRING,
         serverDebugDebugPathSvcVerbose OCTET STRING,
         serverDebugDebugWTCGwtEx OCTET STRING,
         serverDebugDebugConnectorService OCTET STRING,
         serverDebugDebugJMSMessagePath OCTET STRING,
         serverDebugDebugJTAMigration OCTET STRING,
         serverDebugDebugSecurityRealm OCTET STRING,
         serverDebugDebugIIOPStartup OCTET STRING,
         serverDebugDebugJDBCDriverLogging OCTET STRING,
         serverDebugDebugJMSModule OCTET STRING,
         serverDebugDebugEjbCmpRuntime OCTET STRING,
         serverDebugDebugWANReplicationDetails OCTET STRING,
         serverDebugDebugJMST3Server OCTET STRING,
         serverDebugDebugXMLEntityCacheIncludeLocation OCTET STRING,
         serverDebugDebugSAFVerbose OCTET STRING,
         serverDebugDebugDRSQueues OCTET STRING,
         serverDebugDebugDiagnosticInstrumentationActions OCTET STRING,
         serverDebugDebugDiagnosticsHarvester OCTET STRING,
         serverDebugDebugEjbMdbConnection OCTET STRING,
         serverDebugDebugJTANaming OCTET STRING,
         serverDebugDebugSecuritySSLEaten OCTET STRING,
         serverDebugDebugEjbTimers OCTET STRING,
         serverDebugDebugJMXCore OCTET STRING,
         serverDebugDebugJpaTool OCTET STRING,
         serverDebugDebugIIOPNaming OCTET STRING,
         serverDebugDebugJTARMI OCTET STRING,
         serverDebugDebugJMSFrontEnd OCTET STRING,
         serverDebugDebugSecuritySAMLService OCTET STRING,
         serverDebugDebugRA   OCTET STRING,
         serverDebugDebugXMLRegistryDebugName OCTET STRING,
         serverDebugDebugSelfTuning OCTET STRING,
         serverDebugDebugIIOPMarshal OCTET STRING,
         serverDebugDebugSecurityAtz OCTET STRING,
         serverDebugDebugIIOPOTS OCTET STRING,
         serverDebugDebugDeployment OCTET STRING,
         serverDebugDebugRAWorkEvents OCTET STRING,
         serverDebugDebugJTAGateway OCTET STRING,
         serverDebugDebugWebAppIdentityAssertion OCTET STRING,
         serverDebugDebugMuxerConnection OCTET STRING,
         serverDebugDebugDiagnosticArchiveRetirement OCTET STRING,
         serverDebugDebugRAPoolVerbose OCTET STRING,
         serverDebugDebugStoreIOLogical OCTET STRING,
         serverDebugDebugRAConnections OCTET STRING,
         serverDebugDebugReplicationDetails OCTET STRING,
         serverDebugDebugDiagnosticsHarvesterMBeanPlugin OCTET STRING,
         serverDebugDebugRALifecycle OCTET STRING,
         serverDebugDebugJMSDistTopic OCTET STRING,
         serverDebugDebugDGCEnrollment OCTET STRING,
         serverDebugDebugPathSvc OCTET STRING,
         serverDebugDebugDiagnosticContext OCTET STRING,
         serverDebugDebugClassRedef OCTET STRING,
         serverDebugDebugSAFMessagePath OCTET STRING,
         serverDebugDebugJMSXA OCTET STRING,
         serverDebugDebugClassSize OCTET STRING,
         serverDebugDebugJMSDurableSubscribers OCTET STRING,
         serverDebugClassChangeNotifier OCTET STRING,
         serverDebugDebugJMSStore OCTET STRING,
         serverDebugDebugAsyncQueue OCTET STRING,
         serverDebugRedefiningClassLoader OCTET STRING,
         serverDebugDebugMaskCriterias OCTET STRING,
         serverDebugDebugSecuritySAML2Lib OCTET STRING,
         serverDebugDebugSecuritySAML2Atn OCTET STRING,
         serverDebugDebugIIOP OCTET STRING,
         serverDebugDebugJMSLocking OCTET STRING,
         serverDebugDefaultStore OCTET STRING,
         serverDebugDebugJMSAME OCTET STRING,
         serverDebugDebugSecuritySAML2CredMap OCTET STRING,
         serverDebugDebugSAFLifeCycle OCTET STRING,
         serverDebugDebugBootstrapServlet OCTET STRING,
         serverDebugDebugStoreXAVerbose OCTET STRING,
         serverDebugDebugServerStartStatistics OCTET STRING,
         serverDebugDebugJMSJDBCScavengeOnFlush OCTET STRING,
         serverDebugDebugStoreXA OCTET STRING,
         serverDebugDebugSecuritySAML2Service OCTET STRING,
         serverDebugDebugRAClassloader OCTET STRING,
         serverDebugDebugWorkContext OCTET STRING,
         serverDebugDebugSNMPExtensionProvider OCTET STRING,
         serverDebugDebugScaContainer OCTET STRING,
         serverDebugDebugDiagnosticDataGathering OCTET STRING,
         serverDebugDebugJDBCRAC OCTET STRING,
         serverDebugDebugJDBCONS OCTET STRING,
         serverDebugDebugMBeanTypeUtilityListener OCTET STRING,
         serverDebugDebugMBeanTypingUtility OCTET STRING,
         serverDebugDebugDiagnosticRuntimeControlService OCTET STRING,
         serverDebugDebugDiagnosticRuntimeControlDriver OCTET STRING,
         serverDebugDebugEjbMetadata OCTET STRING,
         serverDebugDebugManagementServicesResource OCTET STRING,
         serverDebugDebugDeploymentPlan OCTET STRING,
         serverDebugDebugMBeanTypeUtilQueue OCTET STRING,
         serverDebugDebugJDBCReplay OCTET STRING,
         serverDebugDebugCertRevocCheck OCTET STRING,
         serverDebugDebugMBeanTypeUtilQueuePriority OCTET STRING,
         serverDebugDebugJDBCUCP OCTET STRING,
         serverDebugDebugReplicationSize OCTET STRING,
         serverDebugDebugDiagnosticWatchEventsDetails OCTET STRING,
         serverDebugDebugDiagnosticWatchEvents OCTET STRING,
         serverDebugDebugClassLoadingVerbose OCTET STRING,
         serverDebugDebugClassLoadingContextualTrace OCTET STRING,
         serverDebugTags      OCTET STRING,
         serverDebugDebugExpressionBeanLocalizer OCTET STRING,
         serverDebugDebugInterceptors OCTET STRING,
         serverDebugDebugDiagnosticsELContext OCTET STRING,
         serverDebugDebugConcurrentContext OCTET STRING,
         serverDebugDebugReadyApp OCTET STRING,
         serverDebugDebugDiagnosticsExpressionPollerBuffer OCTET STRING,
         serverDebugDebugDiagnosticsUtils OCTET STRING,
         serverDebugDebugDiagnosticsExpressionMetrics OCTET STRING,
         serverDebugDebugConcurrentMSES OCTET STRING,
         serverDebugDebugDynamicSingletonServices OCTET STRING,
         serverDebugDebugJTACDI OCTET STRING,
         serverDebugDebugVerboseRCM OCTET STRING,
         serverDebugDebugDiagnosticsELResolver OCTET STRING,
         serverDebugPartitionDebugLoggingEnabled OCTET STRING,
         serverDebugDebugDiagnosticsExpressionPoller OCTET STRING,
         serverDebugDebugDiagnosticsExpressionFunctionMapper OCTET STRING,
         serverDebugDebugConcurrentTransaction OCTET STRING,
         serverDebugDebugElasticServices OCTET STRING,
         serverDebugDebugMBeanHarvesterResolution OCTET STRING,
         serverDebugDebugBeanTreeHarvesterDataCollection OCTET STRING,
         serverDebugDebugRCM  OCTET STRING,
         serverDebugDebugDiagnosticsScriptAction OCTET STRING,
         serverDebugDebugNodeManagerRuntime OCTET STRING,
         serverDebugDebugRESTNotifications OCTET STRING,
         serverDebugDebugPatchingRuntime OCTET STRING,
         serverDebugDebugConcurrentMES OCTET STRING,
         serverDebugDebugDiagnosticsExpressionFunctions OCTET STRING,
         serverDebugDebugDiagnosticsMBeanELResolver OCTET STRING,
         serverDebugDebugBuzzProtocolHttp OCTET STRING,
         serverDebugDebugDiagnosticsValueTracingELResolver OCTET STRING,
         serverDebugDebugElasticActions OCTET STRING,
         serverDebugDebugConcurrentMTF OCTET STRING,
         serverDebugDebugAppAnnotations OCTET STRING,
         serverDebugDebugBeanTreeHarvesterControl OCTET STRING,
         serverDebugDebugExpressionExtensionsManager OCTET STRING,
         serverDebugDebugMBeanHarvesterControl OCTET STRING,
         serverDebugDebugRestJersey1Integration OCTET STRING,
         serverDebugDebugBeanTreeHarvesterResolution OCTET STRING,
         serverDebugDebugMBeanHarvesterDataCollection OCTET STRING,
         serverDebugDebugLifecycleManager OCTET STRING,
         serverDebugDebugDiagnosticsBeanExtensionResolver OCTET STRING,
         serverDebugDebugJMSDispatcherProxy OCTET STRING,
         serverDebugDebugLocalRemoteJVM OCTET STRING,
         serverDebugDebugMBeanHarvesterThreading OCTET STRING,
         serverDebugDebugRestJersey2Integration OCTET STRING,
         serverDebugDebugBuzzProtocolDetails OCTET STRING,
         serverDebugDebugBeanTreeHarvesterThreading OCTET STRING,
         serverDebugDebugPartitionResourceMetricsRuntime OCTET STRING,
         serverDebugDebugConcurrent OCTET STRING,
         serverDebugDebugBuzzProtocol OCTET STRING,
         serverDebugDebugDiagnosticsBeanInfoProviders OCTET STRING,
         serverDebugDebugMessagingOwnableLock OCTET STRING,
         serverDebugDebugHttpConcise OCTET STRING,
         serverDebugDebugJMXCoreConcise OCTET STRING,
         serverDebugDebugDeploymentConcise OCTET STRING,
         serverDebugDebugRestartInPlace OCTET STRING,
         serverDebugDebugDiagnosticsExpressionEvaluators OCTET STRING,
         serverDebugDebugSituationalConfig OCTET STRING
      }
      
   
   serverDebugIndex OBJECT-TYPE
      SYNTAX      OCTET STRING
      MAX-ACCESS  not-accessible
      STATUS      current
      DESCRIPTION "Index column"
      ::= { serverDebugEntry 1  }
   
   
   serverDebugObjectName OBJECT-TYPE
      SYNTAX      OCTET STRING
      MAX-ACCESS  read-only
      STATUS      current
      DESCRIPTION "ObjectName column"
      ::= { serverDebugEntry 2  }
   
   
   serverDebugDebugJDBCSQL OBJECT-TYPE
      SYNTAX      OCTET STRING
      MAX-ACCESS  read-only
      STATUS      current
      DESCRIPTION "Debug JDBC SQL processing "
      ::= { serverDebugEntry 3  }
   
   
   serverDebugDebugIIOPConnection OBJECT-TYPE
      SYNTAX      OCTET STRING
      MAX-ACCESS  read-only
      STATUS      current
      DESCRIPTION "Debug IIOP connection management processing "
      ::= { serverDebugEntry 4  }
   
   
   serverDebugDebugJAXPIncludeTime OBJECT-TYPE
      SYNTAX      OCTET STRING
      MAX-ACCESS  read-only
      STATUS      current
      DESCRIPTION "JAXP debugging option: Debug IncludeTime "
      ::= { serverDebugEntry 5  }
   
   
   serverDebugDebugMessagingBridgeRuntime OBJECT-TYPE
      SYNTAX      OCTET STRING
      MAX-ACCESS  read-only
      STATUS      current
      DESCRIPTION "Debug Messaging Bridge runtime processing "
      ::= { serverDebugEntry 6  }
   
   
   serverDebugDebugWebAppSecurity OBJECT-TYPE
      SYNTAX      OCTET STRING
      MAX-ACCESS  read-only
      STATUS      current
      DESCRIPTION "Debug webapp security "
      ::= { serverDebugEntry 7  }
   
   
   serverDebugDebugMuxerDetail OBJECT-TYPE
      SYNTAX      OCTET STRING
      MAX-ACCESS  read-only
      STATUS      current
      DESCRIPTION "Detailed debug for Muxer processing "
      ::= { serverDebugEntry 8  }
   
   
   serverDebugDebugXMLRegistryIncludeLocation OBJECT-TYPE
      SYNTAX      OCTET STRING
      MAX-ACCESS  read-only
      STATUS      current
      DESCRIPTION "XML Registry debugging option: Debug IncludeLocation "
      ::= { serverDebugEntry 9  }
   
   
   serverDebugDebugJMXRuntime OBJECT-TYPE
      SYNTAX      OCTET STRING
      MAX-ACCESS  read-only
      STATUS      current
      DESCRIPTION "Debug JMX runtime service processing "
      ::= { serverDebugEntry 10  }
   
   
   serverDebugDebugJNDIFactories OBJECT-TYPE
      SYNTAX      OCTET STRING
      MAX-ACCESS  read-only
      STATUS      current
      DESCRIPTION "Debug JNDI state and object factories. "
      ::= { serverDebugEntry 11  }
   
   
   serverDebugDebugDiagnosticInstrumentationWeaving OBJECT-TYPE
      SYNTAX      OCTET STRING
      MAX-ACCESS  read-only
      STATUS      current
      DESCRIPTION "Debug instrumentation weaving "
      ::= { serverDebugEntry 12  }
   
   
   serverDebugDebugJTARecovery OBJECT-TYPE
      SYNTAX      OCTET STRING
      MAX-ACCESS  read-only
      STATUS      current
      DESCRIPTION "Debug JTA Recovery processing "
      ::= { serverDebugEntry 13  }
   
   
   serverDebugClassLoader OBJECT-TYPE
      SYNTAX      OCTET STRING
      MAX-ACCESS  read-only
      STATUS      current
      DESCRIPTION "Debug ClassLoader processing "
      ::= { serverDebugEntry 14  }
   
   
   serverDebugDebugRADeployment OBJECT-TYPE
      SYNTAX      OCTET STRING
      MAX-ACCESS  read-only
      STATUS      current
      DESCRIPTION "Debug Resource Adapter (un)deploy, security id settings "
      ::= { serverDebugEntry 15  }
   
   
   serverDebugDebugMessagingKernel OBJECT-TYPE
      SYNTAX      OCTET STRING
      MAX-ACCESS  read-only
      STATUS      current
      DESCRIPTION "Debugging for the messaging kernel. The messaging kernel is low- level messaging code that is used by the JMS and store and forward subsystems. "
      ::= { serverDebugEntry 16  }
   
   
   serverDebugDebugJTAAPI OBJECT-TYPE
      SYNTAX      OCTET STRING
      MAX-ACCESS  read-only
      STATUS      current
      DESCRIPTION "Debug JTA external API "
      ::= { serverDebugEntry 17  }
   
   
   serverDebugDebugEjbLocking OBJECT-TYPE
      SYNTAX      OCTET STRING
      MAX-ACCESS  read-only
      STATUS      current
      DESCRIPTION "Debug EJB locking "
      ::= { serverDebugEntry 18  }
   
   
   serverDebugDebugDescriptor OBJECT-TYPE
      SYNTAX      OCTET STRING
      MAX-ACCESS  read-only
      STATUS      current
      DESCRIPTION "Debug descriptor framework processing "
      ::= { serverDebugEntry 19  }
   
   
   serverDebugDebugDiagnosticsHarvesterTreeBeanPlugin OBJECT-TYPE
      SYNTAX      OCTET STRING
      MAX-ACCESS  read-only
      STATUS      current
      DESCRIPTION "Debug tree bean harvester processing "
      ::= { serverDebugEntry 20  }
   
   
   serverDebugDebugSAFTransport OBJECT-TYPE
      SYNTAX      OCTET STRING
      MAX-ACCESS  read-only
      STATUS      current
      DESCRIPTION "Debug Messaging SAF Transport. "
      ::= { serverDebugEntry 21  }
   
   
   serverDebugDebugStoreIOPhysicalVerbose OBJECT-TYPE
      SYNTAX      OCTET STRING
      MAX-ACCESS  read-only
      STATUS      current
      DESCRIPTION "Detailed debug for persistent store low-level physical operations which typically directly correspond to file or JDBC operations. This will produce a great deal of debugging for every disk I/O performed by the store. Multiple logical operations may occur in a single physical operation. "
      ::= { serverDebugEntry 22  }
   
   
   serverDebugDebugStoreIOPhysical OBJECT-TYPE
      SYNTAX      OCTET STRING
      MAX-ACCESS  read-only
      STATUS      current
      DESCRIPTION "Debugging for persistent store low-level physical operations which typically directly correspond to file or JDBC operations. Multiple logical operations may occur in a single physical operation. "
      ::= { serverDebugEntry 23  }
   
   
   serverDebugDebugJNDI OBJECT-TYPE
      SYNTAX      OCTET STRING
      MAX-ACCESS  read-only
      STATUS      current
      DESCRIPTION "Debug basic naming service machinery. "
      ::= { serverDebugEntry 24  }
   
   
   serverDebugDebugJTALLR OBJECT-TYPE
      SYNTAX      OCTET STRING
      MAX-ACCESS  read-only
      STATUS      current
      DESCRIPTION "Debug JTA Logging Last Resource  "
      ::= { serverDebugEntry 25  }
   
   
   serverDebugDebugJTARecoveryStackTrace OBJECT-TYPE
      SYNTAX      OCTET STRING
      MAX-ACCESS  read-only
      STATUS      current
      DESCRIPTION "Detailed debug of JTA Recovery processing "
      ::= { serverDebugEntry 26  }
   
   
   serverDebugDebugJTATransactionName OBJECT-TYPE
      SYNTAX      OCTET STRING
      MAX-ACCESS  read-only
      STATUS      current
      DESCRIPTION "Debug JTA Transaction name filter processing "
      ::= { serverDebugEntry 27  }
   
   
   serverDebugDebugRAPooling OBJECT-TYPE
      SYNTAX      OCTET STRING
      MAX-ACCESS  read-only
      STATUS      current
      DESCRIPTION "Debug Resource Adapter operations on a connection pool (proxy testing) "
      ::= { serverDebugEntry 28  }
   
   
   serverDebugDebugDeploymentServiceTransportHttp OBJECT-TYPE
      SYNTAX      OCTET STRING
      MAX-ACCESS  read-only
      STATUS      current
      DESCRIPTION "Debug deployment service HTTP transport processing "
      ::= { serverDebugEntry 29  }
   
   
   serverDebugDebugDiagnosticCollections OBJECT-TYPE
      SYNTAX      OCTET STRING
      MAX-ACCESS  read-only
      STATUS      current
      DESCRIPTION "Debug diagnostic collection processing "
      ::= { serverDebugEntry 30  }
   
   
   serverDebugDebugJMXCompatibility OBJECT-TYPE
      SYNTAX      OCTET STRING
      MAX-ACCESS  read-only
      STATUS      current
      DESCRIPTION "Debug JMX CompatibilityMBeanServer service processing "
      ::= { serverDebugEntry 31  }
   
   
   serverDebugDebugDRSMessages OBJECT-TYPE
      SYNTAX      OCTET STRING
      MAX-ACCESS  read-only
      STATUS      current
      DESCRIPTION "Debug DRS Message traffic. "
      ::= { serverDebugEntry 32  }
   
   
   serverDebugDebugMessagingBridgeRuntimeVerbose OBJECT-TYPE
      SYNTAX      OCTET STRING
      MAX-ACCESS  read-only
      STATUS      current
      DESCRIPTION "Detailed debug of Messaging Bridge runtime processing "
      ::= { serverDebugEntry 33  }
   
   
   serverDebugDebugSecurityJACCNonPolicy OBJECT-TYPE
      SYNTAX      OCTET STRING
      MAX-ACCESS  read-only
      STATUS      current
      DESCRIPTION "Debug Security Framework JACC nonPolicy processing "
      ::= { serverDebugEntry 34  }
   
   
   serverDebugClassLoaderVerbose OBJECT-TYPE
      SYNTAX      OCTET STRING
      MAX-ACCESS  read-only
      STATUS      current
      DESCRIPTION "Detailed debug of ClassLoader processing "
      ::= { serverDebugEntry 35  }
   
   
   serverDebugDebugXMLEntityCacheUseShortClass OBJECT-TYPE
      SYNTAX      OCTET STRING
      MAX-ACCESS  read-only
      STATUS      current
      DESCRIPTION "XMLEntityCache debugging option: Debug UseShortClass "
      ::= { serverDebugEntry 36  }
   
   
   serverDebugDebugJMSWrappers OBJECT-TYPE
      SYNTAX      OCTET STRING
      MAX-ACCESS  read-only
      STATUS      current
      DESCRIPTION "Debug the pooling and wrapping of JMS connections, sessions, and other objects. This feature is enabled when a JMS connection factory, from any vendor, is used inside an EJB or a servlet using the 'resource-reference' element in the deployment descriptor. "
      ::= { serverDebugEntry 37  }
   
   
   serverDebugDebugEmbeddedLDAP OBJECT-TYPE
      SYNTAX      OCTET STRING
      MAX-ACCESS  read-only
      STATUS      current
      DESCRIPTION "Debug Embedded LDAP processing "
      ::= { serverDebugEntry 38  }
   
   
   serverDebugDebugLeaderElection OBJECT-TYPE
      SYNTAX      OCTET STRING
      MAX-ACCESS  read-only
      STATUS      current
      DESCRIPTION "Debug the cluster leader election messages. "
      ::= { serverDebugEntry 39  }
   
   
   serverDebugDebugDiagnosticAccessor OBJECT-TYPE
      SYNTAX      OCTET STRING
      MAX-ACCESS  read-only
      STATUS      current
      DESCRIPTION "Debug diagnostic accessor processing "
      ::= { serverDebugEntry 40  }
   
   
   serverDebugDebugDiagnosticWatch OBJECT-TYPE
      SYNTAX      OCTET STRING
      MAX-ACCESS  read-only
      STATUS      current
      DESCRIPTION "Debug diagnostic policy processing. "
      ::= { serverDebugEntry 41  }
   
   
   serverDebugDebugJTAJDBC OBJECT-TYPE
      SYNTAX      OCTET STRING
      MAX-ACCESS  read-only
      STATUS      current
      DESCRIPTION "Debug JTA JDBC processing "
      ::= { serverDebugEntry 42  }
   
   
   serverDebugDebugMessagingBridgeStartup OBJECT-TYPE
      SYNTAX      OCTET STRING
      MAX-ACCESS  read-only
      STATUS      current
      DESCRIPTION "Debug Messaging Bridge start up processing "
      ::= { serverDebugEntry 43  }
   
   
   serverDebugDebugXMLRegistryDebugLevel OBJECT-TYPE
      SYNTAX      Integer32
      MAX-ACCESS  read-only
      STATUS      current
      DESCRIPTION "XML Registry debugging option: Debug levels "
      ::= { serverDebugEntry 44  }
   
   
   serverDebugDebugWTCCorbaEx OBJECT-TYPE
      SYNTAX      OCTET STRING
      MAX-ACCESS  read-only
      STATUS      current
      DESCRIPTION "Debug WTC corba execution "
      ::= { serverDebugEntry 45  }
   
   
   serverDebugDebugSAFSendingAgent OBJECT-TYPE
      SYNTAX      OCTET STRING
      MAX-ACCESS  read-only
      STATUS      current
      DESCRIPTION "Debug Messaging SAF SendingAgent. "
      ::= { serverDebugEntry 46  }
   
   
   serverDebugForceGCEachDGCPeriod OBJECT-TYPE
      SYNTAX      OCTET STRING
      MAX-ACCESS  read-only
      STATUS      current
      DESCRIPTION "Force VM garbage collection on each DGC interval "
      ::= { serverDebugEntry 47  }
   
   
   serverDebugDebugDiagnosticInstrumentation OBJECT-TYPE
      SYNTAX      OCTET STRING
      MAX-ACCESS  read-only
      STATUS      current
      DESCRIPTION "Debug diagnostic instrumentation processing "
      ::= { serverDebugEntry 48  }
   
   
   serverDebugDebugIIOPReplacer OBJECT-TYPE
      SYNTAX      OCTET STRING
      MAX-ACCESS  read-only
      STATUS      current
      DESCRIPTION "Debug IIOP object replacement processing "
      ::= { serverDebugEntry 49  }
   
   
   serverDebugDebugFileDistributionServlet OBJECT-TYPE
      SYNTAX      OCTET STRING
      MAX-ACCESS  read-only
      STATUS      current
      DESCRIPTION "Debug the file distribution servlet that runs on the Admin Server and is invoked over HTTP by a booting managed server. "
      ::= { serverDebugEntry 50  }
   
   
   serverDebugDebugJTAPropagate OBJECT-TYPE
      SYNTAX      OCTET STRING
      MAX-ACCESS  read-only
      STATUS      current
      DESCRIPTION "Debug JTA transaction propagation "
      ::= { serverDebugEntry 51  }
   
   
   serverDebugDebugXMLRegistryIncludeClass OBJECT-TYPE
      SYNTAX      OCTET STRING
      MAX-ACCESS  read-only
      STATUS      current
      DESCRIPTION "XML Registry debugging option: Debug IncludeClass "
      ::= { serverDebugEntry 52  }
   
   
   serverDebugDebugXMLEntityCacheDebugLevel OBJECT-TYPE
      SYNTAX      Integer32
      MAX-ACCESS  read-only
      STATUS      current
      DESCRIPTION "XMLEntityCache debugging option: Debug level "
      ::= { serverDebugEntry 53  }
   
   
   serverDebugDebugJTAHealth OBJECT-TYPE
      SYNTAX      OCTET STRING
      MAX-ACCESS  read-only
      STATUS      current
      DESCRIPTION "Debug JTA Health Monitoring "
      ::= { serverDebugEntry 54  }
   
   
   serverDebugDebugEjbSecurity OBJECT-TYPE
      SYNTAX      OCTET STRING
      MAX-ACCESS  read-only
      STATUS      current
      DESCRIPTION "Debug EJB Security "
      ::= { serverDebugEntry 55  }
   
   
   serverDebugDebugIIOPTransport OBJECT-TYPE
      SYNTAX      OCTET STRING
      MAX-ACCESS  read-only
      STATUS      current
      DESCRIPTION "Debug IIOP message processing "
      ::= { serverDebugEntry 56  }
   
   
   serverDebugDebugJDBCRMI OBJECT-TYPE
      SYNTAX      OCTET STRING
      MAX-ACCESS  read-only
      STATUS      current
      DESCRIPTION "Debug JDBC RMI processing "
      ::= { serverDebugEntry 57  }
   
   
   serverDebugDebugJMSCDS OBJECT-TYPE
      SYNTAX      OCTET STRING
      MAX-ACCESS  read-only
      STATUS      current
      DESCRIPTION "Debug JMS CDS processing "
      ::= { serverDebugEntry 58  }
   
   
   serverDebugDebugXMLEntityCacheDebugName OBJECT-TYPE
      SYNTAX      OCTET STRING
      MAX-ACCESS  read-only
      STATUS      current
      DESCRIPTION "XMLEntityCache debugging option: Debug name "
      ::= { serverDebugEntry 59  }
   
   
   serverDebugDebugEjbCaching OBJECT-TYPE
      SYNTAX      OCTET STRING
      MAX-ACCESS  read-only
      STATUS      current
      DESCRIPTION "Debug EJB Caching "
      ::= { serverDebugEntry 60  }
   
   
   serverDebugDebugRAXAwork OBJECT-TYPE
      SYNTAX      OCTET STRING
      MAX-ACCESS  read-only
      STATUS      current
      DESCRIPTION "Debug Resource Adapter XA Work request processing "
      ::= { serverDebugEntry 61  }
   
   
   serverDebugDebugServerMigration OBJECT-TYPE
      SYNTAX      OCTET STRING
      MAX-ACCESS  read-only
      STATUS      current
      DESCRIPTION "Debug low-level Server Migration processing "
      ::= { serverDebugEntry 62  }
   
   
   serverDebugDebugEmbeddedLDAPLogToConsole OBJECT-TYPE
      SYNTAX      OCTET STRING
      MAX-ACCESS  read-only
      STATUS      current
      DESCRIPTION "Debug Embedded LDAP processing (output to console) "
      ::= { serverDebugEntry 63  }
   
   
   serverDebugDebugJAXPDebugName OBJECT-TYPE
      SYNTAX      OCTET STRING
      MAX-ACCESS  read-only
      STATUS      current
      DESCRIPTION "JAXP debugging option: Debug name "
      ::= { serverDebugEntry 64  }
   
   
   serverDebugDebugRAConnEvents OBJECT-TYPE
      SYNTAX      OCTET STRING
      MAX-ACCESS  read-only
      STATUS      current
      DESCRIPTION "Debug Resource Adapter connection event processing "
      ::= { serverDebugEntry 65  }
   
   
   serverDebugDebugRAXAin OBJECT-TYPE
      SYNTAX      OCTET STRING
      MAX-ACCESS  read-only
      STATUS      current
      DESCRIPTION "Debug Resource Adapter XA incoming message processing "
      ::= { serverDebugEntry 66  }
   
   
   serverDebugDebugJMSConfig OBJECT-TYPE
      SYNTAX      OCTET STRING
      MAX-ACCESS  read-only
      STATUS      current
      DESCRIPTION "Debug JMSConfig processing "
      ::= { serverDebugEntry 67  }
   
   
   serverDebugClassloaderWebApp OBJECT-TYPE
      SYNTAX      OCTET STRING
      MAX-ACCESS  read-only
      STATUS      current
      DESCRIPTION "Debug WebApp ClassLoader processing "
      ::= { serverDebugEntry 68  }
   
   
   serverDebugDebugJDBCInternal OBJECT-TYPE
      SYNTAX      OCTET STRING
      MAX-ACCESS  read-only
      STATUS      current
      DESCRIPTION "Debug JDBC Internal processing "
      ::= { serverDebugEntry 69  }
   
   
   serverDebugDebugJpaProfile OBJECT-TYPE
      SYNTAX      OCTET STRING
      MAX-ACCESS  read-only
      STATUS      current
      DESCRIPTION "Debug JPA profiling "
      ::= { serverDebugEntry 70  }
   
   
   serverDebugDebugMessagingKernelBoot OBJECT-TYPE
      SYNTAX      OCTET STRING
      MAX-ACCESS  read-only
      STATUS      current
      DESCRIPTION "Debugging for the messaging kernel as the server is being rebooted. This provides detailed information on every persistent message that is recovered. "
      ::= { serverDebugEntry 71  }
   
   
   serverDebugWebModule OBJECT-TYPE
      SYNTAX      OCTET STRING
      MAX-ACCESS  read-only
      STATUS      current
      DESCRIPTION "Debug WebModule processing "
      ::= { serverDebugEntry 72  }
   
   
   serverDebugDebugReplication OBJECT-TYPE
      SYNTAX      OCTET STRING
      MAX-ACCESS  read-only
      STATUS      current
      DESCRIPTION "Debug cluster replication information. "
      ::= { serverDebugEntry 73  }
   
   
   serverDebugDebugFailOver OBJECT-TYPE
      SYNTAX      OCTET STRING
      MAX-ACCESS  read-only
      STATUS      current
      DESCRIPTION "Debug stub-level fail-over processing "
      ::= { serverDebugEntry 74  }
   
   
   serverDebugDebugXMLEntityCacheIncludeName OBJECT-TYPE
      SYNTAX      OCTET STRING
      MAX-ACCESS  read-only
      STATUS      current
      DESCRIPTION "XMLEntityCache debugging option: Debug IncludeName "
      ::= { serverDebugEntry 75  }
   
   
   serverDebugDebugSNMPAgent OBJECT-TYPE
      SYNTAX      OCTET STRING
      MAX-ACCESS  read-only
      STATUS      current
      DESCRIPTION "Debug the SNMP agent framework. "
      ::= { serverDebugEntry 76  }
   
   
   serverDebugDebugDRSStateTransitions OBJECT-TYPE
      SYNTAX      OCTET STRING
      MAX-ACCESS  read-only
      STATUS      current
      DESCRIPTION "Debug DRS State transitions. "
      ::= { serverDebugEntry 77  }
   
   
   serverDebugDebugJpaManage OBJECT-TYPE
      SYNTAX      OCTET STRING
      MAX-ACCESS  read-only
      STATUS      current
      DESCRIPTION "Debug JPA management and monitoring "
      ::= { serverDebugEntry 78  }
   
   
   serverDebugDebugJMSCommon OBJECT-TYPE
      SYNTAX      OCTET STRING
      MAX-ACCESS  read-only
      STATUS      current
      DESCRIPTION "Debug JMSCommon processing "
      ::= { serverDebugEntry 79  }
   
   
   serverDebugDebugJpaRuntime OBJECT-TYPE
      SYNTAX      OCTET STRING
      MAX-ACCESS  read-only
      STATUS      current
      DESCRIPTION "Debug JPA runtime diagnostics "
      ::= { serverDebugEntry 80  }
   
   
   serverDebugDebugEmbeddedLDAPLogLevel OBJECT-TYPE
      SYNTAX      Integer32
      MAX-ACCESS  read-only
      STATUS      current
      DESCRIPTION "Debug Embedded LDAP processing (log level) "
      ::= { serverDebugEntry 81  }
   
   
   serverDebugDebugSecurityAdjudicator OBJECT-TYPE
      SYNTAX      OCTET STRING
      MAX-ACCESS  read-only
      STATUS      current
      DESCRIPTION "Debug Security Framework Adjudication processing "
      ::= { serverDebugEntry 82  }
   
   
   serverDebugDebugSAFAdmin OBJECT-TYPE
      SYNTAX      OCTET STRING
      MAX-ACCESS  read-only
      STATUS      current
      DESCRIPTION "Debug Messaging SAF Admin. "
      ::= { serverDebugEntry 83  }
   
   
   serverDebugDebugEjbPooling OBJECT-TYPE
      SYNTAX      OCTET STRING
      MAX-ACCESS  read-only
      STATUS      current
      DESCRIPTION "Debug EJB pooling "
      ::= { serverDebugEntry 84  }
   
   
   serverDebugDebugWTCtBridgeEx OBJECT-TYPE
      SYNTAX      OCTET STRING
      MAX-ACCESS  read-only
      STATUS      current
      DESCRIPTION "Debug WTC tBridge execution "
      ::= { serverDebugEntry 85  }
   
   
   serverDebugDebugSecuritySAMLLib OBJECT-TYPE
      SYNTAX      OCTET STRING
      MAX-ACCESS  read-only
      STATUS      current
      DESCRIPTION "Debug Security Framework SAML library processing "
      ::= { serverDebugEntry 86  }
   
   
   serverDebugDebugDiagnosticArchive OBJECT-TYPE
      SYNTAX      OCTET STRING
      MAX-ACCESS  read-only
      STATUS      current
      DESCRIPTION "Debug diagnostic archive processing "
      ::= { serverDebugEntry 87  }
   
   
   serverDebugDebugURLResolution OBJECT-TYPE
      SYNTAX      OCTET STRING
      MAX-ACCESS  read-only
      STATUS      current
      DESCRIPTION "Debug URL resolution for incoming http requests "
      ::= { serverDebugEntry 88  }
   
   
   serverDebugDebugLoadBalancing OBJECT-TYPE
      SYNTAX      OCTET STRING
      MAX-ACCESS  read-only
      STATUS      current
      DESCRIPTION "Debug stub-level load-balancing processing "
      ::= { serverDebugEntry 89  }
   
   
   serverDebugDebugWebAppModule OBJECT-TYPE
      SYNTAX      OCTET STRING
      MAX-ACCESS  read-only
      STATUS      current
      DESCRIPTION "Debug WebApp Module deployment callbacks "
      ::= { serverDebugEntry 90  }
   
   
   serverDebugDebugSecurityService OBJECT-TYPE
      SYNTAX      OCTET STRING
      MAX-ACCESS  read-only
      STATUS      current
      DESCRIPTION "Debug Security Service "
      ::= { serverDebugEntry 91  }
   
   
   serverDebugDebugRC4 OBJECT-TYPE
      SYNTAX      OCTET STRING
      MAX-ACCESS  read-only
      STATUS      current
      DESCRIPTION "Debug RC4 cipher processing "
      ::= { serverDebugEntry 92  }
   
   
   serverDebugDebugXMLRegistryIncludeTime OBJECT-TYPE
      SYNTAX      OCTET STRING
      MAX-ACCESS  read-only
      STATUS      current
      DESCRIPTION "XML Registry debugging option: Debug IncludeTime "
      ::= { serverDebugEntry 93  }
   
   
   serverDebugDebugJAXPIncludeLocation OBJECT-TYPE
      SYNTAX      OCTET STRING
      MAX-ACCESS  read-only
      STATUS      current
      DESCRIPTION "JAXP debugging option: Debug IncludeLocation "
      ::= { serverDebugEntry 94  }
   
   
   serverDebugDebugLoggingConfiguration OBJECT-TYPE
      SYNTAX      OCTET STRING
      MAX-ACCESS  read-only
      STATUS      current
      DESCRIPTION "Debug log configuration processing "
      ::= { serverDebugEntry 95  }
   
   
   serverDebugDebugHttp OBJECT-TYPE
      SYNTAX      OCTET STRING
      MAX-ACCESS  read-only
      STATUS      current
      DESCRIPTION "Debug WebApp Container HTTP processing. "
      ::= { serverDebugEntry 96  }
   
   
   serverDebugDebugDiagnosticFileArchive OBJECT-TYPE
      SYNTAX      OCTET STRING
      MAX-ACCESS  read-only
      STATUS      current
      DESCRIPTION "Debug diagnostic file archive processing "
      ::= { serverDebugEntry 97  }
   
   
   serverDebugDebugJTAXA OBJECT-TYPE
      SYNTAX      OCTET STRING
      MAX-ACCESS  read-only
      STATUS      current
      DESCRIPTION "Debug JTA XA resources "
      ::= { serverDebugEntry 98  }
   
   
   serverDebugDebugIIOPSecurity OBJECT-TYPE
      SYNTAX      OCTET STRING
      MAX-ACCESS  read-only
      STATUS      current
      DESCRIPTION "Debug IIOP security processing "
      ::= { serverDebugEntry 99  }
   
   
   serverDebugDebugRAXAout OBJECT-TYPE
      SYNTAX      OCTET STRING
      MAX-ACCESS  read-only
      STATUS      current
      DESCRIPTION "Debug Resource Adapter XA outgoing message processing "
      ::= { serverDebugEntry 100  }
   
   
   serverDebugDebugJAXPIncludeName OBJECT-TYPE
      SYNTAX      OCTET STRING
      MAX-ACCESS  read-only
      STATUS      current
      DESCRIPTION "JAXP debugging option: Debug IncludeName "
      ::= { serverDebugEntry 101  }
   
   
   serverDebugDebugDiagnosticsModule OBJECT-TYPE
      SYNTAX      OCTET STRING
      MAX-ACCESS  read-only
      STATUS      current
      DESCRIPTION "Debug diagnostic module processing "
      ::= { serverDebugEntry 102  }
   
   
   serverDebugApplicationContainer OBJECT-TYPE
      SYNTAX      OCTET STRING
      MAX-ACCESS  read-only
      STATUS      current
      DESCRIPTION "Debug Application Container deployment processing "
      ::= { serverDebugEntry 103  }
   
   
   serverDebugDebugDeploy OBJECT-TYPE
      SYNTAX      OCTET STRING
      MAX-ACCESS  read-only
      STATUS      current
      DESCRIPTION "Debug deploy command processing "
      ::= { serverDebugEntry 104  }
   
   
   serverDebugDebugDeploymentServiceTransport OBJECT-TYPE
      SYNTAX      OCTET STRING
      MAX-ACCESS  read-only
      STATUS      current
      DESCRIPTION "Debug deployment service transport processing "
      ::= { serverDebugEntry 105  }
   
   
   serverDebugDebugWTCTDomPdu OBJECT-TYPE
      SYNTAX      OCTET STRING
      MAX-ACCESS  read-only
      STATUS      current
      DESCRIPTION "Debug WTC XATMI Message processing "
      ::= { serverDebugEntry 106  }
   
   
   serverDebugDebugJTALifecycle OBJECT-TYPE
      SYNTAX      OCTET STRING
      MAX-ACCESS  read-only
      STATUS      current
      DESCRIPTION "Debug JTA ServerLifecycle "
      ::= { serverDebugEntry 107  }
   
   
   serverDebugDebugJTATLOG OBJECT-TYPE
      SYNTAX      OCTET STRING
      MAX-ACCESS  read-only
      STATUS      current
      DESCRIPTION "Debug JTA transaction log processing "
      ::= { serverDebugEntry 108  }
   
   
   serverDebugDebugRAParsing OBJECT-TYPE
      SYNTAX      OCTET STRING
      MAX-ACCESS  read-only
      STATUS      current
      DESCRIPTION "Debug Resource Adapter descriptor parsing "
      ::= { serverDebugEntry 109  }
   
   
   serverDebugDebugServerLifeCycle OBJECT-TYPE
      SYNTAX      OCTET STRING
      MAX-ACCESS  read-only
      STATUS      current
      DESCRIPTION "Debug Server ServerLifeCycle processing "
      ::= { serverDebugEntry 110  }
   
   
   serverDebugDebugSAFReceivingAgent OBJECT-TYPE
      SYNTAX      OCTET STRING
      MAX-ACCESS  read-only
      STATUS      current
      DESCRIPTION "Debug Messaging SAF ReceivingAgent. "
      ::= { serverDebugEntry 111  }
   
   
   serverDebugDebugConnection OBJECT-TYPE
      SYNTAX      OCTET STRING
      MAX-ACCESS  read-only
      STATUS      current
      DESCRIPTION "Debug JVM to JVM connections "
      ::= { serverDebugEntry 112  }
   
   
   serverDebugDebugJMSBoot OBJECT-TYPE
      SYNTAX      OCTET STRING
      MAX-ACCESS  read-only
      STATUS      current
      DESCRIPTION "Debug JMS boot operations "
      ::= { serverDebugEntry 113  }
   
   
   serverDebugDebugJMSSAF OBJECT-TYPE
      SYNTAX      OCTET STRING
      MAX-ACCESS  read-only
      STATUS      current
      DESCRIPTION "Debug JMS SAF processing "
      ::= { serverDebugEntry 114  }
   
   
   serverDebugDebugDiagnosticImage OBJECT-TYPE
      SYNTAX      OCTET STRING
      MAX-ACCESS  read-only
      STATUS      current
      DESCRIPTION "Debug diagnostic image processing "
      ::= { serverDebugEntry 115  }
   
   
   serverDebugDebugJpaJdbcSchema OBJECT-TYPE
      SYNTAX      OCTET STRING
      MAX-ACCESS  read-only
      STATUS      current
      DESCRIPTION "Debug JPA RDBMS schema manipulation "
      ::= { serverDebugEntry 116  }
   
   
   serverDebugDebugTunnelingConnection OBJECT-TYPE
      SYNTAX      OCTET STRING
      MAX-ACCESS  read-only
      STATUS      current
      DESCRIPTION "Debug HTTP tunneling connection open/close processing. "
      ::= { serverDebugEntry 117  }
   
   
   serverDebugDebugClusterHeartbeats OBJECT-TYPE
      SYNTAX      OCTET STRING
      MAX-ACCESS  read-only
      STATUS      current
      DESCRIPTION "Debug each cluster Heartbeat that is sent or received by multicast. "
      ::= { serverDebugEntry 118  }
   
   
   serverDebugDebugRSA OBJECT-TYPE
      SYNTAX      OCTET STRING
      MAX-ACCESS  read-only
      STATUS      current
      DESCRIPTION "Debug RSA security processing "
      ::= { serverDebugEntry 119  }
   
   
   serverDebugDebugSecurityEEngine OBJECT-TYPE
      SYNTAX      OCTET STRING
      MAX-ACCESS  read-only
      STATUS      current
      DESCRIPTION "Debug Security Framework Entitlements Engine processing "
      ::= { serverDebugEntry 120  }
   
   
   serverDebugDebugSecurityKeyStore OBJECT-TYPE
      SYNTAX      OCTET STRING
      MAX-ACCESS  read-only
      STATUS      current
      DESCRIPTION "Debug Security Framework KeyStore processing "
      ::= { serverDebugEntry 121  }
   
   
   serverDebugDebugXMLEntityCacheIncludeTime OBJECT-TYPE
      SYNTAX      OCTET STRING
      MAX-ACCESS  read-only
      STATUS      current
      DESCRIPTION "XMLEntityCache debugging option: Debug IncludeTime "
      ::= { serverDebugEntry 122  }
   
   
   serverDebugDebugJMSPauseResume OBJECT-TYPE
      SYNTAX      OCTET STRING
      MAX-ACCESS  read-only
      STATUS      current
      DESCRIPTION "Debug JMS Pause/Resume processing "
      ::= { serverDebugEntry 123  }
   
   
   serverDebugDebugLibraries OBJECT-TYPE
      SYNTAX      OCTET STRING
      MAX-ACCESS  read-only
      STATUS      current
      DESCRIPTION "Debug application library processing "
      ::= { serverDebugEntry 124  }
   
   
   serverDebugDebugSecurityCredMap OBJECT-TYPE
      SYNTAX      OCTET STRING
      MAX-ACCESS  read-only
      STATUS      current
      DESCRIPTION "Debug Security Framework Credential Mapper processing "
      ::= { serverDebugEntry 125  }
   
   
   serverDebugDebugConfigurationRuntime OBJECT-TYPE
      SYNTAX      OCTET STRING
      MAX-ACCESS  read-only
      STATUS      current
      DESCRIPTION "Debug management configuration runtime processing "
      ::= { serverDebugEntry 126  }
   
   
   serverDebugDebugDiagnosticLifecycleHandlers OBJECT-TYPE
      SYNTAX      OCTET STRING
      MAX-ACCESS  read-only
      STATUS      current
      DESCRIPTION "Debug diagnostic lifecycle handler processing "
      ::= { serverDebugEntry 127  }
   
   
   serverDebugDebugConfigurationEdit OBJECT-TYPE
      SYNTAX      OCTET STRING
      MAX-ACCESS  read-only
      STATUS      current
      DESCRIPTION "Debug management configuration edit processing "
      ::= { serverDebugEntry 128  }
   
   
   serverDebugDebugDiagnosticWlstoreArchive OBJECT-TYPE
      SYNTAX      OCTET STRING
      MAX-ACCESS  read-only
      STATUS      current
      DESCRIPTION "Debug diagnostic wlstore archive processing "
      ::= { serverDebugEntry 129  }
   
   
   serverDebugDebugSecurityPasswordPolicy OBJECT-TYPE
      SYNTAX      OCTET STRING
      MAX-ACCESS  read-only
      STATUS      current
      DESCRIPTION "Debug Security Password Guessing "
      ::= { serverDebugEntry 130  }
   
   
   serverDebugDebugEjbCompilation OBJECT-TYPE
      SYNTAX      OCTET STRING
      MAX-ACCESS  read-only
      STATUS      current
      DESCRIPTION "Debug EJB compilation "
      ::= { serverDebugEntry 131  }
   
   
   serverDebugDebugJpaQuery OBJECT-TYPE
      SYNTAX      OCTET STRING
      MAX-ACCESS  read-only
      STATUS      current
      DESCRIPTION "Debug JPA Query processing "
      ::= { serverDebugEntry 132  }
   
   
   serverDebugDebugSSL OBJECT-TYPE
      SYNTAX      OCTET STRING
      MAX-ACCESS  read-only
      STATUS      current
      DESCRIPTION "Debug SSL processing "
      ::= { serverDebugEntry 133  }
   
   
   serverDebugDebugRouting OBJECT-TYPE
      SYNTAX      OCTET STRING
      MAX-ACCESS  read-only
      STATUS      current
      DESCRIPTION "Debug routing of messages over JVM to JVM connections "
      ::= { serverDebugEntry 134  }
   
   
   serverDebugDebugJpaDataCache OBJECT-TYPE
      SYNTAX      OCTET STRING
      MAX-ACCESS  read-only
      STATUS      current
      DESCRIPTION "Debug JPA data cache "
      ::= { serverDebugEntry 135  }
   
   
   serverDebugDebugConsensusLeasing OBJECT-TYPE
      SYNTAX      OCTET STRING
      MAX-ACCESS  read-only
      STATUS      current
      DESCRIPTION "Debug cluster consensus lease processing "
      ::= { serverDebugEntry 136  }
   
   
   serverDebugDebugDiagnosticInstrumentationEvents OBJECT-TYPE
      SYNTAX      OCTET STRING
      MAX-ACCESS  read-only
      STATUS      current
      DESCRIPTION "Debug instrumentation event records "
      ::= { serverDebugEntry 137  }
   
   
   serverDebugDebugStoreIOLogicalBoot OBJECT-TYPE
      SYNTAX      OCTET STRING
      MAX-ACCESS  read-only
      STATUS      current
      DESCRIPTION "Debug persistent store logical boot operations (lists all recovered records). "
      ::= { serverDebugEntry 138  }
   
   
   serverDebugDebugEjbSwapping OBJECT-TYPE
      SYNTAX      OCTET STRING
      MAX-ACCESS  read-only
      STATUS      current
      DESCRIPTION "Debug EJB Swapping "
      ::= { serverDebugEntry 139  }
   
   
   serverDebugDebugJTANonXA OBJECT-TYPE
      SYNTAX      OCTET STRING
      MAX-ACCESS  read-only
      STATUS      current
      DESCRIPTION "Debug JTA non-XA resources "
      ::= { serverDebugEntry 140  }
   
   
   serverDebugDebugDiagnosticInstrumentationConfig OBJECT-TYPE
      SYNTAX      OCTET STRING
      MAX-ACCESS  read-only
      STATUS      current
      DESCRIPTION "Debug instrumentation configuration processing "
      ::= { serverDebugEntry 141  }
   
   
   serverDebugDebugMessaging OBJECT-TYPE
      SYNTAX      OCTET STRING
      MAX-ACCESS  read-only
      STATUS      current
      DESCRIPTION "Debug messages sent over JVM to JVM connections "
      ::= { serverDebugEntry 142  }
   
   
   serverDebugDebugSecurityCertPath OBJECT-TYPE
      SYNTAX      OCTET STRING
      MAX-ACCESS  read-only
      STATUS      current
      DESCRIPTION "Debug Security Framework CertPath processing "
      ::= { serverDebugEntry 143  }
   
   
   serverDebugDebugJNDIResolution OBJECT-TYPE
      SYNTAX      OCTET STRING
      MAX-ACCESS  read-only
      STATUS      current
      DESCRIPTION "Debug naming service name resolution. "
      ::= { serverDebugEntry 144  }
   
   
   serverDebugDebugSNMPProtocolTCP OBJECT-TYPE
      SYNTAX      OCTET STRING
      MAX-ACCESS  read-only
      STATUS      current
      DESCRIPTION "Debug the SNMP TCP protocol handler. "
      ::= { serverDebugEntry 145  }
   
   
   serverDebugDebugRALocalOut OBJECT-TYPE
      SYNTAX      OCTET STRING
      MAX-ACCESS  read-only
      STATUS      current
      DESCRIPTION "Debug Resource Adapter local tx outgoing message processing "
      ::= { serverDebugEntry 146  }
   
   
   serverDebugDebugJMXDomain OBJECT-TYPE
      SYNTAX      OCTET STRING
      MAX-ACCESS  read-only
      STATUS      current
      DESCRIPTION "Debug JMX domain service processing "
      ::= { serverDebugEntry 147  }
   
   
   serverDebugDebugDiagnosticsHarvesterData OBJECT-TYPE
      SYNTAX      OCTET STRING
      MAX-ACCESS  read-only
      STATUS      current
      DESCRIPTION "Detailed debug of diagnostic harvester processing This should be used in conjunction with DebugDiagnosticsHarvester. "
      ::= { serverDebugEntry 148  }
   
   
   serverDebugDebugSecurityRoleMap OBJECT-TYPE
      SYNTAX      OCTET STRING
      MAX-ACCESS  read-only
      STATUS      current
      DESCRIPTION "Debug Security Framework Role Mapping "
      ::= { serverDebugEntry 149  }
   
   
   serverDebugDebugEjbDeployment OBJECT-TYPE
      SYNTAX      OCTET STRING
      MAX-ACCESS  read-only
      STATUS      current
      DESCRIPTION "Debug EJB deployment "
      ::= { serverDebugEntry 150  }
   
   
   serverDebugDebugSNMPToolkit OBJECT-TYPE
      SYNTAX      OCTET STRING
      MAX-ACCESS  read-only
      STATUS      current
      DESCRIPTION "Debug the SNMP vendor toolkit implementation. "
      ::= { serverDebugEntry 151  }
   
   
   serverDebugDebugMuxer OBJECT-TYPE
      SYNTAX      OCTET STRING
      MAX-ACCESS  read-only
      STATUS      current
      DESCRIPTION "Debug Muxer processing "
      ::= { serverDebugEntry 152  }
   
   
   serverDebugMasterDeployer OBJECT-TYPE
      SYNTAX      OCTET STRING
      MAX-ACCESS  read-only
      STATUS      current
      DESCRIPTION "Debug Master Deployer processing "
      ::= { serverDebugEntry 153  }
   
   
   serverDebugDebugSecuritySAMLCredMap OBJECT-TYPE
      SYNTAX      OCTET STRING
      MAX-ACCESS  read-only
      STATUS      current
      DESCRIPTION "Debug Security Framework SAML Provider credential mapper processing "
      ::= { serverDebugEntry 154  }
   
   
   serverDebugDiagnosticContextDebugMode OBJECT-TYPE
      SYNTAX      OCTET STRING
      MAX-ACCESS  read-only
      STATUS      current
      DESCRIPTION "Specifies how context based debugging is enabled for the Server. The default behavior in the Off mode is that debug output is emitted for all requests.   The DiagnosticContextDebugMode works in conjunction with the DebugMaskCriterias specified in the And or Or modes. For context based debugging the WLDF Instrumentation needs to be enabled and DyeInjection monitor needs to be configured for the Server.   When the context debug mode is set to And mode, debug is emitted only for the requests that have all the bits in the WLDF dye vector set for the flags specified in the DebugMaskCriterias attribute.   When the context debug mode is set to Or mode, debug is emitted only for the requests that have any one of the bits in the WLDF dye vector set for the flags specified in the DebugMaskCriterias attribute.  "
      ::= { serverDebugEntry 155  }
   
   
   serverDebugDebugSecuritySSL OBJECT-TYPE
      SYNTAX      OCTET STRING
      MAX-ACCESS  read-only
      STATUS      current
      DESCRIPTION "Debug Security SSL and TLS processing "
      ::= { serverDebugEntry 156  }
   
   
   serverDebugDebugDiagnosticJdbcArchive OBJECT-TYPE
      SYNTAX      OCTET STRING
      MAX-ACCESS  read-only
      STATUS      current
      DESCRIPTION "Debug diagnostic jdbc archive processing "
      ::= { serverDebugEntry 157  }
   
   
   serverDebugSlaveDeployer OBJECT-TYPE
      SYNTAX      OCTET STRING
      MAX-ACCESS  read-only
      STATUS      current
      DESCRIPTION "Debug Slave Deployer processing "
      ::= { serverDebugEntry 158  }
   
   
   serverDebugDebugJTAXAStackTrace OBJECT-TYPE
      SYNTAX      OCTET STRING
      MAX-ACCESS  read-only
      STATUS      current
      DESCRIPTION "Detailed Debug of JTA XA processing "
      ::= { serverDebugEntry 159  }
   
   
   serverDebugDebugSecurityJACC OBJECT-TYPE
      SYNTAX      OCTET STRING
      MAX-ACCESS  read-only
      STATUS      current
      DESCRIPTION "Debug Security Framework JACC processing "
      ::= { serverDebugEntry 160  }
   
   
   serverDebugDebugEjbCmpDeployment OBJECT-TYPE
      SYNTAX      OCTET STRING
      MAX-ACCESS  read-only
      STATUS      current
      DESCRIPTION "Debug EJB CMP deployment processing "
      ::= { serverDebugEntry 161  }
   
   
   serverDebugType OBJECT-TYPE
      SYNTAX      OCTET STRING
      MAX-ACCESS  read-only
      STATUS      current
      DESCRIPTION "Returns the type of the MBean. "
      ::= { serverDebugEntry 162  }
   
   
   serverDebugDebugEmbeddedLDAPWriteOverrideProps OBJECT-TYPE
      SYNTAX      OCTET STRING
      MAX-ACCESS  read-only
      STATUS      current
      DESCRIPTION "Embedded LDAP Write All Overrides to Property Files "
      ::= { serverDebugEntry 163  }
   
   
   serverDebugDebugSecurityJACCPolicy OBJECT-TYPE
      SYNTAX      OCTET STRING
      MAX-ACCESS  read-only
      STATUS      current
      DESCRIPTION "Debug Security Framework JACC Policy processing "
      ::= { serverDebugEntry 164  }
   
   
   serverDebugDebugJMSDispatcher OBJECT-TYPE
      SYNTAX      OCTET STRING
      MAX-ACCESS  read-only
      STATUS      current
      DESCRIPTION "Debug JMS Dispatcher processing "
      ::= { serverDebugEntry 165  }
   
   
   serverDebugDebugClusterAnnouncements OBJECT-TYPE
      SYNTAX      OCTET STRING
      MAX-ACCESS  read-only
      STATUS      current
      DESCRIPTION "Debug each Announcement, StateDump, and Attributes message that is sent or received by multicast. "
      ::= { serverDebugEntry 166  }
   
   
   serverDebugClasspathServlet OBJECT-TYPE
      SYNTAX      OCTET STRING
      MAX-ACCESS  read-only
      STATUS      current
      DESCRIPTION "Debug ClassPathServlet processing "
      ::= { serverDebugEntry 167  }
   
   
   serverDebugDebugIIOPTunneling OBJECT-TYPE
      SYNTAX      OCTET STRING
      MAX-ACCESS  read-only
      STATUS      current
      DESCRIPTION "Debug IIOP tunnelling "
      ::= { serverDebugEntry 168  }
   
   
   serverDebugDebugJAXPDebugLevel OBJECT-TYPE
      SYNTAX      Integer32
      MAX-ACCESS  read-only
      STATUS      current
      DESCRIPTION "JAXP debugging option: Debug level "
      ::= { serverDebugEntry 169  }
   
   
   serverDebugDebugJ2EEManagement OBJECT-TYPE
      SYNTAX      OCTET STRING
      MAX-ACCESS  read-only
      STATUS      current
      DESCRIPTION "Debug Java EE management processing "
      ::= { serverDebugEntry 170  }
   
   
   serverDebugDebugJTAResourceName OBJECT-TYPE
      SYNTAX      OCTET STRING
      MAX-ACCESS  read-only
      STATUS      current
      DESCRIPTION "Debug JTA Resource name filter "
      ::= { serverDebugEntry 171  }
   
   
   serverDebugDebugSecurityEncryptionService OBJECT-TYPE
      SYNTAX      OCTET STRING
      MAX-ACCESS  read-only
      STATUS      current
      DESCRIPTION "Debug Security Framework Encryption Service processing "
      ::= { serverDebugEntry 172  }
   
   
   serverDebugDebugJDBCConn OBJECT-TYPE
      SYNTAX      OCTET STRING
      MAX-ACCESS  read-only
      STATUS      current
      DESCRIPTION "Debug JDBC Connection setup/teardown processing "
      ::= { serverDebugEntry 173  }
   
   
   serverDebugDebugDRSUpdateStatus OBJECT-TYPE
      SYNTAX      OCTET STRING
      MAX-ACCESS  read-only
      STATUS      current
      DESCRIPTION "Debug DRS Update status processing. "
      ::= { serverDebugEntry 174  }
   
   
   serverDebugDebugDeploymentServiceStatusUpdates OBJECT-TYPE
      SYNTAX      OCTET STRING
      MAX-ACCESS  read-only
      STATUS      current
      DESCRIPTION "Debug deployment service status update processing "
      ::= { serverDebugEntry 175  }
   
   
   serverDebugDebugMuxerTimeout OBJECT-TYPE
      SYNTAX      OCTET STRING
      MAX-ACCESS  read-only
      STATUS      current
      DESCRIPTION "Debug Muxer timeout processing "
      ::= { serverDebugEntry 176  }
   
   
   serverDebugDebugSAFStore OBJECT-TYPE
      SYNTAX      OCTET STRING
      MAX-ACCESS  read-only
      STATUS      current
      DESCRIPTION "Debug Messaging SAF Store. "
      ::= { serverDebugEntry 177  }
   
   
   serverDebugName OBJECT-TYPE
      SYNTAX      OCTET STRING
      MAX-ACCESS  read-only
      STATUS      current
      DESCRIPTION "The user-specified name of this MBean instance.  This name is included as one of the key properties in the MBean's javax.management.ObjectName:  Name=user-specified-name "
      ::= { serverDebugEntry 178  }
   
   
   serverDebugDebugDomainLogHandler OBJECT-TYPE
      SYNTAX      OCTET STRING
      MAX-ACCESS  read-only
      STATUS      current
      DESCRIPTION "Debug Domain Log Handler processing "
      ::= { serverDebugEntry 179  }
   
   
   serverDebugDebugWTCConfig OBJECT-TYPE
      SYNTAX      OCTET STRING
      MAX-ACCESS  read-only
      STATUS      current
      DESCRIPTION "Debug WTC configuration processing "
      ::= { serverDebugEntry 180  }
   
   
   serverDebugDebugJTAGatewayStackTrace OBJECT-TYPE
      SYNTAX      OCTET STRING
      MAX-ACCESS  read-only
      STATUS      current
      DESCRIPTION "Detailed debug of JTA imported transactions "
      ::= { serverDebugEntry 181  }
   
   
   serverDebugDebugMuxerException OBJECT-TYPE
      SYNTAX      OCTET STRING
      MAX-ACCESS  read-only
      STATUS      current
      DESCRIPTION "Debug Muxer exception processing "
      ::= { serverDebugEntry 182  }
   
   
   serverDebugDebugDRSHeartbeats OBJECT-TYPE
      SYNTAX      OCTET STRING
      MAX-ACCESS  read-only
      STATUS      current
      DESCRIPTION "Debug DRS Heartbeats. "
      ::= { serverDebugEntry 183  }
   
   
   serverDebugDebugJTA2PCStackTrace OBJECT-TYPE
      SYNTAX      OCTET STRING
      MAX-ACCESS  read-only
      STATUS      current
      DESCRIPTION "Detailed Debug of JTA 2PC processing "
      ::= { serverDebugEntry 184  }
   
   
   serverDebugDebugJMSBackEnd OBJECT-TYPE
      SYNTAX      OCTET STRING
      MAX-ACCESS  read-only
      STATUS      current
      DESCRIPTION "Debug JMSBackEnd processing "
      ::= { serverDebugEntry 185  }
   
   
   serverDebugDebugXMLEntityCacheIncludeClass OBJECT-TYPE
      SYNTAX      OCTET STRING
      MAX-ACCESS  read-only
      STATUS      current
      DESCRIPTION "XMLEntityCache debugging option: Debug IncludeClass "
      ::= { serverDebugEntry 186  }
   
   
   serverDebugDebugCluster OBJECT-TYPE
      SYNTAX      OCTET STRING
      MAX-ACCESS  read-only
      STATUS      current
      DESCRIPTION "Debug each GroupMessage that is sent or received by multicast. "
      ::= { serverDebugEntry 187  }
   
   
   serverDebugDebugJTAResourceHealth OBJECT-TYPE
      SYNTAX      OCTET STRING
      MAX-ACCESS  read-only
      STATUS      current
      DESCRIPTION "Debug JTA resource health "
      ::= { serverDebugEntry 188  }
   
   
   serverDebugDebugRASecurityCtx OBJECT-TYPE
      SYNTAX      OCTET STRING
      MAX-ACCESS  read-only
      STATUS      current
      DESCRIPTION "Debug setup of resource ref processing (container and application managed security set by calling application components) "
      ::= { serverDebugEntry 189  }
   
   
   serverDebugDebugStoreAdmin OBJECT-TYPE
      SYNTAX      OCTET STRING
      MAX-ACCESS  read-only
      STATUS      current
      DESCRIPTION "Debug the persistent store's administration code. This will produce debug events when instances of the store are created and deleted, and when the server is booted. "
      ::= { serverDebugEntry 190  }
   
   
   serverDebugClassFinder OBJECT-TYPE
      SYNTAX      OCTET STRING
      MAX-ACCESS  read-only
      STATUS      current
      DESCRIPTION "Debug ClassFinder processing "
      ::= { serverDebugEntry 191  }
   
   
   serverDebugDebugDeploymentService OBJECT-TYPE
      SYNTAX      OCTET STRING
      MAX-ACCESS  read-only
      STATUS      current
      DESCRIPTION "Debug deployment service processing "
      ::= { serverDebugEntry 192  }
   
   
   serverDebugDebugHttpSessions OBJECT-TYPE
      SYNTAX      OCTET STRING
      MAX-ACCESS  read-only
      STATUS      current
      DESCRIPTION "Debug Http Session management in the webapp container. "
      ::= { serverDebugEntry 193  }
   
   
   serverDebugDebugJMXEdit OBJECT-TYPE
      SYNTAX      OCTET STRING
      MAX-ACCESS  read-only
      STATUS      current
      DESCRIPTION "Debug JMX edit service processing "
      ::= { serverDebugEntry 194  }
   
   
   serverDebugDebugClusterFragments OBJECT-TYPE
      SYNTAX      OCTET STRING
      MAX-ACCESS  read-only
      STATUS      current
      DESCRIPTION "Debug for each fragment that is sent or received by multicast. "
      ::= { serverDebugEntry 195  }
   
   
   serverDebugDebugWTCJatmiEx OBJECT-TYPE
      SYNTAX      OCTET STRING
      MAX-ACCESS  read-only
      STATUS      current
      DESCRIPTION "Debug WTC jatmi execution "
      ::= { serverDebugEntry 196  }
   
   
   serverDebugDebugWTCUData OBJECT-TYPE
      SYNTAX      OCTET STRING
      MAX-ACCESS  read-only
      STATUS      current
      DESCRIPTION "Debug WTC user data processing "
      ::= { serverDebugEntry 197  }
   
   
   serverDebugDebugDeploymentServiceInternal OBJECT-TYPE
      SYNTAX      OCTET STRING
      MAX-ACCESS  read-only
      STATUS      current
      DESCRIPTION "Debug internal deployment service processing "
      ::= { serverDebugEntry 198  }
   
   
   serverDebugDebugSecurityAuditor OBJECT-TYPE
      SYNTAX      OCTET STRING
      MAX-ACCESS  read-only
      STATUS      current
      DESCRIPTION "Debug Security Framework Auditor processing "
      ::= { serverDebugEntry 199  }
   
   
   serverDebugDebugJpaJdbcSql OBJECT-TYPE
      SYNTAX      OCTET STRING
      MAX-ACCESS  read-only
      STATUS      current
      DESCRIPTION "Debug JPA RDBMS SQL interaction "
      ::= { serverDebugEntry 200  }
   
   
   serverDebugDebugEjbInvoke OBJECT-TYPE
      SYNTAX      OCTET STRING
      MAX-ACCESS  read-only
      STATUS      current
      DESCRIPTION "Debug EJB invocation processing "
      ::= { serverDebugEntry 201  }
   
   
   serverDebugDebugRAWork OBJECT-TYPE
      SYNTAX      OCTET STRING
      MAX-ACCESS  read-only
      STATUS      current
      DESCRIPTION "Debug Resource Adapter Work submission and cancel processing "
      ::= { serverDebugEntry 202  }
   
   
   serverDebugDebugDRSCalls OBJECT-TYPE
      SYNTAX      OCTET STRING
      MAX-ACCESS  read-only
      STATUS      current
      DESCRIPTION "Debug Data replication service (DRS) API calls. "
      ::= { serverDebugEntry 203  }
   
   
   serverDebugDebugSecurityPredicate OBJECT-TYPE
      SYNTAX      OCTET STRING
      MAX-ACCESS  read-only
      STATUS      current
      DESCRIPTION "Debug Security Framework predicate processing "
      ::= { serverDebugEntry 204  }
   
   
   serverDebugDebugXMLRegistryUseShortClass OBJECT-TYPE
      SYNTAX      OCTET STRING
      MAX-ACCESS  read-only
      STATUS      current
      DESCRIPTION "XML Registry debugging option: Debug UseShortClass "
      ::= { serverDebugEntry 205  }
   
   
   serverDebugDebugSecurityUserLockout OBJECT-TYPE
      SYNTAX      OCTET STRING
      MAX-ACCESS  read-only
      STATUS      current
      DESCRIPTION "Debug Security User Lockout processing "
      ::= { serverDebugEntry 206  }
   
   
   serverDebugDebugJTANamingStackTrace OBJECT-TYPE
      SYNTAX      OCTET STRING
      MAX-ACCESS  read-only
      STATUS      current
      DESCRIPTION "Detailed debug of JTA naming "
      ::= { serverDebugEntry 207  }
   
   
   serverDebugListenThreadDebug OBJECT-TYPE
      SYNTAX      OCTET STRING
      MAX-ACCESS  read-only
      STATUS      current
      DESCRIPTION "Debug listenThread processing "
      ::= { serverDebugEntry 208  }
   
   
   serverDebugDebugJpaMetaData OBJECT-TYPE
      SYNTAX      OCTET STRING
      MAX-ACCESS  read-only
      STATUS      current
      DESCRIPTION "Debug JPA MetaData processing "
      ::= { serverDebugEntry 209  }
   
   
   serverDebugDebugJTA2PC OBJECT-TYPE
      SYNTAX      OCTET STRING
      MAX-ACCESS  read-only
      STATUS      current
      DESCRIPTION "Debug JTA 2PC processing "
      ::= { serverDebugEntry 210  }
   
   
   serverDebugDebugAppContainer OBJECT-TYPE
      SYNTAX      OCTET STRING
      MAX-ACCESS  read-only
      STATUS      current
      DESCRIPTION "Debug Application Container processing "
      ::= { serverDebugEntry 211  }
   
   
   serverDebugDebugJAXPUseShortClass OBJECT-TYPE
      SYNTAX      OCTET STRING
      MAX-ACCESS  read-only
      STATUS      current
      DESCRIPTION "JAXP debugging option: Debug UseShortClass "
      ::= { serverDebugEntry 212  }
   
   
   serverDebugDebugEventManager OBJECT-TYPE
      SYNTAX      OCTET STRING
      MAX-ACCESS  read-only
      STATUS      current
      DESCRIPTION "Debug Event Manager processing "
      ::= { serverDebugEntry 213  }
   
   
   serverDebugDebugJpaEnhance OBJECT-TYPE
      SYNTAX      OCTET STRING
      MAX-ACCESS  read-only
      STATUS      current
      DESCRIPTION "Debug JPA post-compilation "
      ::= { serverDebugEntry 214  }
   
   
   serverDebugDebugTunnelingConnectionTimeout OBJECT-TYPE
      SYNTAX      OCTET STRING
      MAX-ACCESS  read-only
      STATUS      current
      DESCRIPTION "Debug HTTP tunneling connection timed out processing. "
      ::= { serverDebugEntry 215  }
   
   
   serverDebugDebugSecuritySAMLAtn OBJECT-TYPE
      SYNTAX      OCTET STRING
      MAX-ACCESS  read-only
      STATUS      current
      DESCRIPTION "Debug Security Framework SAML Provider atn processing "
      ::= { serverDebugEntry 216  }
   
   
   serverDebugDebugSecurityAtn OBJECT-TYPE
      SYNTAX      OCTET STRING
      MAX-ACCESS  read-only
      STATUS      current
      DESCRIPTION "Debug Security Framework Atn processing "
      ::= { serverDebugEntry 217  }
   
   
   serverDebugLogDGCStatistics OBJECT-TYPE
      SYNTAX      OCTET STRING
      MAX-ACCESS  read-only
      STATUS      current
      DESCRIPTION "Debug DGC with Statistics "
      ::= { serverDebugEntry 218  }
   
   
   serverDebugDebugDiagnosticQuery OBJECT-TYPE
      SYNTAX      OCTET STRING
      MAX-ACCESS  read-only
      STATUS      current
      DESCRIPTION "Debug diagnostic query processing "
      ::= { serverDebugEntry 219  }
   
   
   serverDebugDebugJMX OBJECT-TYPE
      SYNTAX      OCTET STRING
      MAX-ACCESS  read-only
      STATUS      current
      DESCRIPTION "Debug JMX processing "
      ::= { serverDebugEntry 220  }
   
   
   serverDebugDebugXMLRegistryIncludeName OBJECT-TYPE
      SYNTAX      OCTET STRING
      MAX-ACCESS  read-only
      STATUS      current
      DESCRIPTION "XML Registry debugging option: Debug IncludeName "
      ::= { serverDebugEntry 221  }
   
   
   serverDebugDebugDiagnosticInstrumentationWeavingMatches OBJECT-TYPE
      SYNTAX      OCTET STRING
      MAX-ACCESS  read-only
      STATUS      current
      DESCRIPTION "Debug instrumentation weaving for matches only "
      ::= { serverDebugEntry 222  }
   
   
   serverDebugDebugAbbreviation OBJECT-TYPE
      SYNTAX      OCTET STRING
      MAX-ACCESS  read-only
      STATUS      current
      DESCRIPTION "Debug abbreviations over JVM to JVM connections "
      ::= { serverDebugEntry 223  }
   
   
   serverDebugDebugJAXPIncludeClass OBJECT-TYPE
      SYNTAX      OCTET STRING
      MAX-ACCESS  read-only
      STATUS      current
      DESCRIPTION "JAXP debugging option: Debug IncludeClass "
      ::= { serverDebugEntry 224  }
   
   
   serverDebugDebugHttpLogging OBJECT-TYPE
      SYNTAX      OCTET STRING
      MAX-ACCESS  read-only
      STATUS      current
      DESCRIPTION "Debug log manager in the webapp container. "
      ::= { serverDebugEntry 225  }
   
   
   serverDebugDebugJpaJdbcJdbc OBJECT-TYPE
      SYNTAX      OCTET STRING
      MAX-ACCESS  read-only
      STATUS      current
      DESCRIPTION "Debug JPA RDBMS JDBC interaction "
      ::= { serverDebugEntry 226  }
   
   
   serverDebugDebugSAFManager OBJECT-TYPE
      SYNTAX      OCTET STRING
      MAX-ACCESS  read-only
      STATUS      current
      DESCRIPTION "Debug Messaging SAF Manager. "
      ::= { serverDebugEntry 227  }
   
   
   serverDebugDebugPathSvcVerbose OBJECT-TYPE
      SYNTAX      OCTET STRING
      MAX-ACCESS  read-only
      STATUS      current
      DESCRIPTION "Detailed debug for the Path Service "
      ::= { serverDebugEntry 228  }
   
   
   serverDebugDebugWTCGwtEx OBJECT-TYPE
      SYNTAX      OCTET STRING
      MAX-ACCESS  read-only
      STATUS      current
      DESCRIPTION "Debug WTC gwt execution "
      ::= { serverDebugEntry 229  }
   
   
   serverDebugDebugConnectorService OBJECT-TYPE
      SYNTAX      OCTET STRING
      MAX-ACCESS  read-only
      STATUS      current
      DESCRIPTION "Debug connector service action processing "
      ::= { serverDebugEntry 230  }
   
   
   serverDebugDebugJMSMessagePath OBJECT-TYPE
      SYNTAX      OCTET STRING
      MAX-ACCESS  read-only
      STATUS      current
      DESCRIPTION "Debug JMS MessagePath processing "
      ::= { serverDebugEntry 231  }
   
   
   serverDebugDebugJTAMigration OBJECT-TYPE
      SYNTAX      OCTET STRING
      MAX-ACCESS  read-only
      STATUS      current
      DESCRIPTION "Debug JTA TLOG Migration "
      ::= { serverDebugEntry 232  }
   
   
   serverDebugDebugSecurityRealm OBJECT-TYPE
      SYNTAX      OCTET STRING
      MAX-ACCESS  read-only
      STATUS      current
      DESCRIPTION "Debug Security Realm processing "
      ::= { serverDebugEntry 233  }
   
   
   serverDebugDebugIIOPStartup OBJECT-TYPE
      SYNTAX      OCTET STRING
      MAX-ACCESS  read-only
      STATUS      current
      DESCRIPTION "Debug IIOP startup processing "
      ::= { serverDebugEntry 234  }
   
   
   serverDebugDebugJDBCDriverLogging OBJECT-TYPE
      SYNTAX      OCTET STRING
      MAX-ACCESS  read-only
      STATUS      current
      DESCRIPTION "Debug JDBC DriverLogging processing "
      ::= { serverDebugEntry 235  }
   
   
   serverDebugDebugJMSModule OBJECT-TYPE
      SYNTAX      OCTET STRING
      MAX-ACCESS  read-only
      STATUS      current
      DESCRIPTION "Debug JMSModule deployment processing "
      ::= { serverDebugEntry 236  }
   
   
   serverDebugDebugEjbCmpRuntime OBJECT-TYPE
      SYNTAX      OCTET STRING
      MAX-ACCESS  read-only
      STATUS      current
      DESCRIPTION "Debug EJB CMP runtime processing "
      ::= { serverDebugEntry 237  }
   
   
   serverDebugDebugWANReplicationDetails OBJECT-TYPE
      SYNTAX      OCTET STRING
      MAX-ACCESS  read-only
      STATUS      current
      DESCRIPTION "Debug low-level wan replication processing "
      ::= { serverDebugEntry 238  }
   
   
   serverDebugDebugJMST3Server OBJECT-TYPE
      SYNTAX      OCTET STRING
      MAX-ACCESS  read-only
      STATUS      current
      DESCRIPTION "Debug DebugJMST3Server processing "
      ::= { serverDebugEntry 239  }
   
   
   serverDebugDebugXMLEntityCacheIncludeLocation OBJECT-TYPE
      SYNTAX      OCTET STRING
      MAX-ACCESS  read-only
      STATUS      current
      DESCRIPTION "XMLEntityCache debugging option: Debug IncludeLocation "
      ::= { serverDebugEntry 240  }
   
   
   serverDebugDebugSAFVerbose OBJECT-TYPE
      SYNTAX      OCTET STRING
      MAX-ACCESS  read-only
      STATUS      current
      DESCRIPTION "Detailed debug of Messaging SAF. "
      ::= { serverDebugEntry 241  }
   
   
   serverDebugDebugDRSQueues OBJECT-TYPE
      SYNTAX      OCTET STRING
      MAX-ACCESS  read-only
      STATUS      current
      DESCRIPTION "Debug DRS Queueing traffic. "
      ::= { serverDebugEntry 242  }
   
   
   serverDebugDebugDiagnosticInstrumentationActions OBJECT-TYPE
      SYNTAX      OCTET STRING
      MAX-ACCESS  read-only
      STATUS      current
      DESCRIPTION "Debug instrumentation actions/monitors "
      ::= { serverDebugEntry 243  }
   
   
   serverDebugDebugDiagnosticsHarvester OBJECT-TYPE
      SYNTAX      OCTET STRING
      MAX-ACCESS  read-only
      STATUS      current
      DESCRIPTION "Debug diagnostic harvester processing "
      ::= { serverDebugEntry 244  }
   
   
   serverDebugDebugEjbMdbConnection OBJECT-TYPE
      SYNTAX      OCTET STRING
      MAX-ACCESS  read-only
      STATUS      current
      DESCRIPTION "Debug EJB MDB Connection processing "
      ::= { serverDebugEntry 245  }
   
   
   serverDebugDebugJTANaming OBJECT-TYPE
      SYNTAX      OCTET STRING
      MAX-ACCESS  read-only
      STATUS      current
      DESCRIPTION "Debug JTA naming "
      ::= { serverDebugEntry 246  }
   
   
   serverDebugDebugSecuritySSLEaten OBJECT-TYPE
      SYNTAX      OCTET STRING
      MAX-ACCESS  read-only
      STATUS      current
      DESCRIPTION "Debug Security SSL and TLS exception processing "
      ::= { serverDebugEntry 247  }
   
   
   serverDebugDebugEjbTimers OBJECT-TYPE
      SYNTAX      OCTET STRING
      MAX-ACCESS  read-only
      STATUS      current
      DESCRIPTION "Debug EJB Timer processing "
      ::= { serverDebugEntry 248  }
   
   
   serverDebugDebugJMXCore OBJECT-TYPE
      SYNTAX      OCTET STRING
      MAX-ACCESS  read-only
      STATUS      current
      DESCRIPTION "Debug core JMX processing "
      ::= { serverDebugEntry 249  }
   
   
   serverDebugDebugJpaTool OBJECT-TYPE
      SYNTAX      OCTET STRING
      MAX-ACCESS  read-only
      STATUS      current
      DESCRIPTION "Debug JPA tools "
      ::= { serverDebugEntry 250  }
   
   
   serverDebugDebugIIOPNaming OBJECT-TYPE
      SYNTAX      OCTET STRING
      MAX-ACCESS  read-only
      STATUS      current
      DESCRIPTION "Debug IIOP CosNaming processing "
      ::= { serverDebugEntry 251  }
   
   
   serverDebugDebugJTARMI OBJECT-TYPE
      SYNTAX      OCTET STRING
      MAX-ACCESS  read-only
      STATUS      current
      DESCRIPTION "Debug JTA RMI processing "
      ::= { serverDebugEntry 252  }
   
   
   serverDebugDebugJMSFrontEnd OBJECT-TYPE
      SYNTAX      OCTET STRING
      MAX-ACCESS  read-only
      STATUS      current
      DESCRIPTION "Debug JMSFrontEnd processing "
      ::= { serverDebugEntry 253  }
   
   
   serverDebugDebugSecuritySAMLService OBJECT-TYPE
      SYNTAX      OCTET STRING
      MAX-ACCESS  read-only
      STATUS      current
      DESCRIPTION "Debug Security Framework SAML SSO profile services "
      ::= { serverDebugEntry 254  }
   
   
   serverDebugDebugRA OBJECT-TYPE
      SYNTAX      OCTET STRING
      MAX-ACCESS  read-only
      STATUS      current
      DESCRIPTION "Debug Resource Adapter XA general/top-level processing "
      ::= { serverDebugEntry 255  }
   
   
   serverDebugDebugXMLRegistryDebugName OBJECT-TYPE
      SYNTAX      OCTET STRING
      MAX-ACCESS  read-only
      STATUS      current
      DESCRIPTION "XML Registry debugging option: Debug name "
      ::= { serverDebugEntry 256  }
   
   
   serverDebugDebugSelfTuning OBJECT-TYPE
      SYNTAX      OCTET STRING
      MAX-ACCESS  read-only
      STATUS      current
      DESCRIPTION "Debug WorkManager self-tuning processing "
      ::= { serverDebugEntry 257  }
   
   
   serverDebugDebugIIOPMarshal OBJECT-TYPE
      SYNTAX      OCTET STRING
      MAX-ACCESS  read-only
      STATUS      current
      DESCRIPTION "Debug buffer-level IIOP processing "
      ::= { serverDebugEntry 258  }
   
   
   serverDebugDebugSecurityAtz OBJECT-TYPE
      SYNTAX      OCTET STRING
      MAX-ACCESS  read-only
      STATUS      current
      DESCRIPTION "Debug Security Framework Atz processing "
      ::= { serverDebugEntry 259  }
   
   
   serverDebugDebugIIOPOTS OBJECT-TYPE
      SYNTAX      OCTET STRING
      MAX-ACCESS  read-only
      STATUS      current
      DESCRIPTION "Debug IIOP Object Transaction Service (OTS) processing "
      ::= { serverDebugEntry 260  }
   
   
   serverDebugDebugDeployment OBJECT-TYPE
      SYNTAX      OCTET STRING
      MAX-ACCESS  read-only
      STATUS      current
      DESCRIPTION "Debug deployment processing "
      ::= { serverDebugEntry 261  }
   
   
   serverDebugDebugRAWorkEvents OBJECT-TYPE
      SYNTAX      OCTET STRING
      MAX-ACCESS  read-only
      STATUS      current
      DESCRIPTION "Debug Resource Adapter work event processing "
      ::= { serverDebugEntry 262  }
   
   
   serverDebugDebugJTAGateway OBJECT-TYPE
      SYNTAX      OCTET STRING
      MAX-ACCESS  read-only
      STATUS      current
      DESCRIPTION "Debug JTA imported transactions "
      ::= { serverDebugEntry 263  }
   
   
   serverDebugDebugWebAppIdentityAssertion OBJECT-TYPE
      SYNTAX      OCTET STRING
      MAX-ACCESS  read-only
      STATUS      current
      DESCRIPTION "Debug identity assertion flow when identity assertion occurs in the webapp container. "
      ::= { serverDebugEntry 264  }
   
   
   serverDebugDebugMuxerConnection OBJECT-TYPE
      SYNTAX      OCTET STRING
      MAX-ACCESS  read-only
      STATUS      current
      DESCRIPTION "Debug Muxer connection processing "
      ::= { serverDebugEntry 265  }
   
   
   serverDebugDebugDiagnosticArchiveRetirement OBJECT-TYPE
      SYNTAX      OCTET STRING
      MAX-ACCESS  read-only
      STATUS      current
      DESCRIPTION "Debug diagnostic archive retirement processing "
      ::= { serverDebugEntry 266  }
   
   
   serverDebugDebugRAPoolVerbose OBJECT-TYPE
      SYNTAX      OCTET STRING
      MAX-ACCESS  read-only
      STATUS      current
      DESCRIPTION "Debug Java EE Resource Adapter pool management (size management) processing "
      ::= { serverDebugEntry 267  }
   
   
   serverDebugDebugStoreIOLogical OBJECT-TYPE
      SYNTAX      OCTET STRING
      MAX-ACCESS  read-only
      STATUS      current
      DESCRIPTION "Debug persistent store high-level logical operations, such as read, write, delete, and update. Multiple logical operations may occur in a single physical operation. "
      ::= { serverDebugEntry 268  }
   
   
   serverDebugDebugRAConnections OBJECT-TYPE
      SYNTAX      OCTET STRING
      MAX-ACCESS  read-only
      STATUS      current
      DESCRIPTION "Debug Resource Adapter outbound connection operations (get, close, associate, disassociate, ping) "
      ::= { serverDebugEntry 269  }
   
   
   serverDebugDebugReplicationDetails OBJECT-TYPE
      SYNTAX      OCTET STRING
      MAX-ACCESS  read-only
      STATUS      current
      DESCRIPTION "Debug low-level cluster replication information. "
      ::= { serverDebugEntry 270  }
   
   
   serverDebugDebugDiagnosticsHarvesterMBeanPlugin OBJECT-TYPE
      SYNTAX      OCTET STRING
      MAX-ACCESS  read-only
      STATUS      current
      DESCRIPTION "Debug MBean harvester processing. This should probably be used in conjunction with DebugDiagnosticsHarvester. "
      ::= { serverDebugEntry 271  }
   
   
   serverDebugDebugRALifecycle OBJECT-TYPE
      SYNTAX      OCTET STRING
      MAX-ACCESS  read-only
      STATUS      current
      DESCRIPTION "Debug ResourceAdapter Lifecycle processing "
      ::= { serverDebugEntry 272  }
   
   
   serverDebugDebugJMSDistTopic OBJECT-TYPE
      SYNTAX      OCTET STRING
      MAX-ACCESS  read-only
      STATUS      current
      DESCRIPTION "Debug JMS Distributed Topic processing "
      ::= { serverDebugEntry 273  }
   
   
   serverDebugDebugDGCEnrollment OBJECT-TYPE
      SYNTAX      OCTET STRING
      MAX-ACCESS  read-only
      STATUS      current
      DESCRIPTION "Debug each DGC enrollment. "
      ::= { serverDebugEntry 274  }
   
   
   serverDebugDebugPathSvc OBJECT-TYPE
      SYNTAX      OCTET STRING
      MAX-ACCESS  read-only
      STATUS      current
      DESCRIPTION "Debug the Path Service "
      ::= { serverDebugEntry 275  }
   
   
   serverDebugDebugDiagnosticContext OBJECT-TYPE
      SYNTAX      OCTET STRING
      MAX-ACCESS  read-only
      STATUS      current
      DESCRIPTION "Debug diagnostic context processing "
      ::= { serverDebugEntry 276  }
   
   
   serverDebugDebugClassRedef OBJECT-TYPE
      SYNTAX      OCTET STRING
      MAX-ACCESS  read-only
      STATUS      current
      DESCRIPTION "Gets the DebugClassRedef attribute of ServerDebugMBean "
      ::= { serverDebugEntry 277  }
   
   
   serverDebugDebugSAFMessagePath OBJECT-TYPE
      SYNTAX      OCTET STRING
      MAX-ACCESS  read-only
      STATUS      current
      DESCRIPTION "Debug Messaging SAF MessagePath. "
      ::= { serverDebugEntry 278  }
   
   
   serverDebugDebugJMSXA OBJECT-TYPE
      SYNTAX      OCTET STRING
      MAX-ACCESS  read-only
      STATUS      current
      DESCRIPTION "Debug JMS XA processing "
      ::= { serverDebugEntry 279  }
   
   
   serverDebugDebugClassSize OBJECT-TYPE
      SYNTAX      OCTET STRING
      MAX-ACCESS  read-only
      STATUS      current
      DESCRIPTION "Gets the fastswap DebugClassSize debug attribute of ServerDebugMBean "
      ::= { serverDebugEntry 280  }
   
   
   serverDebugDebugJMSDurableSubscribers OBJECT-TYPE
      SYNTAX      OCTET STRING
      MAX-ACCESS  read-only
      STATUS      current
      DESCRIPTION "Debug JMS durable subscriber operations "
      ::= { serverDebugEntry 281  }
   
   
   serverDebugClassChangeNotifier OBJECT-TYPE
      SYNTAX      OCTET STRING
      MAX-ACCESS  read-only
      STATUS      current
      DESCRIPTION "Gets the fastswap ClassChangeNotifier debug attribute of ServerDebugMBean "
      ::= { serverDebugEntry 282  }
   
   
   serverDebugDebugJMSStore OBJECT-TYPE
      SYNTAX      OCTET STRING
      MAX-ACCESS  read-only
      STATUS      current
      DESCRIPTION "Debug JMS Store operations "
      ::= { serverDebugEntry 283  }
   
   
   serverDebugDebugAsyncQueue OBJECT-TYPE
      SYNTAX      OCTET STRING
      MAX-ACCESS  read-only
      STATUS      current
      DESCRIPTION "Debug async replication/persistence information. "
      ::= { serverDebugEntry 284  }
   
   
   serverDebugRedefiningClassLoader OBJECT-TYPE
      SYNTAX      OCTET STRING
      MAX-ACCESS  read-only
      STATUS      current
      DESCRIPTION "Gets the fastswap RedefiningClassLoader debug attribute of ServerDebugMBean "
      ::= { serverDebugEntry 285  }
   
   
   serverDebugDebugMaskCriterias OBJECT-TYPE
      SYNTAX      OCTET STRING
      MAX-ACCESS  read-only
      STATUS      current
      DESCRIPTION "Dye mask criteria used to determine whether debug will be emitted for a request. Specifies the names of the Dye flags that will be inspected at runtime to determine whether debug needs to be emitted for a request. "
      ::= { serverDebugEntry 286  }
   
   
   serverDebugDebugSecuritySAML2Lib OBJECT-TYPE
      SYNTAX      OCTET STRING
      MAX-ACCESS  read-only
      STATUS      current
      DESCRIPTION "Debug Security Framework SAML2 library processing "
      ::= { serverDebugEntry 287  }
   
   
   serverDebugDebugSecuritySAML2Atn OBJECT-TYPE
      SYNTAX      OCTET STRING
      MAX-ACCESS  read-only
      STATUS      current
      DESCRIPTION "Debug Security Framework SAML2 Provider atn processing "
      ::= { serverDebugEntry 288  }
   
   
   serverDebugDebugIIOP OBJECT-TYPE
      SYNTAX      OCTET STRING
      MAX-ACCESS  read-only
      STATUS      current
      DESCRIPTION "Debug IIOP processing "
      ::= { serverDebugEntry 289  }
   
   
   serverDebugDebugJMSLocking OBJECT-TYPE
      SYNTAX      OCTET STRING
      MAX-ACCESS  read-only
      STATUS      current
      DESCRIPTION "Debug JMS Lock processing "
      ::= { serverDebugEntry 290  }
   
   
   serverDebugDefaultStore OBJECT-TYPE
      SYNTAX      OCTET STRING
      MAX-ACCESS  read-only
      STATUS      current
      DESCRIPTION "Gets the fastswap DefaultStore debug attribute of ServerDebugMBean "
      ::= { serverDebugEntry 291  }
   
   
   serverDebugDebugJMSAME OBJECT-TYPE
      SYNTAX      OCTET STRING
      MAX-ACCESS  read-only
      STATUS      current
      DESCRIPTION "Debug JMS AME processing "
      ::= { serverDebugEntry 292  }
   
   
   serverDebugDebugSecuritySAML2CredMap OBJECT-TYPE
      SYNTAX      OCTET STRING
      MAX-ACCESS  read-only
      STATUS      current
      DESCRIPTION "Debug Security Framework SAML2 Provider credential mapper processing "
      ::= { serverDebugEntry 293  }
   
   
   serverDebugDebugSAFLifeCycle OBJECT-TYPE
      SYNTAX      OCTET STRING
      MAX-ACCESS  read-only
      STATUS      current
      DESCRIPTION "Debug Messaging SAF Lifecycle. "
      ::= { serverDebugEntry 294  }
   
   
   serverDebugDebugBootstrapServlet OBJECT-TYPE
      SYNTAX      OCTET STRING
      MAX-ACCESS  read-only
      STATUS      current
      DESCRIPTION "Debug the bootstrap servlet that runs on the Admin Server and is invoked over HTTP by a booting managed server. "
      ::= { serverDebugEntry 295  }
   
   
   serverDebugDebugStoreXAVerbose OBJECT-TYPE
      SYNTAX      OCTET STRING
      MAX-ACCESS  read-only
      STATUS      current
      DESCRIPTION "Detailed debug of persistent store resource manager transaction activity, includes tracing for the related operations of layered subsystems (such as JMS). "
      ::= { serverDebugEntry 296  }
   
   
   serverDebugDebugServerStartStatistics OBJECT-TYPE
      SYNTAX      OCTET STRING
      MAX-ACCESS  read-only
      STATUS      current
      DESCRIPTION " If statistics about server start will be logged after the running message. "
      ::= { serverDebugEntry 297  }
   
   
   serverDebugDebugJMSJDBCScavengeOnFlush OBJECT-TYPE
      SYNTAX      OCTET STRING
      MAX-ACCESS  read-only
      STATUS      current
      DESCRIPTION "Debug JMS JDBC store scavenge mode processing "
      ::= { serverDebugEntry 298  }
   
   
   serverDebugDebugStoreXA OBJECT-TYPE
      SYNTAX      OCTET STRING
      MAX-ACCESS  read-only
      STATUS      current
      DESCRIPTION "Debug persistent store resource manager transaction activity, includes tracing for the related operations of layered subsystems (such as JMS). "
      ::= { serverDebugEntry 299  }
   
   
   serverDebugDebugSecuritySAML2Service OBJECT-TYPE
      SYNTAX      OCTET STRING
      MAX-ACCESS  read-only
      STATUS      current
      DESCRIPTION "Debug Security Framework SAML2 SSO profile services "
      ::= { serverDebugEntry 300  }
   
   
   serverDebugDebugRAClassloader OBJECT-TYPE
      SYNTAX      OCTET STRING
      MAX-ACCESS  read-only
      STATUS      current
      DESCRIPTION "Debug Resource Adapter class loading "
      ::= { serverDebugEntry 301  }
   
   
   serverDebugDebugWorkContext OBJECT-TYPE
      SYNTAX      OCTET STRING
      MAX-ACCESS  read-only
      STATUS      current
      DESCRIPTION "Debug Work context (out of band data propagation) "
      ::= { serverDebugEntry 302  }
   
   
   serverDebugDebugSNMPExtensionProvider OBJECT-TYPE
      SYNTAX      OCTET STRING
      MAX-ACCESS  read-only
      STATUS      current
      DESCRIPTION " The debug attribute to enable or disable the SNMP Agent Extension Provider discovery and initialization.  "
      ::= { serverDebugEntry 303  }
   
   
   serverDebugDebugScaContainer OBJECT-TYPE
      SYNTAX      OCTET STRING
      MAX-ACCESS  read-only
      STATUS      current
      DESCRIPTION "Debug Weblogic SCA Container  "
      ::= { serverDebugEntry 304  }
   
   
   serverDebugDebugDiagnosticDataGathering OBJECT-TYPE
      SYNTAX      OCTET STRING
      MAX-ACCESS  read-only
      STATUS      current
      DESCRIPTION "Debug data gathering processing "
      ::= { serverDebugEntry 305  }
   
   
   serverDebugDebugJDBCRAC OBJECT-TYPE
      SYNTAX      OCTET STRING
      MAX-ACCESS  read-only
      STATUS      current
      DESCRIPTION "Debug Oracle RAC processing "
      ::= { serverDebugEntry 306  }
   
   
   serverDebugDebugJDBCONS OBJECT-TYPE
      SYNTAX      OCTET STRING
      MAX-ACCESS  read-only
      STATUS      current
      DESCRIPTION "Debug ONS client  "
      ::= { serverDebugEntry 307  }
   
   
   serverDebugDebugMBeanTypeUtilityListener OBJECT-TYPE
      SYNTAX      OCTET STRING
      MAX-ACCESS  read-only
      STATUS      current
      DESCRIPTION "Debug the Harvester MBean registration processing "
      ::= { serverDebugEntry 308  }
   
   
   serverDebugDebugMBeanTypingUtility OBJECT-TYPE
      SYNTAX      OCTET STRING
      MAX-ACCESS  read-only
      STATUS      current
      DESCRIPTION "Debug the Harvester MBean type utility "
      ::= { serverDebugEntry 309  }
   
   
   serverDebugDebugDiagnosticRuntimeControlService OBJECT-TYPE
      SYNTAX      OCTET STRING
      MAX-ACCESS  read-only
      STATUS      current
      DESCRIPTION "Debug the WLDF runtime control service. "
      ::= { serverDebugEntry 310  }
   
   
   serverDebugDebugDiagnosticRuntimeControlDriver OBJECT-TYPE
      SYNTAX      OCTET STRING
      MAX-ACCESS  read-only
      STATUS      current
      DESCRIPTION "Debug the WLDF runtime control MBeans. "
      ::= { serverDebugEntry 311  }
   
   
   serverDebugDebugEjbMetadata OBJECT-TYPE
      SYNTAX      OCTET STRING
      MAX-ACCESS  read-only
      STATUS      current
      DESCRIPTION "Debug EJB metadata processing "
      ::= { serverDebugEntry 312  }
   
   
   serverDebugDebugManagementServicesResource OBJECT-TYPE
      SYNTAX      OCTET STRING
      MAX-ACCESS  read-only
      STATUS      current
      DESCRIPTION "Debug Management Services Resources "
      ::= { serverDebugEntry 313  }
   
   
   serverDebugDebugDeploymentPlan OBJECT-TYPE
      SYNTAX      OCTET STRING
      MAX-ACCESS  read-only
      STATUS      current
      DESCRIPTION "Debug deployment plan processing "
      ::= { serverDebugEntry 314  }
   
   
   serverDebugDebugMBeanTypeUtilQueue OBJECT-TYPE
      SYNTAX      OCTET STRING
      MAX-ACCESS  read-only
      STATUS      current
      DESCRIPTION "Debug the Harvester MBean registration queue events "
      ::= { serverDebugEntry 315  }
   
   
   serverDebugDebugJDBCReplay OBJECT-TYPE
      SYNTAX      OCTET STRING
      MAX-ACCESS  read-only
      STATUS      current
      DESCRIPTION "Debug REPLAY client  "
      ::= { serverDebugEntry 316  }
   
   
   serverDebugDebugCertRevocCheck OBJECT-TYPE
      SYNTAX      OCTET STRING
      MAX-ACCESS  read-only
      STATUS      current
      DESCRIPTION "Debug Security PKI X.509 certificate revocation checking "
      ::= { serverDebugEntry 317  }
   
   
   serverDebugDebugMBeanTypeUtilQueuePriority OBJECT-TYPE
      SYNTAX      OCTET STRING
      MAX-ACCESS  read-only
      STATUS      current
      DESCRIPTION "Debug the Harvester MBean registration prioritized events processing "
      ::= { serverDebugEntry 318  }
   
   
   serverDebugDebugJDBCUCP OBJECT-TYPE
      SYNTAX      OCTET STRING
      MAX-ACCESS  read-only
      STATUS      current
      DESCRIPTION "Debug Oracle UCP processing "
      ::= { serverDebugEntry 319  }
   
   
   serverDebugDebugReplicationSize OBJECT-TYPE
      SYNTAX      OCTET STRING
      MAX-ACCESS  read-only
      STATUS      current
      DESCRIPTION "Debug cluster replication size information. "
      ::= { serverDebugEntry 320  }
   
   
   serverDebugDebugDiagnosticWatchEventsDetails OBJECT-TYPE
      SYNTAX      OCTET STRING
      MAX-ACCESS  read-only
      STATUS      current
      DESCRIPTION "Debug diagnostic policy event processing details. "
      ::= { serverDebugEntry 321  }
   
   
   serverDebugDebugDiagnosticWatchEvents OBJECT-TYPE
      SYNTAX      OCTET STRING
      MAX-ACCESS  read-only
      STATUS      current
      DESCRIPTION "Debug diagnostic policy events processing. "
      ::= { serverDebugEntry 322  }
   
   
   serverDebugDebugClassLoadingVerbose OBJECT-TYPE
      SYNTAX      OCTET STRING
      MAX-ACCESS  read-only
      STATUS      current
      DESCRIPTION "Verbose Debugger for Class Loading "
      ::= { serverDebugEntry 323  }
   
   
   serverDebugDebugClassLoadingContextualTrace OBJECT-TYPE
      SYNTAX      OCTET STRING
      MAX-ACCESS  read-only
      STATUS      current
      DESCRIPTION "Contextual Trace Debugger for Class Loading "
      ::= { serverDebugEntry 324  }
   
   
   serverDebugTags OBJECT-TYPE
      SYNTAX      OCTET STRING
      MAX-ACCESS  read-only
      STATUS      current
      DESCRIPTION "Return all tags on this Configuration MBean "
      ::= { serverDebugEntry 325  }
   
   
   serverDebugDebugExpressionBeanLocalizer OBJECT-TYPE
      SYNTAX      OCTET STRING
      MAX-ACCESS  read-only
      STATUS      current
      DESCRIPTION "Debug the Diagnostics expressions framework extension bean localizer "
      ::= { serverDebugEntry 326  }
   
   
   serverDebugDebugInterceptors OBJECT-TYPE
      SYNTAX      OCTET STRING
      MAX-ACCESS  read-only
      STATUS      current
      DESCRIPTION "Debug interceptors processing "
      ::= { serverDebugEntry 327  }
   
   
   serverDebugDebugDiagnosticsELContext OBJECT-TYPE
      SYNTAX      OCTET STRING
      MAX-ACCESS  read-only
      STATUS      current
      DESCRIPTION "Debug the ELContext in the Diagnostics expressions framework "
      ::= { serverDebugEntry 328  }
   
   
   serverDebugDebugConcurrentContext OBJECT-TYPE
      SYNTAX      OCTET STRING
      MAX-ACCESS  read-only
      STATUS      current
      DESCRIPTION "Debug concurrent context processing "
      ::= { serverDebugEntry 329  }
   
   
   serverDebugDebugReadyApp OBJECT-TYPE
      SYNTAX      OCTET STRING
      MAX-ACCESS  read-only
      STATUS      current
      DESCRIPTION "Debug ReadyApp processing. "
      ::= { serverDebugEntry 330  }
   
   
   serverDebugDebugDiagnosticsExpressionPollerBuffer OBJECT-TYPE
      SYNTAX      OCTET STRING
      MAX-ACCESS  read-only
      STATUS      current
      DESCRIPTION "Debug the Diagnostics expressions poller extract() buffers "
      ::= { serverDebugEntry 331  }
   
   
   serverDebugDebugDiagnosticsUtils OBJECT-TYPE
      SYNTAX      OCTET STRING
      MAX-ACCESS  read-only
      STATUS      current
      DESCRIPTION "Debug the Diagnostics utils "
      ::= { serverDebugEntry 332  }
   
   
   serverDebugDebugDiagnosticsExpressionMetrics OBJECT-TYPE
      SYNTAX      OCTET STRING
      MAX-ACCESS  read-only
      STATUS      current
      DESCRIPTION "Debug metrics collection for the Diagnostics expressions framework "
      ::= { serverDebugEntry 333  }
   
   
   serverDebugDebugConcurrentMSES OBJECT-TYPE
      SYNTAX      OCTET STRING
      MAX-ACCESS  read-only
      STATUS      current
      DESCRIPTION "Debug concurrent MSES processing "
      ::= { serverDebugEntry 334  }
   
   
   serverDebugDebugDynamicSingletonServices OBJECT-TYPE
      SYNTAX      OCTET STRING
      MAX-ACCESS  read-only
      STATUS      current
      DESCRIPTION "Debug Dynamic Service Migration processing "
      ::= { serverDebugEntry 335  }
   
   
   serverDebugDebugJTACDI OBJECT-TYPE
      SYNTAX      OCTET STRING
      MAX-ACCESS  read-only
      STATUS      current
      DESCRIPTION "Debug JTA CDI log processing "
      ::= { serverDebugEntry 336  }
   
   
   serverDebugDebugVerboseRCM OBJECT-TYPE
      SYNTAX      OCTET STRING
      MAX-ACCESS  read-only
      STATUS      current
      DESCRIPTION "Debug Verbose RCM "
      ::= { serverDebugEntry 337  }
   
   
   serverDebugDebugDiagnosticsELResolver OBJECT-TYPE
      SYNTAX      OCTET STRING
      MAX-ACCESS  read-only
      STATUS      current
      DESCRIPTION "Debug the DiagnosticsELResolver in the Diagnostics expressions framework "
      ::= { serverDebugEntry 338  }
   
   
   serverDebugPartitionDebugLoggingEnabled OBJECT-TYPE
      SYNTAX      OCTET STRING
      MAX-ACCESS  read-only
      STATUS      current
      DESCRIPTION "Enables or disables whether Partition Administrators can enable Debug Logging for their respective Partitions. "
      ::= { serverDebugEntry 339  }
   
   
   serverDebugDebugDiagnosticsExpressionPoller OBJECT-TYPE
      SYNTAX      OCTET STRING
      MAX-ACCESS  read-only
      STATUS      current
      DESCRIPTION "Debug metrics polling for the Diagnostics expressions framework "
      ::= { serverDebugEntry 340  }
   
   
   serverDebugDebugDiagnosticsExpressionFunctionMapper OBJECT-TYPE
      SYNTAX      OCTET STRING
      MAX-ACCESS  read-only
      STATUS      current
      DESCRIPTION "Debug the Diagnostics expressions framework function mapper "
      ::= { serverDebugEntry 341  }
   
   
   serverDebugDebugConcurrentTransaction OBJECT-TYPE
      SYNTAX      OCTET STRING
      MAX-ACCESS  read-only
      STATUS      current
      DESCRIPTION "Debug concurrent transaction processing "
      ::= { serverDebugEntry 342  }
   
   
   serverDebugDebugElasticServices OBJECT-TYPE
      SYNTAX      OCTET STRING
      MAX-ACCESS  read-only
      STATUS      current
      DESCRIPTION "Debug the elastic services framework "
      ::= { serverDebugEntry 343  }
   
   
   serverDebugDebugMBeanHarvesterResolution OBJECT-TYPE
      SYNTAX      OCTET STRING
      MAX-ACCESS  read-only
      STATUS      current
      DESCRIPTION "Debug the JMX Harvester delegate metric resolution process. "
      ::= { serverDebugEntry 344  }
   
   
   serverDebugDebugBeanTreeHarvesterDataCollection OBJECT-TYPE
      SYNTAX      OCTET STRING
      MAX-ACCESS  read-only
      STATUS      current
      DESCRIPTION "Debug the BeanTree Harvester delegate metric collection process. "
      ::= { serverDebugEntry 345  }
   
   
   serverDebugDebugRCM OBJECT-TYPE
      SYNTAX      OCTET STRING
      MAX-ACCESS  read-only
      STATUS      current
      DESCRIPTION "Debug RCM "
      ::= { serverDebugEntry 346  }
   
   
   serverDebugDebugDiagnosticsScriptAction OBJECT-TYPE
      SYNTAX      OCTET STRING
      MAX-ACCESS  read-only
      STATUS      current
      DESCRIPTION "Debug the diagnostics policy script action. "
      ::= { serverDebugEntry 347  }
   
   
   serverDebugDebugNodeManagerRuntime OBJECT-TYPE
      SYNTAX      OCTET STRING
      MAX-ACCESS  read-only
      STATUS      current
      DESCRIPTION "Debug NodeManagerRuntime "
      ::= { serverDebugEntry 348  }
   
   
   serverDebugDebugRESTNotifications OBJECT-TYPE
      SYNTAX      OCTET STRING
      MAX-ACCESS  read-only
      STATUS      current
      DESCRIPTION "Debug the diagnostics policy REST action. "
      ::= { serverDebugEntry 349  }
   
   
   serverDebugDebugPatchingRuntime OBJECT-TYPE
      SYNTAX      OCTET STRING
      MAX-ACCESS  read-only
      STATUS      current
      DESCRIPTION "Debug management patching runtime processing "
      ::= { serverDebugEntry 350  }
   
   
   serverDebugDebugConcurrentMES OBJECT-TYPE
      SYNTAX      OCTET STRING
      MAX-ACCESS  read-only
      STATUS      current
      DESCRIPTION "Debug concurrent MES processing "
      ::= { serverDebugEntry 351  }
   
   
   serverDebugDebugDiagnosticsExpressionFunctions OBJECT-TYPE
      SYNTAX      OCTET STRING
      MAX-ACCESS  read-only
      STATUS      current
      DESCRIPTION "Debug the Diagnostics expressions framework functions "
      ::= { serverDebugEntry 352  }
   
   
   serverDebugDebugDiagnosticsMBeanELResolver OBJECT-TYPE
      SYNTAX      OCTET STRING
      MAX-ACCESS  read-only
      STATUS      current
      DESCRIPTION "Debug the MBean ELResolver in the Diagnostics expressions framework "
      ::= { serverDebugEntry 353  }
   
   
   serverDebugDebugBuzzProtocolHttp OBJECT-TYPE
      SYNTAX      OCTET STRING
      MAX-ACCESS  read-only
      STATUS      current
      DESCRIPTION "Debugs Buzz protocol http. "
      ::= { serverDebugEntry 354  }
   
   
   serverDebugDebugDiagnosticsValueTracingELResolver OBJECT-TYPE
      SYNTAX      OCTET STRING
      MAX-ACCESS  read-only
      STATUS      current
      DESCRIPTION "Debug the value tracing ELResolver in the Diagnostics expressions framework "
      ::= { serverDebugEntry 355  }
   
   
   serverDebugDebugElasticActions OBJECT-TYPE
      SYNTAX      OCTET STRING
      MAX-ACCESS  read-only
      STATUS      current
      DESCRIPTION "Debug the elastic actions framework "
      ::= { serverDebugEntry 356  }
   
   
   serverDebugDebugConcurrentMTF OBJECT-TYPE
      SYNTAX      OCTET STRING
      MAX-ACCESS  read-only
      STATUS      current
      DESCRIPTION "Debug concurrent MTF processing "
      ::= { serverDebugEntry 357  }
   
   
   serverDebugDebugAppAnnotations OBJECT-TYPE
      SYNTAX      OCTET STRING
      MAX-ACCESS  read-only
      STATUS      current
      DESCRIPTION " Debug AppContainer's scanning and processing of annotations "
      ::= { serverDebugEntry 358  }
   
   
   serverDebugDebugBeanTreeHarvesterControl OBJECT-TYPE
      SYNTAX      OCTET STRING
      MAX-ACCESS  read-only
      STATUS      current
      DESCRIPTION "Debug the BeanTree Harvester delegate metric control process. "
      ::= { serverDebugEntry 359  }
   
   
   serverDebugDebugExpressionExtensionsManager OBJECT-TYPE
      SYNTAX      OCTET STRING
      MAX-ACCESS  read-only
      STATUS      current
      DESCRIPTION "Debug the Diagnostics expressions extensions manager "
      ::= { serverDebugEntry 360  }
   
   
   serverDebugDebugMBeanHarvesterControl OBJECT-TYPE
      SYNTAX      OCTET STRING
      MAX-ACCESS  read-only
      STATUS      current
      DESCRIPTION "Debug the JMX Harvester delegate metric control process. "
      ::= { serverDebugEntry 361  }
   
   
   serverDebugDebugRestJersey1Integration OBJECT-TYPE
      SYNTAX      OCTET STRING
      MAX-ACCESS  read-only
      STATUS      current
      DESCRIPTION "Debug JAX-RS 1 / Jersey 1 Client integration "
      ::= { serverDebugEntry 362  }
   
   
   serverDebugDebugBeanTreeHarvesterResolution OBJECT-TYPE
      SYNTAX      OCTET STRING
      MAX-ACCESS  read-only
      STATUS      current
      DESCRIPTION "Debug the BeanTree Harvester delegate metric resolution process. "
      ::= { serverDebugEntry 363  }
   
   
   serverDebugDebugMBeanHarvesterDataCollection OBJECT-TYPE
      SYNTAX      OCTET STRING
      MAX-ACCESS  read-only
      STATUS      current
      DESCRIPTION "Debug the JMX Harvester delegate metric collection process. "
      ::= { serverDebugEntry 364  }
   
   
   serverDebugDebugLifecycleManager OBJECT-TYPE
      SYNTAX      OCTET STRING
      MAX-ACCESS  read-only
      STATUS      current
      DESCRIPTION "Debug Lifecycle Manager "
      ::= { serverDebugEntry 365  }
   
   
   serverDebugDebugDiagnosticsBeanExtensionResolver OBJECT-TYPE
      SYNTAX      OCTET STRING
      MAX-ACCESS  read-only
      STATUS      current
      DESCRIPTION "Debug the bean extensions ELResolver in the Diagnostics expressions framework "
      ::= { serverDebugEntry 366  }
   
   
   serverDebugDebugJMSDispatcherProxy OBJECT-TYPE
      SYNTAX      OCTET STRING
      MAX-ACCESS  read-only
      STATUS      current
      DESCRIPTION "Debug JMS Dispatcher Proxy "
      ::= { serverDebugEntry 367  }
   
   
   serverDebugDebugLocalRemoteJVM OBJECT-TYPE
      SYNTAX      OCTET STRING
      MAX-ACCESS  read-only
      STATUS      current
      DESCRIPTION "Debug how is LocalRemoteJVM working. "
      ::= { serverDebugEntry 368  }
   
   
   serverDebugDebugMBeanHarvesterThreading OBJECT-TYPE
      SYNTAX      OCTET STRING
      MAX-ACCESS  read-only
      STATUS      current
      DESCRIPTION "Debug JMX Harvester delegate threading issues. "
      ::= { serverDebugEntry 369  }
   
   
   serverDebugDebugRestJersey2Integration OBJECT-TYPE
      SYNTAX      OCTET STRING
      MAX-ACCESS  read-only
      STATUS      current
      DESCRIPTION "Debug JAX-RS 2 / Jersey 2 integration "
      ::= { serverDebugEntry 370  }
   
   
   serverDebugDebugBuzzProtocolDetails OBJECT-TYPE
      SYNTAX      OCTET STRING
      MAX-ACCESS  read-only
      STATUS      current
      DESCRIPTION "Debugs Buzz protocol details. "
      ::= { serverDebugEntry 371  }
   
   
   serverDebugDebugBeanTreeHarvesterThreading OBJECT-TYPE
      SYNTAX      OCTET STRING
      MAX-ACCESS  read-only
      STATUS      current
      DESCRIPTION "Debug BeanTree Harvester delegate threading issues. "
      ::= { serverDebugEntry 372  }
   
   
   serverDebugDebugPartitionResourceMetricsRuntime OBJECT-TYPE
      SYNTAX      OCTET STRING
      MAX-ACCESS  read-only
      STATUS      current
      DESCRIPTION "Debug PartitionResourceMetricsRuntimeMBean operations. "
      ::= { serverDebugEntry 373  }
   
   
   serverDebugDebugConcurrent OBJECT-TYPE
      SYNTAX      OCTET STRING
      MAX-ACCESS  read-only
      STATUS      current
      DESCRIPTION "Debug concurrent general processing "
      ::= { serverDebugEntry 374  }
   
   
   serverDebugDebugBuzzProtocol OBJECT-TYPE
      SYNTAX      OCTET STRING
      MAX-ACCESS  read-only
      STATUS      current
      DESCRIPTION "Debugs Buzz protocol. "
      ::= { serverDebugEntry 375  }
   
   
   serverDebugDebugDiagnosticsBeanInfoProviders OBJECT-TYPE
      SYNTAX      OCTET STRING
      MAX-ACCESS  read-only
      STATUS      current
      DESCRIPTION "Debug the custom BeanInfo providers for the Diagnostics expressions framework "
      ::= { serverDebugEntry 376  }
   
   
   serverDebugDebugMessagingOwnableLock OBJECT-TYPE
      SYNTAX      OCTET STRING
      MAX-ACCESS  read-only
      STATUS      current
      DESCRIPTION "Debugging for the messaging kernel ownable lock. This provides detailed information on lock owners. "
      ::= { serverDebugEntry 377  }
   
   
   serverDebugDebugHttpConcise OBJECT-TYPE
      SYNTAX      OCTET STRING
      MAX-ACCESS  read-only
      STATUS      current
      DESCRIPTION "Debug WebApp Container for supplimentary HTTP processing. "
      ::= { serverDebugEntry 378  }
   
   
   serverDebugDebugJMXCoreConcise OBJECT-TYPE
      SYNTAX      OCTET STRING
      MAX-ACCESS  read-only
      STATUS      current
      DESCRIPTION "Debug core JMX connection processing "
      ::= { serverDebugEntry 379  }
   
   
   serverDebugDebugDeploymentConcise OBJECT-TYPE
      SYNTAX      OCTET STRING
      MAX-ACCESS  read-only
      STATUS      current
      DESCRIPTION "Debug deployment concise processing "
      ::= { serverDebugEntry 380  }
   
   
   serverDebugDebugRestartInPlace OBJECT-TYPE
      SYNTAX      OCTET STRING
      MAX-ACCESS  read-only
      STATUS      current
      DESCRIPTION "Gets debugRestartInPlace attribute of ServerDebugMBean "
      ::= { serverDebugEntry 381  }
   
   
   serverDebugDebugDiagnosticsExpressionEvaluators OBJECT-TYPE
      SYNTAX      OCTET STRING
      MAX-ACCESS  read-only
      STATUS      current
      DESCRIPTION "Debug the EL expression evaluators for the Diagnostics expressions framework "
      ::= { serverDebugEntry 382  }
   
   
   serverDebugDebugSituationalConfig OBJECT-TYPE
      SYNTAX      OCTET STRING
      MAX-ACCESS  read-only
      STATUS      current
      DESCRIPTION "Debug management situational configuration processing "
      ::= { serverDebugEntry 383  }
   
   
   serverFailureTriggerTable OBJECT-TYPE
      SYNTAX      SEQUENCE OF ServerFailureTriggerEntry
      MAX-ACCESS  not-accessible
      STATUS      current
      DESCRIPTION "Configuration to mark the server as failed when threads are stuck. A failed server in turn can be configured to shutdown or go into admin state. "
      ::= { wls 1095  }
      
   
   serverFailureTriggerEntry OBJECT-TYPE
      SYNTAX      ServerFailureTriggerEntry
      MAX-ACCESS  not-accessible
      STATUS      current
      DESCRIPTION "Generated SNMP Table Entry."
      INDEX { serverFailureTriggerIndex}
      ::= { serverFailureTriggerTable 1 }
      
   ServerFailureTriggerEntry ::=
      SEQUENCE
      {
         serverFailureTriggerIndex OCTET STRING,
         serverFailureTriggerObjectName OCTET STRING,
         serverFailureTriggerType OCTET STRING,
         serverFailureTriggerMaxStuckThreadTime Integer32,
         serverFailureTriggerStuckThreadCount Integer32,
         serverFailureTriggerName OCTET STRING,
         serverFailureTriggerTags OCTET STRING
      }
      
   
   serverFailureTriggerIndex OBJECT-TYPE
      SYNTAX      OCTET STRING
      MAX-ACCESS  not-accessible
      STATUS      current
      DESCRIPTION "Index column"
      ::= { serverFailureTriggerEntry 1  }
   
   
   serverFailureTriggerObjectName OBJECT-TYPE
      SYNTAX      OCTET STRING
      MAX-ACCESS  read-only
      STATUS      current
      DESCRIPTION "ObjectName column"
      ::= { serverFailureTriggerEntry 2  }
   
   
   serverFailureTriggerType OBJECT-TYPE
      SYNTAX      OCTET STRING
      MAX-ACCESS  read-only
      STATUS      current
      DESCRIPTION "Returns the type of the MBean. "
      ::= { serverFailureTriggerEntry 3  }
   
   
   serverFailureTriggerMaxStuckThreadTime OBJECT-TYPE
      SYNTAX      Integer32
      MAX-ACCESS  read-only
      STATUS      current
      DESCRIPTION "The number of seconds that a thread must be continually working before this server diagnoses the thread as being stuck.  For example, if you set this to 600 seconds, WebLogic Server considers a thread to be 'stuck' after 600 seconds of continuous use. "
      ::= { serverFailureTriggerEntry 4  }
   
   
   serverFailureTriggerStuckThreadCount OBJECT-TYPE
      SYNTAX      Integer32
      MAX-ACCESS  read-only
      STATUS      current
      DESCRIPTION "The number of stuck threads after which the server is transitioned into FAILED state. There are options in OverloadProtectionMBean to suspend and shutdown a FAILED server. By default, the server continues to run in FAILED state.  If the StuckThreadCount value is set to zero then the server never transitions into FAILED server irrespective of the number of stuck threads.  "
      ::= { serverFailureTriggerEntry 5  }
   
   
   serverFailureTriggerName OBJECT-TYPE
      SYNTAX      OCTET STRING
      MAX-ACCESS  read-only
      STATUS      current
      DESCRIPTION "The user-specified name of this MBean instance.  This name is included as one of the key properties in the MBean's javax.management.ObjectName:  Name=user-specified-name "
      ::= { serverFailureTriggerEntry 6  }
   
   
   serverFailureTriggerTags OBJECT-TYPE
      SYNTAX      OCTET STRING
      MAX-ACCESS  read-only
      STATUS      current
      DESCRIPTION "Return all tags on this Configuration MBean "
      ::= { serverFailureTriggerEntry 7  }
   
   
   shutdownClassTable OBJECT-TYPE
      SYNTAX      SEQUENCE OF ShutdownClassEntry
      MAX-ACCESS  not-accessible
      STATUS      current
      DESCRIPTION "Provides methods for configuring a shutdown class. A shutdown class is a Java program that is automatically loaded and executed when a WebLogic Server instance is shut down gracefully. "
      ::= { wls 1100  }
      
   
   shutdownClassEntry OBJECT-TYPE
      SYNTAX      ShutdownClassEntry
      MAX-ACCESS  not-accessible
      STATUS      current
      DESCRIPTION "Generated SNMP Table Entry."
      INDEX { shutdownClassIndex}
      ::= { shutdownClassTable 1 }
      
   ShutdownClassEntry ::=
      SEQUENCE
      {
         shutdownClassIndex   OCTET STRING,
         shutdownClassObjectName OCTET STRING,
         shutdownClassType    OCTET STRING,
         shutdownClassDeploymentOrder Integer32,
         shutdownClassArguments OCTET STRING,
         shutdownClassName    OCTET STRING,
         shutdownClassClassName OCTET STRING,
         shutdownClassTags    OCTET STRING
      }
      
   
   shutdownClassIndex OBJECT-TYPE
      SYNTAX      OCTET STRING
      MAX-ACCESS  not-accessible
      STATUS      current
      DESCRIPTION "Index column"
      ::= { shutdownClassEntry 1  }
   
   
   shutdownClassObjectName OBJECT-TYPE
      SYNTAX      OCTET STRING
      MAX-ACCESS  read-only
      STATUS      current
      DESCRIPTION "ObjectName column"
      ::= { shutdownClassEntry 2  }
   
   
   shutdownClassType OBJECT-TYPE
      SYNTAX      OCTET STRING
      MAX-ACCESS  read-only
      STATUS      current
      DESCRIPTION "Returns the type of the MBean. "
      ::= { shutdownClassEntry 3  }
   
   
   shutdownClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { shutdownClassEntry 4  }
   
   
   shutdownClassArguments OBJECT-TYPE
      SYNTAX      OCTET STRING
      MAX-ACCESS  read-only
      STATUS      current
      DESCRIPTION "Arguments that a server uses to initialize a class.  Separate multiple arguments with a comma. For example:  first=MyFirstName,last=MyLastName "
      ::= { shutdownClassEntry 5  }
   
   
   shutdownClassName OBJECT-TYPE
      SYNTAX      OCTET STRING
      MAX-ACCESS  read-only
      STATUS      current
      DESCRIPTION "The user-specified name of this MBean instance.  This name is included as one of the key properties in the MBean's javax.management.ObjectName:  Name=user-specified-name "
      ::= { shutdownClassEntry 6  }
   
   
   shutdownClassClassName OBJECT-TYPE
      SYNTAX      OCTET STRING
      MAX-ACCESS  read-only
      STATUS      current
      DESCRIPTION "The fully qualified name of a class to load and run. The class must be on the server's classpath.  For example, mycompany.mypackage.myclass "
      ::= { shutdownClassEntry 7  }
   
   
   shutdownClassTags OBJECT-TYPE
      SYNTAX      OCTET STRING
      MAX-ACCESS  read-only
      STATUS      current
      DESCRIPTION "Return all tags on this Configuration MBean "
      ::= { shutdownClassEntry 8  }
   
   
   singleSignOnServicesTable OBJECT-TYPE
      SYNTAX      SEQUENCE OF SingleSignOnServicesEntry
      MAX-ACCESS  not-accessible
      STATUS      current
      DESCRIPTION "This MBean represents configuration for SAML 2.0-based local site Single Sign-On Services. "
      ::= { wls 1105  }
      
   
   singleSignOnServicesEntry OBJECT-TYPE
      SYNTAX      SingleSignOnServicesEntry
      MAX-ACCESS  not-accessible
      STATUS      current
      DESCRIPTION "Generated SNMP Table Entry."
      INDEX { singleSignOnServicesIndex}
      ::= { singleSignOnServicesTable 1 }
      
   SingleSignOnServicesEntry ::=
      SEQUENCE
      {
         singleSignOnServicesIndex OCTET STRING,
         singleSignOnServicesObjectName OCTET STRING,
         singleSignOnServicesArtifactMaxCacheSize Integer32,
         singleSignOnServicesIdentityProviderRedirectBindingEnabled OCTET STRING,
         singleSignOnServicesForceAuthn OCTET STRING,
         singleSignOnServicesIdentityProviderPreferredBinding OCTET STRING,
         singleSignOnServicesContactPersonGivenName OCTET STRING,
         singleSignOnServicesWantArtifactRequestsSigned OCTET STRING,
         singleSignOnServicesContactPersonTelephoneNumber OCTET STRING,
         singleSignOnServicesPassive OCTET STRING,
         singleSignOnServicesTransportLayerSecurityKeyAlias OCTET STRING,
         singleSignOnServicesSSOSigningKeyAlias OCTET STRING,
         singleSignOnServicesLoginReturnQueryParameter OCTET STRING,
         singleSignOnServicesAuthnRequestTimeout Integer32,
         singleSignOnServicesPOSTOneUseCheckEnabled OCTET STRING,
         singleSignOnServicesIdentityProviderArtifactBindingEnabled OCTET STRING,
         singleSignOnServicesWantTransportLayerSecurityClientAtn OCTET STRING,
         singleSignOnServicesIdentityProviderEnabled OCTET STRING,
         singleSignOnServicesLoginURL OCTET STRING,
         singleSignOnServicesArtifactTimeout Integer32,
         singleSignOnServicesContactPersonType OCTET STRING,
         singleSignOnServicesOrganizationName OCTET STRING,
         singleSignOnServicesDefaultURL OCTET STRING,
         singleSignOnServicesWantBasicAuthClientAuthentication OCTET STRING,
         singleSignOnServicesType OCTET STRING,
         singleSignOnServicesContactPersonEmailAddress OCTET STRING,
         singleSignOnServicesRecipientCheckEnabled OCTET STRING,
         singleSignOnServicesAuthnRequestMaxCacheSize Integer32,
         singleSignOnServicesReplicatedCacheEnabled OCTET STRING,
         singleSignOnServicesServiceProviderEnabled OCTET STRING,
         singleSignOnServicesName OCTET STRING,
         singleSignOnServicesSignAuthnRequests OCTET STRING,
         singleSignOnServicesContactPersonCompany OCTET STRING,
         singleSignOnServicesBasicAuthUsername OCTET STRING,
         singleSignOnServicesServiceProviderPOSTBindingEnabled OCTET STRING,
         singleSignOnServicesEntityID OCTET STRING,
         singleSignOnServicesPublishedSiteURL OCTET STRING,
         singleSignOnServicesOrganizationURL OCTET STRING,
         singleSignOnServicesServiceProviderArtifactBindingEnabled OCTET STRING,
         singleSignOnServicesWantAssertionsSigned OCTET STRING,
         singleSignOnServicesWantAuthnRequestsSigned OCTET STRING,
         singleSignOnServicesServiceProviderPreferredBinding OCTET STRING,
         singleSignOnServicesIdentityProviderPOSTBindingEnabled OCTET STRING,
         singleSignOnServicesContactPersonSurName OCTET STRING,
         singleSignOnServicesTags OCTET STRING,
         singleSignOnServicesAssertionEncryptionDecryptionKeyAlias OCTET STRING,
         singleSignOnServicesKeyEncryptionAlgorithm OCTET STRING,
         singleSignOnServicesDataEncryptionAlgorithm OCTET STRING,
         singleSignOnServicesMetadataEncryptionAlgorithms OCTET STRING,
         singleSignOnServicesAssertionEncryptionEnabled OCTET STRING,
         singleSignOnServicesAllowedTargetHosts OCTET STRING
      }
      
   
   singleSignOnServicesIndex OBJECT-TYPE
      SYNTAX      OCTET STRING
      MAX-ACCESS  not-accessible
      STATUS      current
      DESCRIPTION "Index column"
      ::= { singleSignOnServicesEntry 1  }
   
   
   singleSignOnServicesObjectName OBJECT-TYPE
      SYNTAX      OCTET STRING
      MAX-ACCESS  read-only
      STATUS      current
      DESCRIPTION "ObjectName column"
      ::= { singleSignOnServicesEntry 2  }
   
   
   singleSignOnServicesArtifactMaxCacheSize OBJECT-TYPE
      SYNTAX      Integer32
      MAX-ACCESS  read-only
      STATUS      current
      DESCRIPTION "The maximum size of the artifact cache.  This cache contains the artifacts issued by the local site that are awaiting referencing by a partner.  Specify '0' to indicate that the cache is unbounded. "
      ::= { singleSignOnServicesEntry 3  }
   
   
   singleSignOnServicesIdentityProviderRedirectBindingEnabled OBJECT-TYPE
      SYNTAX      OCTET STRING
      MAX-ACCESS  read-only
      STATUS      current
      DESCRIPTION "Specifies whether the Redirect binding is enabled for the Identity Provider. "
      ::= { singleSignOnServicesEntry 4  }
   
   
   singleSignOnServicesForceAuthn OBJECT-TYPE
      SYNTAX      OCTET STRING
      MAX-ACCESS  read-only
      STATUS      current
      DESCRIPTION "Specifies whether the Identity Provider must authenticate users directly and not use a previous security context. The default is false.   Note the following:  Setting ForceAuthn to true -- that is, enabling Force Authentication -- has no effect in WebLogic Server. SAML logout is not supported in WebLogic Server, so even if the user is already authenticated at the Identity Provider site and ForceAuthn is set to true, the user is not forced to authenticate again at the Identity Provider site. Setting both ForceAuthn and IsPassive to true -- that is, Force Authentication and Passive are enabled -- is an invalid configuration that causes WebLogic server to generate an exception and also causes the single sign-on session to fail.  "
      ::= { singleSignOnServicesEntry 5  }
   
   
   singleSignOnServicesIdentityProviderPreferredBinding OBJECT-TYPE
      SYNTAX      OCTET STRING
      MAX-ACCESS  read-only
      STATUS      current
      DESCRIPTION "Specifies the preferred binding type for endpoints of the Identity Provider services. Must be set to None, HTTP/POST, HTTP/Artifact, or HTTP/Redirect. "
      ::= { singleSignOnServicesEntry 6  }
   
   
   singleSignOnServicesContactPersonGivenName OBJECT-TYPE
      SYNTAX      OCTET STRING
      MAX-ACCESS  read-only
      STATUS      current
      DESCRIPTION "The contact person given (first) name. "
      ::= { singleSignOnServicesEntry 7  }
   
   
   singleSignOnServicesWantArtifactRequestsSigned OBJECT-TYPE
      SYNTAX      OCTET STRING
      MAX-ACCESS  read-only
      STATUS      current
      DESCRIPTION "Specifies whether incoming artifact requests must be signed.   This attribute can be set if the Artifact binding is enabled. "
      ::= { singleSignOnServicesEntry 8  }
   
   
   singleSignOnServicesContactPersonTelephoneNumber OBJECT-TYPE
      SYNTAX      OCTET STRING
      MAX-ACCESS  read-only
      STATUS      current
      DESCRIPTION "The contact person's telephone number. "
      ::= { singleSignOnServicesEntry 9  }
   
   
   singleSignOnServicesPassive OBJECT-TYPE
      SYNTAX      OCTET STRING
      MAX-ACCESS  read-only
      STATUS      current
      DESCRIPTION "Determines whether the Identity Provider and the user must not take control of the user interface from the requester and interact with the user in a noticeable fashion. The default setting is false.  The WebLogic Server SAML 2.0 services generate an exception if Passive (IsPassive) is enabled and the end user is not already authenticated at the Identity Provider site.  In this situation, web single sign-on fails. "
      ::= { singleSignOnServicesEntry 10  }
   
   
   singleSignOnServicesTransportLayerSecurityKeyAlias OBJECT-TYPE
      SYNTAX      OCTET STRING
      MAX-ACCESS  read-only
      STATUS      current
      DESCRIPTION "The string alias used to store and retrieve the server's private key, which is used to establish outgoing TLS/SSL connections.  If you do not specify an alias, the server's configured SSL private key alias from the server's SSL configuration is used for the TLS alias by default. "
      ::= { singleSignOnServicesEntry 11  }
   
   
   singleSignOnServicesSSOSigningKeyAlias OBJECT-TYPE
      SYNTAX      OCTET STRING
      MAX-ACCESS  read-only
      STATUS      current
      DESCRIPTION "The keystore alias for the key to be used when signing documents.  The key is used to generate signatures on all the outgoing documents, such as authentication requests and responses. If you do not specify an alias, the server's configured SSL private key alias from the server's SSL configuration is used by default. "
      ::= { singleSignOnServicesEntry 12  }
   
   
   singleSignOnServicesLoginReturnQueryParameter OBJECT-TYPE
      SYNTAX      OCTET STRING
      MAX-ACCESS  read-only
      STATUS      current
      DESCRIPTION "The name of the query parameter to be used for conveying the login-return URL to the login form web application. "
      ::= { singleSignOnServicesEntry 13  }
   
   
   singleSignOnServicesAuthnRequestTimeout OBJECT-TYPE
      SYNTAX      Integer32
      MAX-ACCESS  read-only
      STATUS      current
      DESCRIPTION "The maximum timeout (in seconds) of &lt;AuthnRequest&gt; documents stored in the local cache.  This cache stores documents issued by the local Service provider that are awaiting response from a partner Identity Provider. Documents that reach this maximum timeout duration are expired from the local cache even if no response is received from the Identity Provider.  If a response is subsequently returned by the Identity Provider, the cache behaves as if the &lt;AuthnRequest&gt; had never been generated. "
      ::= { singleSignOnServicesEntry 14  }
   
   
   singleSignOnServicesPOSTOneUseCheckEnabled OBJECT-TYPE
      SYNTAX      OCTET STRING
      MAX-ACCESS  read-only
      STATUS      current
      DESCRIPTION "Specifies whether the POST one-use check is enabled.  If set, the local site POST binding endpoints will store identifiers of all inbound documents to ensure that those documents are not presented more than once. "
      ::= { singleSignOnServicesEntry 15  }
   
   
   singleSignOnServicesIdentityProviderArtifactBindingEnabled OBJECT-TYPE
      SYNTAX      OCTET STRING
      MAX-ACCESS  read-only
      STATUS      current
      DESCRIPTION "Specifies whether the Artifact binding is enabled for the Identity Provider. "
      ::= { singleSignOnServicesEntry 16  }
   
   
   singleSignOnServicesWantTransportLayerSecurityClientAtn OBJECT-TYPE
      SYNTAX      OCTET STRING
      MAX-ACCESS  read-only
      STATUS      current
      DESCRIPTION "Specifies whether TLS/SSL client authentication is required.  If enabled, callers to TLS/SSL bindings of the local site must specify client authentication (two-way SSL), and the identity specified must validate against the TLS certificate of the binding client partner. "
      ::= { singleSignOnServicesEntry 17  }
   
   
   singleSignOnServicesIdentityProviderEnabled OBJECT-TYPE
      SYNTAX      OCTET STRING
      MAX-ACCESS  read-only
      STATUS      current
      DESCRIPTION "Specifies whether the local site is enabled for the Identity Provider role. "
      ::= { singleSignOnServicesEntry 18  }
   
   
   singleSignOnServicesLoginURL OBJECT-TYPE
      SYNTAX      OCTET STRING
      MAX-ACCESS  read-only
      STATUS      current
      DESCRIPTION "The URL of the login form web application to which unauthenticated requests are directed.  By default, the login URL is /saml2/idp/login using Basic authentication. Typically you specify this URL if you are using a custom login web application. "
      ::= { singleSignOnServicesEntry 19  }
   
   
   singleSignOnServicesArtifactTimeout OBJECT-TYPE
      SYNTAX      Integer32
      MAX-ACCESS  read-only
      STATUS      current
      DESCRIPTION "The maximum timeout (in seconds) of artifacts stored in the local cache.  This cache stores artifacts issued by the local site that are awaiting referencing by a partner. Artifacts that reach this maximum timeout duration are expired in the local cache even if no reference request has been received from the partner.  If a reference request is subsequently received from the partner, the cache behaves as if the artifact had never been generated. "
      ::= { singleSignOnServicesEntry 20  }
   
   
   singleSignOnServicesContactPersonType OBJECT-TYPE
      SYNTAX      OCTET STRING
      MAX-ACCESS  read-only
      STATUS      current
      DESCRIPTION "The contact person type. "
      ::= { singleSignOnServicesEntry 21  }
   
   
   singleSignOnServicesOrganizationName OBJECT-TYPE
      SYNTAX      OCTET STRING
      MAX-ACCESS  read-only
      STATUS      current
      DESCRIPTION "The organization name.  This string specifies the name of the organization to which a user may refer for obtaining additional information about the local site. "
      ::= { singleSignOnServicesEntry 22  }
   
   
   singleSignOnServicesDefaultURL OBJECT-TYPE
      SYNTAX      OCTET STRING
      MAX-ACCESS  read-only
      STATUS      current
      DESCRIPTION "The Service Provider's default URL.  When an unsolicited SSO response arrives at the Service Provider without an accompanying target URL, the user (if authenticated) is redirected to this default URL. "
      ::= { singleSignOnServicesEntry 23  }
   
   
   singleSignOnServicesWantBasicAuthClientAuthentication OBJECT-TYPE
      SYNTAX      OCTET STRING
      MAX-ACCESS  read-only
      STATUS      current
      DESCRIPTION "Specifies whether Basic Authentication client authentication is required.  If enabled, callers to HTTPS bindings of the local site must specify a Basic authentication header, and the username and password must be validated against the Basic authentication values of the binding client partner. "
      ::= { singleSignOnServicesEntry 24  }
   
   
   singleSignOnServicesType OBJECT-TYPE
      SYNTAX      OCTET STRING
      MAX-ACCESS  read-only
      STATUS      current
      DESCRIPTION "Returns the type of the MBean. "
      ::= { singleSignOnServicesEntry 25  }
   
   
   singleSignOnServicesContactPersonEmailAddress OBJECT-TYPE
      SYNTAX      OCTET STRING
      MAX-ACCESS  read-only
      STATUS      current
      DESCRIPTION "The contact person's e-mail address. "
      ::= { singleSignOnServicesEntry 26  }
   
   
   singleSignOnServicesRecipientCheckEnabled OBJECT-TYPE
      SYNTAX      OCTET STRING
      MAX-ACCESS  read-only
      STATUS      current
      DESCRIPTION "Specifies whether the recipient/destination check is enabled. When true, the recipient of the SAML Request/Response must match the URL in the HTTP Request. "
      ::= { singleSignOnServicesEntry 27  }
   
   
   singleSignOnServicesAuthnRequestMaxCacheSize OBJECT-TYPE
      SYNTAX      Integer32
      MAX-ACCESS  read-only
      STATUS      current
      DESCRIPTION "The maximum size of the authentication request cache.  This cache stores documents issued by the local Service Provider that are awaiting response from a partner Identity Provider.    Specify '0' to indicate that the cache is unbounded. "
      ::= { singleSignOnServicesEntry 29  }
   
   
   singleSignOnServicesReplicatedCacheEnabled OBJECT-TYPE
      SYNTAX      OCTET STRING
      MAX-ACCESS  read-only
      STATUS      current
      DESCRIPTION "Specifies whether the persistent cache (LDAP or RDBMS) is used for storing SAML 2.0 artifacts and authentication requests.  RDBMS is required by the SAML 2.0 security providers in production environments.  Use LDAP only in development environments.  If this is not set, artifacts and requests are saved in memory.  If you are configuring SAML 2.0 services for two or more WebLogic Server instances in a domain, you must enable the replicated cache individually on each server.  In addition, if you are configuring SAML 2.0 services in a cluster, each Managed Server must also be configured individually. "
      ::= { singleSignOnServicesEntry 30  }
   
   
   singleSignOnServicesServiceProviderEnabled OBJECT-TYPE
      SYNTAX      OCTET STRING
      MAX-ACCESS  read-only
      STATUS      current
      DESCRIPTION "Specifies whether the local site is enabled for the Service Provider role.  This attribute must be enabled in order to publish the metadata file. "
      ::= { singleSignOnServicesEntry 31  }
   
   
   singleSignOnServicesName OBJECT-TYPE
      SYNTAX      OCTET STRING
      MAX-ACCESS  read-only
      STATUS      current
      DESCRIPTION "The user-specified name of this MBean instance.  This name is included as one of the key properties in the MBean's javax.management.ObjectName:  Name=user-specified-name "
      ::= { singleSignOnServicesEntry 32  }
   
   
   singleSignOnServicesSignAuthnRequests OBJECT-TYPE
      SYNTAX      OCTET STRING
      MAX-ACCESS  read-only
      STATUS      current
      DESCRIPTION "Specifies whether authentication requests must be signed.  If set, all outgoing authentication requests are signed. "
      ::= { singleSignOnServicesEntry 33  }
   
   
   singleSignOnServicesContactPersonCompany OBJECT-TYPE
      SYNTAX      OCTET STRING
      MAX-ACCESS  read-only
      STATUS      current
      DESCRIPTION "The contact person's company name. "
      ::= { singleSignOnServicesEntry 34  }
   
   
   singleSignOnServicesBasicAuthUsername OBJECT-TYPE
      SYNTAX      OCTET STRING
      MAX-ACCESS  read-only
      STATUS      current
      DESCRIPTION "The username that is used to assign Basic authentication credentials to outgoing HTTPS connections. "
      ::= { singleSignOnServicesEntry 35  }
   
   
   singleSignOnServicesServiceProviderPOSTBindingEnabled OBJECT-TYPE
      SYNTAX      OCTET STRING
      MAX-ACCESS  read-only
      STATUS      current
      DESCRIPTION "Specifies whether the POST binding is enabled for the Service Provider. "
      ::= { singleSignOnServicesEntry 36  }
   
   
   singleSignOnServicesEntityID OBJECT-TYPE
      SYNTAX      OCTET STRING
      MAX-ACCESS  read-only
      STATUS      current
      DESCRIPTION "The string that uniquely identifies the local site. "
      ::= { singleSignOnServicesEntry 37  }
   
   
   singleSignOnServicesPublishedSiteURL OBJECT-TYPE
      SYNTAX      OCTET STRING
      MAX-ACCESS  read-only
      STATUS      current
      DESCRIPTION "The published site URL.  When publishing SAML 2.0 metadata, this URL is used as a base URL to construct endpoint URLs for the various SAML 2.0 services.  The published site URL is also used during request processing to generate and/or parse various URLs.  The hostname and port portion of the URL should be the hostname and port at which the server is visible externally; this may not be the same as the hostname and port by which the server is known locally. If you are configuring SAML 2.0 services in a cluster, the hostname and port may correspond to the load balancer or proxy server that distributes client requests to servers in the cluster.  The remainder of the URL should be a single path component corresponding to the application context at which the SAML 2.0 services application is deployed (typically /saml2). "
      ::= { singleSignOnServicesEntry 38  }
   
   
   singleSignOnServicesOrganizationURL OBJECT-TYPE
      SYNTAX      OCTET STRING
      MAX-ACCESS  read-only
      STATUS      current
      DESCRIPTION "The organization URL.  This string specifies a location to which a user may refer for information about the local site. This string is not used by SAML 2.0 services for the actual handling or processing of messages. "
      ::= { singleSignOnServicesEntry 39  }
   
   
   singleSignOnServicesServiceProviderArtifactBindingEnabled OBJECT-TYPE
      SYNTAX      OCTET STRING
      MAX-ACCESS  read-only
      STATUS      current
      DESCRIPTION "Specifies whether the Artifact binding is enabled for the Service Provider. "
      ::= { singleSignOnServicesEntry 40  }
   
   
   singleSignOnServicesWantAssertionsSigned OBJECT-TYPE
      SYNTAX      OCTET STRING
      MAX-ACCESS  read-only
      STATUS      current
      DESCRIPTION "Specifies whether incoming SAML 2.0 assertions must be signed. "
      ::= { singleSignOnServicesEntry 41  }
   
   
   singleSignOnServicesWantAuthnRequestsSigned OBJECT-TYPE
      SYNTAX      OCTET STRING
      MAX-ACCESS  read-only
      STATUS      current
      DESCRIPTION "Specifies whether incoming authentication requests must be signed. If set, authentication requests that are not signed are not accepted. "
      ::= { singleSignOnServicesEntry 42  }
   
   
   singleSignOnServicesServiceProviderPreferredBinding OBJECT-TYPE
      SYNTAX      OCTET STRING
      MAX-ACCESS  read-only
      STATUS      current
      DESCRIPTION "Specifies the preferred binding type for endpoints of Service Provider services. Must be set to 'None', 'POST', or 'Artifact'. "
      ::= { singleSignOnServicesEntry 43  }
   
   
   singleSignOnServicesIdentityProviderPOSTBindingEnabled OBJECT-TYPE
      SYNTAX      OCTET STRING
      MAX-ACCESS  read-only
      STATUS      current
      DESCRIPTION "Specifies whether the POST binding is enabled for the Identity Provider. "
      ::= { singleSignOnServicesEntry 44  }
   
   
   singleSignOnServicesContactPersonSurName OBJECT-TYPE
      SYNTAX      OCTET STRING
      MAX-ACCESS  read-only
      STATUS      current
      DESCRIPTION "The contact person surname (last name). "
      ::= { singleSignOnServicesEntry 45  }
   
   
   singleSignOnServicesTags OBJECT-TYPE
      SYNTAX      OCTET STRING
      MAX-ACCESS  read-only
      STATUS      current
      DESCRIPTION "Return all tags on this Configuration MBean "
      ::= { singleSignOnServicesEntry 46  }
   
   
   singleSignOnServicesAssertionEncryptionDecryptionKeyAlias OBJECT-TYPE
      SYNTAX      OCTET STRING
      MAX-ACCESS  read-only
      STATUS      current
      DESCRIPTION "The keystore alias for the certificate and private key to be used to encrypt and decrypt SAML Assertions.   The certificate is published in the SP metadata, which will be used by an external SP to encrypt SAML assertions.  The private key is used to decrypt assertions. If the alias is not specified, the server's configured SSL identity alias is used by default. "
      ::= { singleSignOnServicesEntry 47  }
   
   
   singleSignOnServicesKeyEncryptionAlgorithm OBJECT-TYPE
      SYNTAX      OCTET STRING
      MAX-ACCESS  read-only
      STATUS      current
      DESCRIPTION "Get the preferred key encryption algorithm for SAML assertion encryption. This algorithm is used if it is found in the Service Provider's metadata or if the Service Partner's metadata does not include any key encryption algorithm. "
      ::= { singleSignOnServicesEntry 48  }
   
   
   singleSignOnServicesDataEncryptionAlgorithm OBJECT-TYPE
      SYNTAX      OCTET STRING
      MAX-ACCESS  read-only
      STATUS      current
      DESCRIPTION "Get the preferred data encryption algorithm for SAML assertion encryption. This algorithm is used if it is found in the Service Provider's metadata or if the Service Partner's metadata does not include any data encryption algorithm. "
      ::= { singleSignOnServicesEntry 49  }
   
   
   singleSignOnServicesMetadataEncryptionAlgorithms OBJECT-TYPE
      SYNTAX      OCTET STRING
      MAX-ACCESS  read-only
      STATUS      current
      DESCRIPTION " "
      ::= { singleSignOnServicesEntry 50  }
   
   
   singleSignOnServicesAssertionEncryptionEnabled OBJECT-TYPE
      SYNTAX      OCTET STRING
      MAX-ACCESS  read-only
      STATUS      current
      DESCRIPTION "Get assertion encryption enabled flag "
      ::= { singleSignOnServicesEntry 51  }
   
   
   singleSignOnServicesAllowedTargetHosts OBJECT-TYPE
      SYNTAX      OCTET STRING
      MAX-ACCESS  read-only
      STATUS      current
      DESCRIPTION "List of hosts to compare against the host in the SAML SP target redirect URL. When the list is empty, the target redirect URL will not be checked. "
      ::= { singleSignOnServicesEntry 52  }
   
   
   singletonServiceAppScopedTable OBJECT-TYPE
      SYNTAX      SEQUENCE OF SingletonServiceAppScopedEntry
      MAX-ACCESS  not-accessible
      STATUS      current
      DESCRIPTION "A service that will be automatically maintained as a Singleton in a cluster. There will always be exactly one instance of it active at any given time. "
      ::= { wls 1110  }
      
   
   singletonServiceAppScopedEntry OBJECT-TYPE
      SYNTAX      SingletonServiceAppScopedEntry
      MAX-ACCESS  not-accessible
      STATUS      current
      DESCRIPTION "Generated SNMP Table Entry."
      INDEX { singletonServiceAppScopedIndex}
      ::= { singletonServiceAppScopedTable 1 }
      
   SingletonServiceAppScopedEntry ::=
      SEQUENCE
      {
         singletonServiceAppScopedIndex OCTET STRING,
         singletonServiceAppScopedObjectName OCTET STRING,
         singletonServiceAppScopedType OCTET STRING,
         singletonServiceAppScopedCompatibilityName OCTET STRING,
         singletonServiceAppScopedMillisToSleepBetweenAttempts Integer32,
         singletonServiceAppScopedModuleType OCTET STRING,
         singletonServiceAppScopedName OCTET STRING,
         singletonServiceAppScopedAdditionalMigrationAttempts Integer32,
         singletonServiceAppScopedClassName OCTET STRING,
         singletonServiceAppScopedUntargeted OCTET STRING,
         singletonServiceAppScopedTags OCTET STRING
      }
      
   
   singletonServiceAppScopedIndex OBJECT-TYPE
      SYNTAX      OCTET STRING
      MAX-ACCESS  not-accessible
      STATUS      current
      DESCRIPTION "Index column"
      ::= { singletonServiceAppScopedEntry 1  }
   
   
   singletonServiceAppScopedObjectName OBJECT-TYPE
      SYNTAX      OCTET STRING
      MAX-ACCESS  read-only
      STATUS      current
      DESCRIPTION "ObjectName column"
      ::= { singletonServiceAppScopedEntry 2  }
   
   
   singletonServiceAppScopedType OBJECT-TYPE
      SYNTAX      OCTET STRING
      MAX-ACCESS  read-only
      STATUS      current
      DESCRIPTION "Returns the type of the MBean. "
      ::= { singletonServiceAppScopedEntry 3  }
   
   
   singletonServiceAppScopedCompatibilityName OBJECT-TYPE
      SYNTAX      OCTET STRING
      MAX-ACCESS  read-only
      STATUS      current
      DESCRIPTION " This is only set for beans created as a result of conversion from an 8.1 application configured using ApplicationMBean and ComponentMBean.  Standalone modules in 8.1 have both an ApplicationMBean name and ComponentMBean name. This attribute stores the name of the latter, to be used when the server creates the transient ComponentMBean for backward compatibility. "
      ::= { singletonServiceAppScopedEntry 4  }
   
   
   singletonServiceAppScopedMillisToSleepBetweenAttempts OBJECT-TYPE
      SYNTAX      Integer32
      MAX-ACCESS  read-only
      STATUS      current
      DESCRIPTION "Controls how long of a pause there should be between the migration attempts described in getAdditionalMigrationAttempts(). Note that this delay only happens when the service has failed to come up on every server. It does not cause any sort of delay between attempts to migrate otherwise. "
      ::= { singletonServiceAppScopedEntry 5  }
   
   
   singletonServiceAppScopedModuleType OBJECT-TYPE
      SYNTAX      OCTET STRING
      MAX-ACCESS  read-only
      STATUS      current
      DESCRIPTION "The values match those defined by jsr88. This attribute may move to another MBean. "
      ::= { singletonServiceAppScopedEntry 6  }
   
   
   singletonServiceAppScopedName OBJECT-TYPE
      SYNTAX      OCTET STRING
      MAX-ACCESS  read-only
      STATUS      current
      DESCRIPTION "Unique identifier for this bean instance. It is used by the application container to match the module in the application package to the targeting information in the configuration.  For modules within an EAR, the name should be the URI of the module as defined in the META-INF/application.xml deployment descriptor. There is an exception to this for web applications. See below. For web modules in an EAR, the name should always equal the context root of that webapp, because the URI is not always unique "
      ::= { singletonServiceAppScopedEntry 7  }
   
   
   singletonServiceAppScopedAdditionalMigrationAttempts OBJECT-TYPE
      SYNTAX      Integer32
      MAX-ACCESS  read-only
      STATUS      current
      DESCRIPTION "A migratable service could fail to come up on every possible configured server. This attribute controls how many further attempts, after the service has failed on every server at least once, should be tried. Note that each attempt specified here indicates another full circuit of migrations amongst all the configured servers. So for a 3-server cluster, and a value of 2, a total of 4 additional migrations will be attempted. (the original server is never a valid destination) "
      ::= { singletonServiceAppScopedEntry 8  }
   
   
   singletonServiceAppScopedClassName OBJECT-TYPE
      SYNTAX      OCTET STRING
      MAX-ACCESS  read-only
      STATUS      current
      DESCRIPTION "The fully qualified name of a class to load and run. The class must be on the server's classpath.  For example, mycompany.mypackage.myclass "
      ::= { singletonServiceAppScopedEntry 9  }
   
   
   singletonServiceAppScopedUntargeted OBJECT-TYPE
      SYNTAX      OCTET STRING
      MAX-ACCESS  read-only
      STATUS      current
      DESCRIPTION "Only relevant for deployments in resource group templates. Sub-deployments cannot have arbitrary targets if they are part of a deployment from resource group template. The sub-deployments, in such cases, may only be targeted to the virtual host of referring partition or stay untargeted. This flag, when specified with true, indicates that the sub-deployment must not be deployed in the referring partition "
      ::= { singletonServiceAppScopedEntry 10  }
   
   
   singletonServiceAppScopedTags OBJECT-TYPE
      SYNTAX      OCTET STRING
      MAX-ACCESS  read-only
      STATUS      current
      DESCRIPTION "Return all tags on this Configuration MBean "
      ::= { singletonServiceAppScopedEntry 11  }
   
   
   singletonServiceTable OBJECT-TYPE
      SYNTAX      SEQUENCE OF SingletonServiceEntry
      MAX-ACCESS  not-accessible
      STATUS      current
      DESCRIPTION "A service that will be automatically maintained as a Singleton in a cluster. There will always be exactly one instance of it active at any given time. "
      ::= { wls 1115  }
      
   
   singletonServiceEntry OBJECT-TYPE
      SYNTAX      SingletonServiceEntry
      MAX-ACCESS  not-accessible
      STATUS      current
      DESCRIPTION "Generated SNMP Table Entry."
      INDEX { singletonServiceIndex}
      ::= { singletonServiceTable 1 }
      
   SingletonServiceEntry ::=
      SEQUENCE
      {
         singletonServiceIndex OCTET STRING,
         singletonServiceObjectName OCTET STRING,
         singletonServiceType OCTET STRING,
         singletonServiceMillisToSleepBetweenAttempts Integer32,
         singletonServiceName OCTET STRING,
         singletonServiceAdditionalMigrationAttempts Integer32,
         singletonServiceClassName OCTET STRING,
         singletonServiceTags OCTET STRING
      }
      
   
   singletonServiceIndex OBJECT-TYPE
      SYNTAX      OCTET STRING
      MAX-ACCESS  not-accessible
      STATUS      current
      DESCRIPTION "Index column"
      ::= { singletonServiceEntry 1  }
   
   
   singletonServiceObjectName OBJECT-TYPE
      SYNTAX      OCTET STRING
      MAX-ACCESS  read-only
      STATUS      current
      DESCRIPTION "ObjectName column"
      ::= { singletonServiceEntry 2  }
   
   
   singletonServiceType OBJECT-TYPE
      SYNTAX      OCTET STRING
      MAX-ACCESS  read-only
      STATUS      current
      DESCRIPTION "Returns the type of the MBean. "
      ::= { singletonServiceEntry 3  }
   
   
   singletonServiceMillisToSleepBetweenAttempts OBJECT-TYPE
      SYNTAX      Integer32
      MAX-ACCESS  read-only
      STATUS      current
      DESCRIPTION "Controls how long of a pause there should be between the migration attempts described in getAdditionalMigrationAttempts(). Note that this delay only happens when the service has failed to come up on every server. It does not cause any sort of delay between attempts to migrate otherwise. "
      ::= { singletonServiceEntry 4  }
   
   
   singletonServiceName OBJECT-TYPE
      SYNTAX      OCTET STRING
      MAX-ACCESS  read-only
      STATUS      current
      DESCRIPTION "The user-specified name of this MBean instance.  This name is included as one of the key properties in the MBean's javax.management.ObjectName:  Name=user-specified-name "
      ::= { singletonServiceEntry 5  }
   
   
   singletonServiceAdditionalMigrationAttempts OBJECT-TYPE
      SYNTAX      Integer32
      MAX-ACCESS  read-only
      STATUS      current
      DESCRIPTION "A migratable service could fail to come up on every possible configured server. This attribute controls how many further attempts, after the service has failed on every server at least once, should be tried. Note that each attempt specified here indicates another full circuit of migrations amongst all the configured servers. So for a 3-server cluster, and a value of 2, a total of 4 additional migrations will be attempted. (the original server is never a valid destination) "
      ::= { singletonServiceEntry 6  }
   
   
   singletonServiceClassName OBJECT-TYPE
      SYNTAX      OCTET STRING
      MAX-ACCESS  read-only
      STATUS      current
      DESCRIPTION "The fully qualified name of a class to load and run. The class must be on the server's classpath.  For example, mycompany.mypackage.myclass "
      ::= { singletonServiceEntry 7  }
   
   
   singletonServiceTags OBJECT-TYPE
      SYNTAX      OCTET STRING
      MAX-ACCESS  read-only
      STATUS      current
      DESCRIPTION "Return all tags on this Configuration MBean "
      ::= { singletonServiceEntry 8  }
   
   
   unixMachineTable OBJECT-TYPE
      SYNTAX      SEQUENCE OF UnixMachineEntry
      MAX-ACCESS  not-accessible
      STATUS      current
      DESCRIPTION "This bean represents a machine that is running the UNIX operating system. It extends MachineMBean with properties specific to the UNIX platform. "
      ::= { wls 1125  }
      
   
   unixMachineEntry OBJECT-TYPE
      SYNTAX      UnixMachineEntry
      MAX-ACCESS  not-accessible
      STATUS      current
      DESCRIPTION "Generated SNMP Table Entry."
      INDEX { unixMachineIndex}
      ::= { unixMachineTable 1 }
      
   UnixMachineEntry ::=
      SEQUENCE
      {
         unixMachineIndex     OCTET STRING,
         unixMachineObjectName OCTET STRING,
         unixMachineType      OCTET STRING,
         unixMachinePostBindUID OCTET STRING,
         unixMachinePostBindUIDEnabled OCTET STRING,
         unixMachinePostBindGID OCTET STRING,
         unixMachinePostBindGIDEnabled OCTET STRING,
         unixMachineName      OCTET STRING,
         unixMachineAddresses OCTET STRING,
         unixMachineTags      OCTET STRING
      }
      
   
   unixMachineIndex OBJECT-TYPE
      SYNTAX      OCTET STRING
      MAX-ACCESS  not-accessible
      STATUS      current
      DESCRIPTION "Index column"
      ::= { unixMachineEntry 1  }
   
   
   unixMachineObjectName OBJECT-TYPE
      SYNTAX      OCTET STRING
      MAX-ACCESS  read-only
      STATUS      current
      DESCRIPTION "ObjectName column"
      ::= { unixMachineEntry 2  }
   
   
   unixMachineType OBJECT-TYPE
      SYNTAX      OCTET STRING
      MAX-ACCESS  read-only
      STATUS      current
      DESCRIPTION "Returns the type of the MBean. "
      ::= { unixMachineEntry 3  }
   
   
   unixMachinePostBindUID OBJECT-TYPE
      SYNTAX      OCTET STRING
      MAX-ACCESS  read-only
      STATUS      current
      DESCRIPTION "The UNIX user ID (UID) that a server running on this machine will run under after it has carried out all privileged startup actions. Otherwise, the server will continue to run under the account under which it was started.(Requires that you enable Post-Bind UID.) "
      ::= { unixMachineEntry 4  }
   
   
   unixMachinePostBindUIDEnabled OBJECT-TYPE
      SYNTAX      OCTET STRING
      MAX-ACCESS  read-only
      STATUS      current
      DESCRIPTION "Specifies whether a server running on this machine binds to a UNIX User ID (UID) after it has carried out all privileged startup actions. "
      ::= { unixMachineEntry 5  }
   
   
   unixMachinePostBindGID OBJECT-TYPE
      SYNTAX      OCTET STRING
      MAX-ACCESS  read-only
      STATUS      current
      DESCRIPTION "The UNIX group ID (GID) that a server running on this machine will run under after it has carried out all privileged startup actions. Otherwise, the server will continue to run under the group under which it was started.(Requires that you enable Post-Bind GID.) "
      ::= { unixMachineEntry 6  }
   
   
   unixMachinePostBindGIDEnabled OBJECT-TYPE
      SYNTAX      OCTET STRING
      MAX-ACCESS  read-only
      STATUS      current
      DESCRIPTION "Specifies whether a server running on this machine binds to a UNIX Group ID (GID) after it has carried out all privileged startup actions. "
      ::= { unixMachineEntry 7  }
   
   
   unixMachineName OBJECT-TYPE
      SYNTAX      OCTET STRING
      MAX-ACCESS  read-only
      STATUS      current
      DESCRIPTION "The user-specified name of this MBean instance.  This name is included as one of the key properties in the MBean's javax.management.ObjectName:  Name=user-specified-name "
      ::= { unixMachineEntry 8  }
   
   
   unixMachineAddresses OBJECT-TYPE
      SYNTAX      OCTET STRING
      MAX-ACCESS  read-only
      STATUS      current
      DESCRIPTION "The addresses by which this machine is known. May be either host names or literal IP addresses. "
      ::= { unixMachineEntry 9  }
   
   
   unixMachineTags OBJECT-TYPE
      SYNTAX      OCTET STRING
      MAX-ACCESS  read-only
      STATUS      current
      DESCRIPTION "Return all tags on this Configuration MBean "
      ::= { unixMachineEntry 10  }
   
   
   virtualDestinationTable OBJECT-TYPE
      SYNTAX      SEQUENCE OF VirtualDestinationEntry
      MAX-ACCESS  not-accessible
      STATUS      current
      DESCRIPTION "This class represents a virtual destination. In 7.0 JMS has distributed destination, which is a form of the virtual destination. "
      ::= { wls 1130  }
      
   
   virtualDestinationEntry OBJECT-TYPE
      SYNTAX      VirtualDestinationEntry
      MAX-ACCESS  not-accessible
      STATUS      current
      DESCRIPTION "Generated SNMP Table Entry."
      INDEX { virtualDestinationIndex}
      ::= { virtualDestinationTable 1 }
      
   VirtualDestinationEntry ::=
      SEQUENCE
      {
         virtualDestinationIndex OCTET STRING,
         virtualDestinationObjectName OCTET STRING,
         virtualDestinationType OCTET STRING,
         virtualDestinationDeploymentOrder Integer32,
         virtualDestinationJNDIName OCTET STRING,
         virtualDestinationName OCTET STRING,
         virtualDestinationTags OCTET STRING
      }
      
   
   virtualDestinationIndex OBJECT-TYPE
      SYNTAX      OCTET STRING
      MAX-ACCESS  not-accessible
      STATUS      current
      DESCRIPTION "Index column"
      ::= { virtualDestinationEntry 1  }
   
   
   virtualDestinationObjectName OBJECT-TYPE
      SYNTAX      OCTET STRING
      MAX-ACCESS  read-only
      STATUS      current
      DESCRIPTION "ObjectName column"
      ::= { virtualDestinationEntry 2  }
   
   
   virtualDestinationType OBJECT-TYPE
      SYNTAX      OCTET STRING
      MAX-ACCESS  read-only
      STATUS      current
      DESCRIPTION "Returns the type of the MBean. "
      ::= { virtualDestinationEntry 3  }
   
   
   virtualDestinationDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { virtualDestinationEntry 4  }
   
   
   virtualDestinationJNDIName OBJECT-TYPE
      SYNTAX      OCTET STRING
      MAX-ACCESS  read-only
      STATUS      current
      DESCRIPTION "The JNDI name used to look up a virtual destination within the JNDI namespace. Applications can use the JNDI name to look up the virtual destination. If not specified, then the destination is not bound into the JNDI namespace. "
      ::= { virtualDestinationEntry 5  }
   
   
   virtualDestinationName OBJECT-TYPE
      SYNTAX      OCTET STRING
      MAX-ACCESS  read-only
      STATUS      current
      DESCRIPTION "The user-specified name of this MBean instance.  This name is included as one of the key properties in the MBean's javax.management.ObjectName:  Name=user-specified-name "
      ::= { virtualDestinationEntry 6  }
   
   
   virtualDestinationTags OBJECT-TYPE
      SYNTAX      OCTET STRING
      MAX-ACCESS  read-only
      STATUS      current
      DESCRIPTION "Return all tags on this Configuration MBean "
      ::= { virtualDestinationEntry 7  }
   
   
   wldfDataRetirementByAgeTable OBJECT-TYPE
      SYNTAX      SEQUENCE OF WldfDataRetirementByAgeEntry
      MAX-ACCESS  not-accessible
      STATUS      current
      DESCRIPTION "This MBean specifies how data retirement for a WLDF archive will be performed based on the age of records in WLDF archives.  "
      ::= { wls 1135  }
      
   
   wldfDataRetirementByAgeEntry OBJECT-TYPE
      SYNTAX      WldfDataRetirementByAgeEntry
      MAX-ACCESS  not-accessible
      STATUS      current
      DESCRIPTION "Generated SNMP Table Entry."
      INDEX { wldfDataRetirementByAgeIndex}
      ::= { wldfDataRetirementByAgeTable 1 }
      
   WldfDataRetirementByAgeEntry ::=
      SEQUENCE
      {
         wldfDataRetirementByAgeIndex OCTET STRING,
         wldfDataRetirementByAgeObjectName OCTET STRING,
         wldfDataRetirementByAgeType OCTET STRING,
         wldfDataRetirementByAgeRetirementTime Integer32,
         wldfDataRetirementByAgeRetirementPeriod Integer32,
         wldfDataRetirementByAgeRetirementAge Integer32,
         wldfDataRetirementByAgeEnabled OCTET STRING,
         wldfDataRetirementByAgeArchiveName OCTET STRING,
         wldfDataRetirementByAgeName OCTET STRING,
         wldfDataRetirementByAgeTags OCTET STRING
      }
      
   
   wldfDataRetirementByAgeIndex OBJECT-TYPE
      SYNTAX      OCTET STRING
      MAX-ACCESS  not-accessible
      STATUS      current
      DESCRIPTION "Index column"
      ::= { wldfDataRetirementByAgeEntry 1  }
   
   
   wldfDataRetirementByAgeObjectName OBJECT-TYPE
      SYNTAX      OCTET STRING
      MAX-ACCESS  read-only
      STATUS      current
      DESCRIPTION "ObjectName column"
      ::= { wldfDataRetirementByAgeEntry 2  }
   
   
   wldfDataRetirementByAgeType OBJECT-TYPE
      SYNTAX      OCTET STRING
      MAX-ACCESS  read-only
      STATUS      current
      DESCRIPTION "Returns the type of the MBean. "
      ::= { wldfDataRetirementByAgeEntry 3  }
   
   
   wldfDataRetirementByAgeRetirementTime OBJECT-TYPE
      SYNTAX      Integer32
      MAX-ACCESS  read-only
      STATUS      current
      DESCRIPTION "This attribute specifies the hour of day at which the data retirement task will first run during the day. "
      ::= { wldfDataRetirementByAgeEntry 4  }
   
   
   wldfDataRetirementByAgeRetirementPeriod OBJECT-TYPE
      SYNTAX      Integer32
      MAX-ACCESS  read-only
      STATUS      current
      DESCRIPTION "This attribute specifies the period in hours at which the data retirement task will be periodically performed for the archive during the day after it is first executed. The value of this attribute must be positive  "
      ::= { wldfDataRetirementByAgeEntry 5  }
   
   
   wldfDataRetirementByAgeRetirementAge OBJECT-TYPE
      SYNTAX      Integer32
      MAX-ACCESS  read-only
      STATUS      current
      DESCRIPTION "Retirement age for records in hours. Older records will be eligible for deletion.  "
      ::= { wldfDataRetirementByAgeEntry 6  }
   
   
   wldfDataRetirementByAgeEnabled OBJECT-TYPE
      SYNTAX      OCTET STRING
      MAX-ACCESS  read-only
      STATUS      current
      DESCRIPTION "Enable data retirement "
      ::= { wldfDataRetirementByAgeEntry 7  }
   
   
   wldfDataRetirementByAgeArchiveName OBJECT-TYPE
      SYNTAX      OCTET STRING
      MAX-ACCESS  read-only
      STATUS      current
      DESCRIPTION "Name of the archive for which data retirement is configured "
      ::= { wldfDataRetirementByAgeEntry 8  }
   
   
   wldfDataRetirementByAgeName OBJECT-TYPE
      SYNTAX      OCTET STRING
      MAX-ACCESS  read-only
      STATUS      current
      DESCRIPTION "The user-specified name of this MBean instance.  This name is included as one of the key properties in the MBean's javax.management.ObjectName:  Name=user-specified-name "
      ::= { wldfDataRetirementByAgeEntry 9  }
   
   
   wldfDataRetirementByAgeTags OBJECT-TYPE
      SYNTAX      OCTET STRING
      MAX-ACCESS  read-only
      STATUS      current
      DESCRIPTION "Return all tags on this Configuration MBean "
      ::= { wldfDataRetirementByAgeEntry 10  }
   
   
   wldfServerDiagnosticTable OBJECT-TYPE
      SYNTAX      SEQUENCE OF WldfServerDiagnosticEntry
      MAX-ACCESS  not-accessible
      STATUS      current
      DESCRIPTION "Use this interface to configure the WebLogic Diagnostic Framework (WLDF) components that are defined for each WebLogic Server instance. "
      ::= { wls 1140  }
      
   
   wldfServerDiagnosticEntry OBJECT-TYPE
      SYNTAX      WldfServerDiagnosticEntry
      MAX-ACCESS  not-accessible
      STATUS      current
      DESCRIPTION "Generated SNMP Table Entry."
      INDEX { wldfServerDiagnosticIndex}
      ::= { wldfServerDiagnosticTable 1 }
      
   WldfServerDiagnosticEntry ::=
      SEQUENCE
      {
         wldfServerDiagnosticIndex OCTET STRING,
         wldfServerDiagnosticObjectName OCTET STRING,
         wldfServerDiagnosticType OCTET STRING,
         wldfServerDiagnosticSynchronousEventPersistenceEnabled OCTET STRING,
         wldfServerDiagnosticEventPersistenceInterval Counter64,
         wldfServerDiagnosticPreferredStoreSizeLimit Integer32,
         wldfServerDiagnosticImageTimeout Integer32,
         wldfServerDiagnosticDiagnosticStoreDir OCTET STRING,
         wldfServerDiagnosticDiagnosticDataArchiveType OCTET STRING,
         wldfServerDiagnosticDiagnosticContextEnabled OCTET STRING,
         wldfServerDiagnosticStoreSizeCheckPeriod Integer32,
         wldfServerDiagnosticEventsImageCaptureInterval Counter64,
         wldfServerDiagnosticImageDir OCTET STRING,
         wldfServerDiagnosticDataRetirementEnabled OCTET STRING,
         wldfServerDiagnosticName OCTET STRING,
         wldfServerDiagnosticWLDFDiagnosticVolume OCTET STRING,
         wldfServerDiagnosticDiagnosticStoreIoBufferSize INTEGER,
         wldfServerDiagnosticDiagnosticStoreFileLockingEnabled OCTET STRING,
         wldfServerDiagnosticDiagnosticStoreMaxWindowBufferSize INTEGER,
         wldfServerDiagnosticDiagnosticStoreBlockSize INTEGER,
         wldfServerDiagnosticDiagnosticStoreMinWindowBufferSize INTEGER,
         wldfServerDiagnosticDiagnosticStoreMaxFileSize Counter64,
         wldfServerDiagnosticWLDFBuiltinSystemResourceType OCTET STRING,
         wldfServerDiagnosticDiagnosticJDBCSchemaName OCTET STRING,
         wldfServerDiagnosticTags OCTET STRING,
         wldfServerDiagnosticMaxHeapDumpCount INTEGER,
         wldfServerDiagnosticMaxThreadDumpCount INTEGER,
         wldfServerDiagnosticDiagnosticDumpsDir OCTET STRING
      }
      
   
   wldfServerDiagnosticIndex OBJECT-TYPE
      SYNTAX      OCTET STRING
      MAX-ACCESS  not-accessible
      STATUS      current
      DESCRIPTION "Index column"
      ::= { wldfServerDiagnosticEntry 1  }
   
   
   wldfServerDiagnosticObjectName OBJECT-TYPE
      SYNTAX      OCTET STRING
      MAX-ACCESS  read-only
      STATUS      current
      DESCRIPTION "ObjectName column"
      ::= { wldfServerDiagnosticEntry 2  }
   
   
   wldfServerDiagnosticType OBJECT-TYPE
      SYNTAX      OCTET STRING
      MAX-ACCESS  read-only
      STATUS      current
      DESCRIPTION "Returns the type of the MBean. "
      ::= { wldfServerDiagnosticEntry 3  }
   
   
   wldfServerDiagnosticSynchronousEventPersistenceEnabled OBJECT-TYPE
      SYNTAX      OCTET STRING
      MAX-ACCESS  read-only
      STATUS      current
      DESCRIPTION "Specifies the instrumentation events persistence policy. If true, events will be persisted synchronously within the same thread. If false, events will be queued up to be persisted in a separate thread. "
      ::= { wldfServerDiagnosticEntry 4  }
   
   
   wldfServerDiagnosticEventPersistenceInterval OBJECT-TYPE
      SYNTAX      Counter64
      MAX-ACCESS  read-only
      STATUS      current
      DESCRIPTION "The interval, in milliseconds, at which queued up instrumentation events will be periodically dispatched to the archive. "
      ::= { wldfServerDiagnosticEntry 5  }
   
   
   wldfServerDiagnosticPreferredStoreSizeLimit OBJECT-TYPE
      SYNTAX      Integer32
      MAX-ACCESS  read-only
      STATUS      current
      DESCRIPTION "Return the preferred limit on the size of diagnostic store file in MB. "
      ::= { wldfServerDiagnosticEntry 6  }
   
   
   wldfServerDiagnosticImageTimeout OBJECT-TYPE
      SYNTAX      Integer32
      MAX-ACCESS  read-only
      STATUS      current
      DESCRIPTION "The default timeout period, in minutes, that the server uses to delay future diagnostic image-capture requests. "
      ::= { wldfServerDiagnosticEntry 7  }
   
   
   wldfServerDiagnosticDiagnosticStoreDir OBJECT-TYPE
      SYNTAX      OCTET STRING
      MAX-ACCESS  read-only
      STATUS      current
      DESCRIPTION "The directory in which the current server maintains its diagnostic store. "
      ::= { wldfServerDiagnosticEntry 8  }
   
   
   wldfServerDiagnosticDiagnosticDataArchiveType OBJECT-TYPE
      SYNTAX      OCTET STRING
      MAX-ACCESS  read-only
      STATUS      current
      DESCRIPTION "Determines whether the current server persists its harvested metrics and event data in a diagnostic store (file-based store) or a JDBC based archive. The default store is file-based.  "
      ::= { wldfServerDiagnosticEntry 9  }
   
   
   wldfServerDiagnosticDiagnosticContextEnabled OBJECT-TYPE
      SYNTAX      OCTET STRING
      MAX-ACCESS  read-only
      STATUS      current
      DESCRIPTION "If true, diagnostic context creation is enabled. If false, the diagnostic context will not be created when requested. However, if the diagnostics context already exists because it was propagated from another VM or was created through the DyeInjection monitor, the context will be made available. "
      ::= { wldfServerDiagnosticEntry 10  }
   
   
   wldfServerDiagnosticStoreSizeCheckPeriod OBJECT-TYPE
      SYNTAX      Integer32
      MAX-ACCESS  read-only
      STATUS      current
      DESCRIPTION "Return the period in hours at which diagnostic store file size check will be performed "
      ::= { wldfServerDiagnosticEntry 11  }
   
   
   wldfServerDiagnosticEventsImageCaptureInterval OBJECT-TYPE
      SYNTAX      Counter64
      MAX-ACCESS  read-only
      STATUS      current
      DESCRIPTION "The time span, in milliseconds, for which recently archived events will be captured in the diagnostic image. All events archived on or after ( System.currentTimeMillis() - interval ) will be captured. "
      ::= { wldfServerDiagnosticEntry 12  }
   
   
   wldfServerDiagnosticImageDir OBJECT-TYPE
      SYNTAX      OCTET STRING
      MAX-ACCESS  read-only
      STATUS      current
      DESCRIPTION "The default directory where the server stores captured diagnostic images.  If you specify a relative pathname, the root of that path is the server's root directory.  If the directory does not exist, it will be created when the WebLogic Diagnostic Framework is initialized on the server. Note that each image capture request can override this default directory location. "
      ::= { wldfServerDiagnosticEntry 13  }
   
   
   wldfServerDiagnosticDataRetirementEnabled OBJECT-TYPE
      SYNTAX      OCTET STRING
      MAX-ACCESS  read-only
      STATUS      current
      DESCRIPTION "This attribute controls if configuration based data retirement functionality is enabled on the server. If disabled, all retirement policies will be disabled. "
      ::= { wldfServerDiagnosticEntry 14  }
   
   
   wldfServerDiagnosticName OBJECT-TYPE
      SYNTAX      OCTET STRING
      MAX-ACCESS  read-only
      STATUS      current
      DESCRIPTION "The user-specified name of this MBean instance.  This name is included as one of the key properties in the MBean's javax.management.ObjectName:  Name=user-specified-name "
      ::= { wldfServerDiagnosticEntry 15  }
   
   
   wldfServerDiagnosticWLDFDiagnosticVolume OBJECT-TYPE
      SYNTAX      OCTET STRING
      MAX-ACCESS  read-only
      STATUS      current
      DESCRIPTION "Specifies the volume of diagnostic data that is automatically produced by WebLogic Server at run time. Note that the WLDF diagnostic volume setting does not affect explicitly configured diagnostic modules. For example, this controls the volume of events generated for Flight Recorder.  This attribute has the following settings:  Off No diagnostic data is produced. Low Minimal amounts of automatic diagnostic data are produced. This is the default. Medium Additional diagnostic data is automatically generated beyond the amount generated for Low. High Additional diagnostic data is automatically generated beyond the amount generated for Medium.  "
      ::= { wldfServerDiagnosticEntry 16  }
   
   
   wldfServerDiagnosticDiagnosticStoreIoBufferSize OBJECT-TYPE
      SYNTAX      INTEGER
      MAX-ACCESS  read-only
      STATUS      current
      DESCRIPTION "The I/O buffer size, in bytes, automatically rounded down to the nearest power of 2, controls the largest write size.   When a native wlfileio driver is available, the setting applies to off-heap (native) memory. When a native wlfileio driver is not available, the setting applies to JAVA heap memory. For the best runtime performance, Oracle recommends setting DiagnosticStoreIOBufferSize so that it is larger than the largest write (multiple concurrent store requests may be combined into a single write).  See AllocatedIOBufferBytes to find out the actual allocated off-heap (native) memory amount. It is a multiple of IOBufferSize  "
      ::= { wldfServerDiagnosticEntry 17  }
   
   
   wldfServerDiagnosticDiagnosticStoreFileLockingEnabled OBJECT-TYPE
      SYNTAX      OCTET STRING
      MAX-ACCESS  read-only
      STATUS      current
      DESCRIPTION "Determines whether OS file locking is used.  When file locking protection is enabled, a store boot fails if another store instance already has opened the store files. Do not disable this setting unless you have procedures in place to prevent multiple store instances from opening the same file. File locking is not required but helps prevent corruption in the event that two same-named file store instances attempt to operate in the same directories. This setting applies to both primary and cache files. "
      ::= { wldfServerDiagnosticEntry 18  }
   
   
   wldfServerDiagnosticDiagnosticStoreMaxWindowBufferSize OBJECT-TYPE
      SYNTAX      INTEGER
      MAX-ACCESS  read-only
      STATUS      current
      DESCRIPTION "The maximum amount of data, in bytes and rounded down to the nearest power of 2, mapped into the JVM's address space per diagnostic store file. Applies only when a native wlfileio library is loaded.  A window buffer does not consume Java heap memory, but does consume off-heap (native) memory. If the store is unable to allocate the requested buffer size, it allocates smaller and smaller buffers until it reaches DiagnosticStoreMinWindowBufferSize, and then fails if it cannot honor DiagnosticStoreMinWindowBufferSize.  Oracle recommends setting the max window buffer size to more than double the size of the largest write (multiple concurrently updated records may be combined into a single write), and greater than or equal to the file size, unless there are other constraints. 32-bit JVMs may impose a total limit of between 2 and 4GB for combined Java heap plus off-heap (native) memory usage. "
      ::= { wldfServerDiagnosticEntry 19  }
   
   
   wldfServerDiagnosticDiagnosticStoreBlockSize OBJECT-TYPE
      SYNTAX      INTEGER
      MAX-ACCESS  read-only
      STATUS      current
      DESCRIPTION "The smallest addressable block, in bytes, of a file. When a native wlfileio driver is available and the block size has not been configured by the user, the store selects the minimum OS specific value for unbuffered (direct) I/O, if it is within the range [512, 8192]. A file store's block size does not change once the file store creates its files. Changes to block size only take effect for new file stores or after the current files have been deleted. See 'Tuning the Persistent Store' in Performance and Tuning for Oracle WebLogic Server. "
      ::= { wldfServerDiagnosticEntry 20  }
   
   
   wldfServerDiagnosticDiagnosticStoreMinWindowBufferSize OBJECT-TYPE
      SYNTAX      INTEGER
      MAX-ACCESS  read-only
      STATUS      current
      DESCRIPTION "The minimum amount of data, in bytes and rounded down to the nearest power of 2, mapped into the JVM's address space per diagnostic store file. Applies only when a native wlfileio library is loaded. See Diagnostic Store Maximum Window Buffer Size. "
      ::= { wldfServerDiagnosticEntry 21  }
   
   
   wldfServerDiagnosticDiagnosticStoreMaxFileSize OBJECT-TYPE
      SYNTAX      Counter64
      MAX-ACCESS  read-only
      STATUS      current
      DESCRIPTION "The maximum file size, in bytes.   The DiagnosticStoreMaxFileSize value affects the number of files needed to accommodate a diagnostic store of a particular size (number of files = diagnostic store size/MaxFileSize rounded up).  A diagnostic store automatically reuses space freed by deleted records and automatically expands individual files up to DiagnosticStoreMaxFileSize if there is not enough space for a new record. If there is no space left in exiting files for a new record, a diagnostic store creates an additional file.   A small number of larger files is normally preferred over a large number of smaller files as each file allocates Window Buffer and file handles.   If DiagnosticStoreMaxFileSize is larger than 2^24 * DiagnosticStoreBlockSize, then DiagnosticStoreMaxFileSize is ignored, and the value becomes 2^24 * DiagnosticStoreBlockSize. The default DiagnosticStoreBlockSize is 512, and 2^24 * 512 is 8 GB.    Oracle recommends not setting the Diagnostic Store Max File Size above the default value of 1,342,177,280. "
      ::= { wldfServerDiagnosticEntry 22  }
   
   
   wldfServerDiagnosticWLDFBuiltinSystemResourceType OBJECT-TYPE
      SYNTAX      OCTET STRING
      MAX-ACCESS  read-only
      STATUS      current
      DESCRIPTION "This attribute specifies the WLDF built-in system resource type in use for this server.  This attribute has the following settings:  None No WLDF built-in system resource in use. Low The Low WLDF built-in system resource. This is the default. Medium The Medium built-in system resource. High The High built-in system resource.  "
      ::= { wldfServerDiagnosticEntry 23  }
   
   
   wldfServerDiagnosticDiagnosticJDBCSchemaName OBJECT-TYPE
      SYNTAX      OCTET STRING
      MAX-ACCESS  read-only
      STATUS      current
      DESCRIPTION "The schema name to use for accessing JDBC-based archive tables.  If multiple WLDF JDBC archive schemas exist in the same database, this value specifies the correct schema to use for accessing JDBC-based archive tables in that database.  There is no default value. If a schema name is not specified, no schema name is applied when WLDF validates the run-time table or is used for the SQL statements. "
      ::= { wldfServerDiagnosticEntry 24  }
   
   
   wldfServerDiagnosticTags OBJECT-TYPE
      SYNTAX      OCTET STRING
      MAX-ACCESS  read-only
      STATUS      current
      DESCRIPTION "Return all tags on this Configuration MBean "
      ::= { wldfServerDiagnosticEntry 25  }
   
   
   wldfServerDiagnosticMaxHeapDumpCount OBJECT-TYPE
      SYNTAX      INTEGER
      MAX-ACCESS  read-only
      STATUS      current
      DESCRIPTION "Returns the maximum number of heap dump files to be retained which are generated by heap dump actions. If this limit is reached, oldest heap dumps will be deleted while creating new heap dump so that this limit is not exceeded. "
      ::= { wldfServerDiagnosticEntry 26  }
   
   
   wldfServerDiagnosticMaxThreadDumpCount OBJECT-TYPE
      SYNTAX      INTEGER
      MAX-ACCESS  read-only
      STATUS      current
      DESCRIPTION "Returns the maximum number of thread dump files to be retained which are generated by thread dump actions. If this limit is reached, oldest thread dump files will be deleted while creating new thread dump file so that this limit is not exceeded. "
      ::= { wldfServerDiagnosticEntry 27  }
   
   
   wldfServerDiagnosticDiagnosticDumpsDir OBJECT-TYPE
      SYNTAX      OCTET STRING
      MAX-ACCESS  read-only
      STATUS      current
      DESCRIPTION "Directory where heap and thread dumps will be generated by actions. This directory is a relative path with respect to the server directory "
      ::= { wldfServerDiagnosticEntry 28  }
   
   
   wldfSystemResourceTable OBJECT-TYPE
      SYNTAX      SEQUENCE OF WldfSystemResourceEntry
      MAX-ACCESS  not-accessible
      STATUS      current
      DESCRIPTION "This bean defines a system-level WebLogic Diagnostic Framework (WLDF) resource.  It links a separate descriptor that specifies the definition. "
      ::= { wls 1145  }
      
   
   wldfSystemResourceEntry OBJECT-TYPE
      SYNTAX      WldfSystemResourceEntry
      MAX-ACCESS  not-accessible
      STATUS      current
      DESCRIPTION "Generated SNMP Table Entry."
      INDEX { wldfSystemResourceIndex}
      ::= { wldfSystemResourceTable 1 }
      
   WldfSystemResourceEntry ::=
      SEQUENCE
      {
         wldfSystemResourceIndex OCTET STRING,
         wldfSystemResourceObjectName OCTET STRING,
         wldfSystemResourceType OCTET STRING,
         wldfSystemResourceCompatibilityName OCTET STRING,
         wldfSystemResourceDeploymentOrder Integer32,
         wldfSystemResourceDeploymentPrincipalName OCTET STRING,
         wldfSystemResourceDescriptorFileName OCTET STRING,
         wldfSystemResourceDescription OCTET STRING,
         wldfSystemResourceModuleType OCTET STRING,
         wldfSystemResourceName OCTET STRING,
         wldfSystemResourceSourcePath OCTET STRING,
         wldfSystemResourceTags OCTET STRING
      }
      
   
   wldfSystemResourceIndex OBJECT-TYPE
      SYNTAX      OCTET STRING
      MAX-ACCESS  not-accessible
      STATUS      current
      DESCRIPTION "Index column"
      ::= { wldfSystemResourceEntry 1  }
   
   
   wldfSystemResourceObjectName OBJECT-TYPE
      SYNTAX      OCTET STRING
      MAX-ACCESS  read-only
      STATUS      current
      DESCRIPTION "ObjectName column"
      ::= { wldfSystemResourceEntry 2  }
   
   
   wldfSystemResourceType OBJECT-TYPE
      SYNTAX      OCTET STRING
      MAX-ACCESS  read-only
      STATUS      current
      DESCRIPTION "Returns the type of the MBean. "
      ::= { wldfSystemResourceEntry 3  }
   
   
   wldfSystemResourceCompatibilityName OBJECT-TYPE
      SYNTAX      OCTET STRING
      MAX-ACCESS  read-only
      STATUS      current
      DESCRIPTION " This is only set for beans created as a result of conversion from an 8.1 application configured using ApplicationMBean and ComponentMBean.  Standalone modules in 8.1 have both an ApplicationMBean name and ComponentMBean name. This attribute stores the name of the latter, to be used when the server creates the transient ComponentMBean for backward compatibility. "
      ::= { wldfSystemResourceEntry 4  }
   
   
   wldfSystemResourceDeploymentOrder OBJECT-TYPE
      SYNTAX      Integer32
      MAX-ACCESS  read-only
      STATUS      current
      DESCRIPTION "An integer value that indicates when this unit is deployed, relative to other deployable units on a server, during startup.  Units with lower values are deployed before those with higher values. "
      ::= { wldfSystemResourceEntry 5  }
   
   
   wldfSystemResourceDeploymentPrincipalName OBJECT-TYPE
      SYNTAX      OCTET STRING
      MAX-ACCESS  read-only
      STATUS      current
      DESCRIPTION "A string value that indicates the principal that should be used when deploying the file or archive during startup and shutdown. This principal will be used to set the current subject when calling out into application code for interfaces such as ApplicationLifecycleListener. If no principal name is specified, then the anonymous principal will be used. "
      ::= { wldfSystemResourceEntry 6  }
   
   
   wldfSystemResourceDescriptorFileName OBJECT-TYPE
      SYNTAX      OCTET STRING
      MAX-ACCESS  read-only
      STATUS      current
      DESCRIPTION "The name of the descriptor file that contains the XML configuration information for this system-level resource. The location of this file is a relative path rooted at DOMAIN_DIR/config.  By default the file resides in the DOMAIN_DIR/config/diagnostics directory, and derives its name from the bean name using the following pattern:  &lt;beanName&gt;.xml  Note that the filename is a read-only property, which is set when the WLDF resource is created. "
      ::= { wldfSystemResourceEntry 7  }
   
   
   wldfSystemResourceDescription OBJECT-TYPE
      SYNTAX      OCTET STRING
      MAX-ACCESS  read-only
      STATUS      current
      DESCRIPTION "Optional short description of this WLDFSystemResource. If provided, the WebLogic Server Administration Console will display the resource description. "
      ::= { wldfSystemResourceEntry 8  }
   
   
   wldfSystemResourceModuleType OBJECT-TYPE
      SYNTAX      OCTET STRING
      MAX-ACCESS  read-only
      STATUS      current
      DESCRIPTION "The values match those defined by jsr88. This attribute may move to another MBean. "
      ::= { wldfSystemResourceEntry 9  }
   
   
   wldfSystemResourceName OBJECT-TYPE
      SYNTAX      OCTET STRING
      MAX-ACCESS  read-only
      STATUS      current
      DESCRIPTION "The user-specified name of this MBean instance.  This name is included as one of the key properties in the MBean's javax.management.ObjectName:  Name=user-specified-name "
      ::= { wldfSystemResourceEntry 10  }
   
   
   wldfSystemResourceSourcePath OBJECT-TYPE
      SYNTAX      OCTET STRING
      MAX-ACCESS  read-only
      STATUS      current
      DESCRIPTION " "
      ::= { wldfSystemResourceEntry 11  }
   
   
   wldfSystemResourceTags OBJECT-TYPE
      SYNTAX      OCTET STRING
      MAX-ACCESS  read-only
      STATUS      current
      DESCRIPTION "Return all tags on this Configuration MBean "
      ::= { wldfSystemResourceEntry 12  }
   
   
   wtcServerTable OBJECT-TYPE
      SYNTAX      SEQUENCE OF WtcServerEntry
      MAX-ACCESS  not-accessible
      STATUS      current
      DESCRIPTION "This MBean defines a WTC Server. "
      ::= { wls 1150  }
      
   
   wtcServerEntry OBJECT-TYPE
      SYNTAX      WtcServerEntry
      MAX-ACCESS  not-accessible
      STATUS      current
      DESCRIPTION "Generated SNMP Table Entry."
      INDEX { wtcServerIndex}
      ::= { wtcServerTable 1 }
      
   WtcServerEntry ::=
      SEQUENCE
      {
         wtcServerIndex       OCTET STRING,
         wtcServerObjectName  OCTET STRING,
         wtcServerType        OCTET STRING,
         wtcServerName        OCTET STRING,
         wtcServerDeploymentOrder Integer32,
         wtcServerTags        OCTET STRING
      }
      
   
   wtcServerIndex OBJECT-TYPE
      SYNTAX      OCTET STRING
      MAX-ACCESS  not-accessible
      STATUS      current
      DESCRIPTION "Index column"
      ::= { wtcServerEntry 1  }
   
   
   wtcServerObjectName OBJECT-TYPE
      SYNTAX      OCTET STRING
      MAX-ACCESS  read-only
      STATUS      current
      DESCRIPTION "ObjectName column"
      ::= { wtcServerEntry 2  }
   
   
   wtcServerType OBJECT-TYPE
      SYNTAX      OCTET STRING
      MAX-ACCESS  read-only
      STATUS      current
      DESCRIPTION "Returns the type of the MBean. "
      ::= { wtcServerEntry 3  }
   
   
   wtcServerName OBJECT-TYPE
      SYNTAX      OCTET STRING
      MAX-ACCESS  read-only
      STATUS      current
      DESCRIPTION "The user-specified name of this MBean instance.  This name is included as one of the key properties in the MBean's javax.management.ObjectName:  Name=user-specified-name "
      ::= { wtcServerEntry 4  }
   
   
   wtcServerDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { wtcServerEntry 5  }
   
   
   wtcServerTags OBJECT-TYPE
      SYNTAX      OCTET STRING
      MAX-ACCESS  read-only
      STATUS      current
      DESCRIPTION "Return all tags on this Configuration MBean "
      ::= { wtcServerEntry 6  }
   
   
   webAppContainerTable OBJECT-TYPE
      SYNTAX      SEQUENCE OF WebAppContainerEntry
      MAX-ACCESS  not-accessible
      STATUS      current
      DESCRIPTION "This MBean is used to specify domain-wide defaults for the WebApp container. In general, these properties can be overridden at the cluster level (in ClusterMBean, if the same property is present there), the server level (in ServerMBean, if the same property is present there) or for a specific Web application (in weblogic.xml). "
      ::= { wls 1155  }
      
   
   webAppContainerEntry OBJECT-TYPE
      SYNTAX      WebAppContainerEntry
      MAX-ACCESS  not-accessible
      STATUS      current
      DESCRIPTION "Generated SNMP Table Entry."
      INDEX { webAppContainerIndex}
      ::= { webAppContainerTable 1 }
      
   WebAppContainerEntry ::=
      SEQUENCE
      {
         webAppContainerIndex OCTET STRING,
         webAppContainerObjectName OCTET STRING,
         webAppContainerType  OCTET STRING,
         webAppContainerMaxPostSize Integer32,
         webAppContainerXPoweredByHeaderLevel OCTET STRING,
         webAppContainerServletAuthenticationFormURL OCTET STRING,
         webAppContainerReloginEnabled OCTET STRING,
         webAppContainerWorkContextPropagationEnabled OCTET STRING,
         webAppContainerRtexprvalueJspParamName OCTET STRING,
         webAppContainerFilterDispatchedRequestsEnabled OCTET STRING,
         webAppContainerClientCertProxyEnabled OCTET STRING,
         webAppContainerOverloadProtectionEnabled OCTET STRING,
         webAppContainerOptimisticSerialization OCTET STRING,
         webAppContainerRetainOriginalURL OCTET STRING,
         webAppContainerWeblogicPluginEnabled OCTET STRING,
         webAppContainerHttpTraceSupportEnabled OCTET STRING,
         webAppContainerWAPEnabled OCTET STRING,
         webAppContainerJSPCompilerBackwardsCompatible OCTET STRING,
         webAppContainerAuthCookieEnabled OCTET STRING,
         webAppContainerName  OCTET STRING,
         webAppContainerAllowAllRoles OCTET STRING,
         webAppContainerP3PHeaderValue OCTET STRING,
         webAppContainerServletReloadCheckSecs Integer32,
         webAppContainerMaxPostTimeSecs Integer32,
         webAppContainerMimeMappingFile OCTET STRING,
         webAppContainerShowArchivedRealPathEnabled OCTET STRING,
         webAppContainerPostTimeoutSecs Integer32,
         webAppContainerChangeSessionIDOnAuthentication OCTET STRING,
         webAppContainerMaxRequestParameterCount INTEGER,
         webAppContainerTags  OCTET STRING,
         webAppContainerJaxRsMonitoringDefaultBehavior OCTET STRING
      }
      
   
   webAppContainerIndex OBJECT-TYPE
      SYNTAX      OCTET STRING
      MAX-ACCESS  not-accessible
      STATUS      current
      DESCRIPTION "Index column"
      ::= { webAppContainerEntry 1  }
   
   
   webAppContainerObjectName OBJECT-TYPE
      SYNTAX      OCTET STRING
      MAX-ACCESS  read-only
      STATUS      current
      DESCRIPTION "ObjectName column"
      ::= { webAppContainerEntry 2  }
   
   
   webAppContainerType OBJECT-TYPE
      SYNTAX      OCTET STRING
      MAX-ACCESS  read-only
      STATUS      current
      DESCRIPTION "Returns the type of the MBean. "
      ::= { webAppContainerEntry 3  }
   
   
   webAppContainerMaxPostSize OBJECT-TYPE
      SYNTAX      Integer32
      MAX-ACCESS  read-only
      STATUS      current
      DESCRIPTION "The maximum post size this server allows for reading HTTP POST data in a servlet request. A value less than 0 indicates an unlimited size. "
      ::= { webAppContainerEntry 4  }
   
   
   webAppContainerXPoweredByHeaderLevel OBJECT-TYPE
      SYNTAX      OCTET STRING
      MAX-ACCESS  read-only
      STATUS      current
      DESCRIPTION " WebLogic Server uses the X-Powered-By HTTP header, as recommended by the Servlet 3.1 specification, to publish its implementation information.   Following are the options:   'NONE' (default):  X-Powered-By header will not be sent  'SHORT':           'Servlet/3.1 JSP/2.3'   'MEDIUM':          'Servlet/3.1 JSP/2.3 (WebLogic/12.2)'  'FULL':            'Servlet/3.1 JSP/2.3 (WebLogic/12.2 JDK/1.8)'   "
      ::= { webAppContainerEntry 5  }
   
   
   webAppContainerServletAuthenticationFormURL OBJECT-TYPE
      SYNTAX      OCTET STRING
      MAX-ACCESS  read-only
      STATUS      current
      DESCRIPTION " ServletAuthenticationFormURL is used for backward compatibility with previous releases of Weblogic Server. If ServletAuthenticationFormURL is set to true (default), then ServletAuthentication.getTargetURLForFormAuthentication() and HttpSession.getAttribute(AuthFilter.TARGET_URL) will return the URL of the protected target resource. If set to false, the above APIs will return the URI of the protected target resource. By default, the value is set to true.(new method added in 9.0.0.1)  "
      ::= { webAppContainerEntry 6  }
   
   
   webAppContainerReloginEnabled OBJECT-TYPE
      SYNTAX      OCTET STRING
      MAX-ACCESS  read-only
      STATUS      current
      DESCRIPTION "Beginning with the 9.0 release, the FORM/BASIC authentication behavior has been modified to conform strictly to the Java EE Specification. If a user has logged-in but does not have privileges to access a resource, the 403 (FORBIDDEN) page will be returned. Turn this flag on to enable the old behavior, which was to return the user to the login form. "
      ::= { webAppContainerEntry 7  }
   
   
   webAppContainerWorkContextPropagationEnabled OBJECT-TYPE
      SYNTAX      OCTET STRING
      MAX-ACCESS  read-only
      STATUS      current
      DESCRIPTION "Indicates whether or not WorkContextPropagation is enabled. By default, it is turned on. There is a little overhead involved in propagating WorkContexts. Therefore, if you don't want WorkContext propagation, turn this value off in production environments.  "
      ::= { webAppContainerEntry 8  }
   
   
   webAppContainerRtexprvalueJspParamName OBJECT-TYPE
      SYNTAX      OCTET STRING
      MAX-ACCESS  read-only
      STATUS      current
      DESCRIPTION "Global property which determines the behavior of the JSP compiler when a jsp:param attribute 'name' has a request time value. Without this property set to 'true', the JSP compiler throws an error for a JSP using a request time value for the 'name' attribute as mandated by the JSP 2.0 specification. This property exists for backward compatibility. "
      ::= { webAppContainerEntry 9  }
   
   
   webAppContainerFilterDispatchedRequestsEnabled OBJECT-TYPE
      SYNTAX      OCTET STRING
      MAX-ACCESS  read-only
      STATUS      current
      DESCRIPTION " Indicates whether or not to apply filters to dispatched requests. This is a backward compatibility flag. Until version 8.1, WebLogic Server applied ServletFilters (if configured for the web application) on request dispatches (and includes/forwards). Servlet 2.4 has introduced the 'Dispatcher' element to make this behavior explicit. The default value is Dispatcher=REQUEST. In order to be compliant with the Java EE specification, the default value for FilterDispatchedRequestsEnabled is false beginning with WebLogic Server 9.0. Note that if you are using old descriptors (meaning web.xml does not have version=2.4), then WebLogic Server automatically uses FilterDispatchedRequestsEnabled = true for the web applications, unless filter-dispatched-requests-enabled is explicitly set to false in weblogic.xml. This means that old applications will work fine without any modification. Additionally, during migration of old domains to the 9.0 domain, the migration plug-in automatically sets this flag to true.  "
      ::= { webAppContainerEntry 10  }
   
   
   webAppContainerClientCertProxyEnabled OBJECT-TYPE
      SYNTAX      OCTET STRING
      MAX-ACCESS  read-only
      STATUS      current
      DESCRIPTION "Specifies whether or not to honor the WL-Proxy-Client-Cert header coming with the request.  "
      ::= { webAppContainerEntry 11  }
   
   
   webAppContainerOverloadProtectionEnabled OBJECT-TYPE
      SYNTAX      OCTET STRING
      MAX-ACCESS  read-only
      STATUS      current
      DESCRIPTION "This parameter is used to enable overload protection in the web application container against low memory conditions. When a low memory situation occurs, new session creation attempts will result in weblogic.servlet.SessionCreationException. The application code needs to catch this exception and take proper action. Alternatively appropriate error-pages can be configured in web.xml against weblogic.servlet.SessionCreationException. This check is performed only on memory and replicated sessions.  "
      ::= { webAppContainerEntry 12  }
   
   
   webAppContainerOptimisticSerialization OBJECT-TYPE
      SYNTAX      OCTET STRING
      MAX-ACCESS  read-only
      STATUS      current
      DESCRIPTION " When OptimisticSerialization is turned on, WebLogic Server does not serialize-deserialize context and request attributes upon getAttribute(name) when a request gets dispatched across servlet contexts. This means you will need to make sure that the attributes common to web applications are scoped to a common parent classloader (they are application-scoped) or placed in the system classpath if the two web applications do not belong to the same application. When OptimisticSerialization is turned off (which is the default), WebLogic Server does serialize-deserialize context and request attributes upon getAttribute(name) to avoid the possibility of ClassCastExceptions. The value of OptimisticSerialization can also be overridden for specific web applications by setting the optimistic-serialization value in weblogic.xml.  "
      ::= { webAppContainerEntry 13  }
   
   
   webAppContainerRetainOriginalURL OBJECT-TYPE
      SYNTAX      OCTET STRING
      MAX-ACCESS  read-only
      STATUS      current
      DESCRIPTION " The retain-original-url property is used in FORM based authentication scenarios. When this property is set to true, after a successful authentication, WebLogic Server will redirect back to the web resource (page/servlet) retaining the protocol (http/https) used to access the protected resource in the original request. If set to false (which is the default value), WebLogic Server will redirect back to the protected resource using the current protocol. The retain-original-url value can also be specified at per web application level in weblogic.xml. The value in weblogic.xml, if specified, overrides the domain level value. "
      ::= { webAppContainerEntry 14  }
   
   
   webAppContainerWeblogicPluginEnabled OBJECT-TYPE
      SYNTAX      OCTET STRING
      MAX-ACCESS  read-only
      STATUS      current
      DESCRIPTION "Specifies whether or not the proprietary WL-Proxy-Client-IP header should be honored. (This is needed only when WebLogic Server plug-ins are configured.) "
      ::= { webAppContainerEntry 15  }
   
   
   webAppContainerHttpTraceSupportEnabled OBJECT-TYPE
      SYNTAX      OCTET STRING
      MAX-ACCESS  read-only
      STATUS      current
      DESCRIPTION " Returns the value of HttpTraceSupportEnabled.  "
      ::= { webAppContainerEntry 16  }
   
   
   webAppContainerWAPEnabled OBJECT-TYPE
      SYNTAX      OCTET STRING
      MAX-ACCESS  read-only
      STATUS      current
      DESCRIPTION "Indicates whether the session ID should include JVM information. (Checking this box may be necessary when using URL rewriting with WAP devices that limit the size of the URL to 128 characters, and may also affect the use of replicated sessions in a cluster.) When this box is selected, the default size of the URL will be set at 52 characters, and it will not contain any special characters. "
      ::= { webAppContainerEntry 17  }
   
   
   webAppContainerJSPCompilerBackwardsCompatible OBJECT-TYPE
      SYNTAX      OCTET STRING
      MAX-ACCESS  read-only
      STATUS      current
      DESCRIPTION "Global property to determine the behavior of the JSP compiler. When this property set to 'true', the JSP compiler throws a translation error for JSPs that do not conform to the JSP2.0 specification. This property exists for backward compatibility. "
      ::= { webAppContainerEntry 18  }
   
   
   webAppContainerAuthCookieEnabled OBJECT-TYPE
      SYNTAX      OCTET STRING
      MAX-ACCESS  read-only
      STATUS      current
      DESCRIPTION "Specifies whether the AuthCookie feature is enabled or not. "
      ::= { webAppContainerEntry 19  }
   
   
   webAppContainerName OBJECT-TYPE
      SYNTAX      OCTET STRING
      MAX-ACCESS  read-only
      STATUS      current
      DESCRIPTION "The user-specified name of this MBean instance.  This name is included as one of the key properties in the MBean's javax.management.ObjectName:  Name=user-specified-name "
      ::= { webAppContainerEntry 20  }
   
   
   webAppContainerAllowAllRoles OBJECT-TYPE
      SYNTAX      OCTET STRING
      MAX-ACCESS  read-only
      STATUS      current
      DESCRIPTION "In the security-constraints elements defined in a web application's web.xml deployment descriptor, the auth-constraint element indicates the user roles that should be permitted access to this resource collection. Here role-name = '*' is a compact syntax for indicating all roles in the Web application. In previous releases, role-name = '*' was treated as all users/roles defined in the realm.  This parameter is a backward-compatibility switch to restore old behavior. Default behavior is one required by the specification, meaning all roles defined in the web application.  If set, the value defined in weblogic.xml (container-descriptor -> allow-all-roles) takes precedence (if set) over this value.  "
      ::= { webAppContainerEntry 21  }
   
   
   webAppContainerP3PHeaderValue OBJECT-TYPE
      SYNTAX      OCTET STRING
      MAX-ACCESS  read-only
      STATUS      current
      DESCRIPTION " Returns the P3P header value that will be sent with all responses for HTTP requests (if non-null). The value of this header points to the location of the policy reference file for the website.  Alternatively, a servlet filter can be used to set the P3P header. "
      ::= { webAppContainerEntry 22  }
   
   
   webAppContainerServletReloadCheckSecs OBJECT-TYPE
      SYNTAX      Integer32
      MAX-ACCESS  read-only
      STATUS      current
      DESCRIPTION " "
      ::= { webAppContainerEntry 23  }
   
   
   webAppContainerMaxPostTimeSecs OBJECT-TYPE
      SYNTAX      Integer32
      MAX-ACCESS  read-only
      STATUS      current
      DESCRIPTION "Maximum post time (in seconds) for reading HTTP POST data in a servlet request. MaxPostTime &lt; 0 means unlimited "
      ::= { webAppContainerEntry 24  }
   
   
   webAppContainerMimeMappingFile OBJECT-TYPE
      SYNTAX      OCTET STRING
      MAX-ACCESS  read-only
      STATUS      current
      DESCRIPTION "Returns the name of the file containing mime-mappings for the domain. The Format of the file should be: extension=mime-type   For Example: htm=text/html gif=image/gif jpg=image/jpeg  If this file does not exist, WebLogic Server uses an implicit mime-mapping set of mappings defined in weblogic.utils.http.HttpConstants (DEFAULT_MIME_MAPPINGS). To remove a mapping defined in implicit map, set it to blank.  "
      ::= { webAppContainerEntry 25  }
   
   
   webAppContainerShowArchivedRealPathEnabled OBJECT-TYPE
      SYNTAX      OCTET STRING
      MAX-ACCESS  read-only
      STATUS      current
      DESCRIPTION "Global property to determine the behavior of getRealPath() for archived web applications. When this property is set to 'true', getRealPath() will return the canonical path of the resource files.  "
      ::= { webAppContainerEntry 26  }
   
   
   webAppContainerPostTimeoutSecs OBJECT-TYPE
      SYNTAX      Integer32
      MAX-ACCESS  read-only
      STATUS      current
      DESCRIPTION "The amount of time this server waits between receiving chunks of data in an HTTP POST data before it times out. (This is used to prevent denial-of-service attacks that attempt to overload the server with POST data.) "
      ::= { webAppContainerEntry 27  }
   
   
   webAppContainerChangeSessionIDOnAuthentication OBJECT-TYPE
      SYNTAX      OCTET STRING
      MAX-ACCESS  read-only
      STATUS      current
      DESCRIPTION "Global property to determine if we need to generate a new SessionID after authentication. When this property is set to 'false', the previous sessionID will be retained even after authorization.  "
      ::= { webAppContainerEntry 28  }
   
   
   webAppContainerMaxRequestParameterCount OBJECT-TYPE
      SYNTAX      INTEGER
      MAX-ACCESS  read-only
      STATUS      current
      DESCRIPTION "The maximum request parameter count this server allows for reading maximum HTTP POST parameters count in a servlet request.  Gets the maxRequestParameterCount attribute of the WebServerMBean object. "
      ::= { webAppContainerEntry 29  }
   
   
   webAppContainerTags OBJECT-TYPE
      SYNTAX      OCTET STRING
      MAX-ACCESS  read-only
      STATUS      current
      DESCRIPTION "Return all tags on this Configuration MBean "
      ::= { webAppContainerEntry 30  }
   
   
   webAppContainerJaxRsMonitoringDefaultBehavior OBJECT-TYPE
      SYNTAX      OCTET STRING
      MAX-ACCESS  read-only
      STATUS      current
      DESCRIPTION " Global property to determine the behavior of monitoring in JAX-RS applications. When the property is set to {@code true} (or not set) the monitoring is turned on (if not overridden by properties set directly in application). If the property is set to {@code false} the monitoring for all JAX-RS applications is disabled.  "
      ::= { webAppContainerEntry 31  }
   
   
   webServerLogTable OBJECT-TYPE
      SYNTAX      SEQUENCE OF WebServerLogEntry
      MAX-ACCESS  not-accessible
      STATUS      current
      DESCRIPTION "Aggregates the logging attributes for the WebServerMBean. "
      ::= { wls 1160  }
      
   
   webServerLogEntry OBJECT-TYPE
      SYNTAX      WebServerLogEntry
      MAX-ACCESS  not-accessible
      STATUS      current
      DESCRIPTION "Generated SNMP Table Entry."
      INDEX { webServerLogIndex}
      ::= { webServerLogTable 1 }
      
   WebServerLogEntry ::=
      SEQUENCE
      {
         webServerLogIndex    OCTET STRING,
         webServerLogObjectName OCTET STRING,
         webServerLogType     OCTET STRING,
         webServerLogLogTimeInGMT OCTET STRING,
         webServerLogNumberOfFilesLimited OCTET STRING,
         webServerLogFileTimeSpan Integer32,
         webServerLogLogFileFormat OCTET STRING,
         webServerLogRotationType OCTET STRING,
         webServerLogFileCount Integer32,
         webServerLogLoggingEnabled OCTET STRING,
         webServerLogELFFields OCTET STRING,
         webServerLogFileName OCTET STRING,
         webServerLogFileMinSize Integer32,
         webServerLogBufferSizeKB Integer32,
         webServerLogDateFormatPattern OCTET STRING,
         webServerLogRotationTime OCTET STRING,
         webServerLogRotateLogOnStartup OCTET STRING,
         webServerLogName     OCTET STRING,
         webServerLogLogFileRotationDir OCTET STRING,
         webServerLogTags     OCTET STRING
      }
      
   
   webServerLogIndex OBJECT-TYPE
      SYNTAX      OCTET STRING
      MAX-ACCESS  not-accessible
      STATUS      current
      DESCRIPTION "Index column"
      ::= { webServerLogEntry 1  }
   
   
   webServerLogObjectName OBJECT-TYPE
      SYNTAX      OCTET STRING
      MAX-ACCESS  read-only
      STATUS      current
      DESCRIPTION "ObjectName column"
      ::= { webServerLogEntry 2  }
   
   
   webServerLogType OBJECT-TYPE
      SYNTAX      OCTET STRING
      MAX-ACCESS  read-only
      STATUS      current
      DESCRIPTION "Returns the type of the MBean. "
      ::= { webServerLogEntry 3  }
   
   
   webServerLogLogTimeInGMT OBJECT-TYPE
      SYNTAX      OCTET STRING
      MAX-ACCESS  read-only
      STATUS      current
      DESCRIPTION "Specifies whether the time stamps for HTTP log messages are in Greenwich Mean Time (GMT) regardless of the local time zone that the host computer specifies.  Use this method to comply with the W3C specification for Extended Format log files. The specification states that all time stamps for Extended Format log entries be in GMT.  This method applies only if you have specified the extended message format. "
      ::= { webServerLogEntry 4  }
   
   
   webServerLogNumberOfFilesLimited OBJECT-TYPE
      SYNTAX      OCTET STRING
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require. "
      ::= { webServerLogEntry 5  }
   
   
   webServerLogFileTimeSpan OBJECT-TYPE
      SYNTAX      Integer32
      MAX-ACCESS  read-only
      STATUS      current
      DESCRIPTION "The interval (in hours) at which the server saves old log messages to another file. (Requires that you specify a file rotation type of TIME.) "
      ::= { webServerLogEntry 6  }
   
   
   webServerLogLogFileFormat OBJECT-TYPE
      SYNTAX      OCTET STRING
      MAX-ACCESS  read-only
      STATUS      current
      DESCRIPTION "The format of the HTTP log file. Both formats are defined by the W3C. With the extended log format, you use server directives in the log file to customize the information that the server records. "
      ::= { webServerLogEntry 7  }
   
   
   webServerLogRotationType OBJECT-TYPE
      SYNTAX      OCTET STRING
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as SERVER_NAME.lognnnnn.  TIME At each time interval that you specify in TimeSpan, the server renames the file as SERVER_NAME.lognnnnn.   After the server renames a file, subsequent messages accumulate in a new file with the name that you specified as the log file name. "
      ::= { webServerLogEntry 8  }
   
   
   webServerLogFileCount OBJECT-TYPE
      SYNTAX      Integer32
      MAX-ACCESS  read-only
      STATUS      current
      DESCRIPTION "The maximum number of log files that the server creates when it rotates the log. This number does not include the file that the server uses to store current messages. (Requires that you enable Number of Files Limited.) "
      ::= { webServerLogEntry 9  }
   
   
   webServerLogLoggingEnabled OBJECT-TYPE
      SYNTAX      OCTET STRING
      MAX-ACCESS  read-only
      STATUS      current
      DESCRIPTION "Indicates whether this server logs HTTP requests. (The remaining fields on this page are relevant only if you select this check box.)  Gets the loggingEnabled attribute of the WebServerMBean object. "
      ::= { webServerLogEntry 10  }
   
   
   webServerLogELFFields OBJECT-TYPE
      SYNTAX      OCTET STRING
      MAX-ACCESS  read-only
      STATUS      current
      DESCRIPTION "Returns the list of fields specified for the extended logging format for access.log.  "
      ::= { webServerLogEntry 11  }
   
   
   webServerLogFileName OBJECT-TYPE
      SYNTAX      OCTET STRING
      MAX-ACCESS  read-only
      STATUS      current
      DESCRIPTION "The name of the log file. "
      ::= { webServerLogEntry 12  }
   
   
   webServerLogFileMinSize OBJECT-TYPE
      SYNTAX      Integer32
      MAX-ACCESS  read-only
      STATUS      current
      DESCRIPTION "The size (1 - 2097150 kilobytes) that triggers the server to move log messages to a separate file. The default is 500 kilobytes. After the log file reaches the specified minimum size, the next time the server checks the file size, it will rename the current log file as SERVER_NAME.lognnnnn and create a new one to store subsequent messages. (Requires that you specify a file rotation type of Size.) "
      ::= { webServerLogEntry 13  }
   
   
   webServerLogBufferSizeKB OBJECT-TYPE
      SYNTAX      Integer32
      MAX-ACCESS  read-only
      STATUS      current
      DESCRIPTION "Gets the underlying log buffer size in kilobytes "
      ::= { webServerLogEntry 14  }
   
   
   webServerLogDateFormatPattern OBJECT-TYPE
      SYNTAX      OCTET STRING
      MAX-ACCESS  read-only
      STATUS      current
      DESCRIPTION "The date format pattern used for rendering dates in the  log. The DateFormatPattern string conforms to the specification of the java.text.SimpleDateFormat class. "
      ::= { webServerLogEntry 15  }
   
   
   webServerLogRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  Note that WebLogic Server sets a threshold size limit of 500 MB before it forces a hard rotation to prevent excessive log file growth.  Use the following format: H:mm, where  H is Hour in day (0-23) mm is the minute in hour  "
      ::= { webServerLogEntry 16  }
   
   
   webServerLogRotateLogOnStartup OBJECT-TYPE
      SYNTAX      OCTET STRING
      MAX-ACCESS  read-only
      STATUS      current
      DESCRIPTION "Specifies whether a server rotates its log file during its startup cycle. The default value in production mode is false. "
      ::= { webServerLogEntry 17  }
   
   
   webServerLogName OBJECT-TYPE
      SYNTAX      OCTET STRING
      MAX-ACCESS  read-only
      STATUS      current
      DESCRIPTION "The user-specified name of this MBean instance.  This name is included as one of the key properties in the MBean's javax.management.ObjectName:  Name=user-specified-name "
      ::= { webServerLogEntry 18  }
   
   
   webServerLogLogFileRotationDir OBJECT-TYPE
      SYNTAX      OCTET STRING
      MAX-ACCESS  read-only
      STATUS      current
      DESCRIPTION "The directory where the rotated log files will be stored. By default the rotated files are stored in the same directory where the log file is stored. "
      ::= { webServerLogEntry 19  }
   
   
   webServerLogTags OBJECT-TYPE
      SYNTAX      OCTET STRING
      MAX-ACCESS  read-only
      STATUS      current
      DESCRIPTION "Return all tags on this Configuration MBean "
      ::= { webServerLogEntry 20  }
   
   
   webServiceTable OBJECT-TYPE
      SYNTAX      SEQUENCE OF WebServiceEntry
      MAX-ACCESS  not-accessible
      STATUS      current
      DESCRIPTION "Encapsulates information about a Web Service configuration. "
      ::= { wls 1165  }
      
   
   webServiceEntry OBJECT-TYPE
      SYNTAX      WebServiceEntry
      MAX-ACCESS  not-accessible
      STATUS      current
      DESCRIPTION "Generated SNMP Table Entry."
      INDEX { webServiceIndex}
      ::= { webServiceTable 1 }
      
   WebServiceEntry ::=
      SEQUENCE
      {
         webServiceIndex      OCTET STRING,
         webServiceObjectName OCTET STRING,
         webServiceType       OCTET STRING,
         webServiceMessagingQueueMDBRunAsPrincipalName OCTET STRING,
         webServiceMessagingQueue OCTET STRING,
         webServiceJmsConnectionFactory OCTET STRING,
         webServiceCallbackQueueMDBRunAsPrincipalName OCTET STRING,
         webServiceCallbackQueue OCTET STRING,
         webServiceName       OCTET STRING,
         webServiceTags       OCTET STRING
      }
      
   
   webServiceIndex OBJECT-TYPE
      SYNTAX      OCTET STRING
      MAX-ACCESS  not-accessible
      STATUS      current
      DESCRIPTION "Index column"
      ::= { webServiceEntry 1  }
   
   
   webServiceObjectName OBJECT-TYPE
      SYNTAX      OCTET STRING
      MAX-ACCESS  read-only
      STATUS      current
      DESCRIPTION "ObjectName column"
      ::= { webServiceEntry 2  }
   
   
   webServiceType OBJECT-TYPE
      SYNTAX      OCTET STRING
      MAX-ACCESS  read-only
      STATUS      current
      DESCRIPTION "Returns the type of the MBean. "
      ::= { webServiceEntry 3  }
   
   
   webServiceMessagingQueueMDBRunAsPrincipalName OBJECT-TYPE
      SYNTAX      OCTET STRING
      MAX-ACCESS  read-only
      STATUS      current
      DESCRIPTION "For use only with the JAX-RPC stack. For JAX-WS, use WebServiceBufferingMBean instead.  "
      ::= { webServiceEntry 4  }
   
   
   webServiceMessagingQueue OBJECT-TYPE
      SYNTAX      OCTET STRING
      MAX-ACCESS  read-only
      STATUS      current
      DESCRIPTION "For use only with the JAX-RPC stack. For JAX-WS, use WebServiceBufferingMBean instead.  "
      ::= { webServiceEntry 5  }
   
   
   webServiceJmsConnectionFactory OBJECT-TYPE
      SYNTAX      OCTET STRING
      MAX-ACCESS  read-only
      STATUS      current
      DESCRIPTION "For use only with the JAX-RPC stack. For JAX-WS, use WebServiceBufferingMBean instead.  "
      ::= { webServiceEntry 6  }
   
   
   webServiceCallbackQueueMDBRunAsPrincipalName OBJECT-TYPE
      SYNTAX      OCTET STRING
      MAX-ACCESS  read-only
      STATUS      current
      DESCRIPTION "For use only with the JAX-RPC stack. For JAX-WS, use WebServiceBufferingMBean instead.  "
      ::= { webServiceEntry 7  }
   
   
   webServiceCallbackQueue OBJECT-TYPE
      SYNTAX      OCTET STRING
      MAX-ACCESS  read-only
      STATUS      current
      DESCRIPTION "For use only with the JAX-RPC stack. For JAX-WS, use WebServiceBufferingMBean instead.  "
      ::= { webServiceEntry 8  }
   
   
   webServiceName OBJECT-TYPE
      SYNTAX      OCTET STRING
      MAX-ACCESS  read-only
      STATUS      current
      DESCRIPTION "The user-specified name of this MBean instance.  This name is included as one of the key properties in the MBean's javax.management.ObjectName:  Name=user-specified-name "
      ::= { webServiceEntry 9  }
   
   
   webServiceTags OBJECT-TYPE
      SYNTAX      OCTET STRING
      MAX-ACCESS  read-only
      STATUS      current
      DESCRIPTION "Return all tags on this Configuration MBean "
      ::= { webServiceEntry 10  }
   
   
   webserviceCredentialProviderTable OBJECT-TYPE
      SYNTAX      SEQUENCE OF WebserviceCredentialProviderEntry
      MAX-ACCESS  not-accessible
      STATUS      current
      DESCRIPTION "Encapsulates information about a particular credential provider that has been configured for a Web Service security configuration. "
      ::= { wls 1170  }
      
   
   webserviceCredentialProviderEntry OBJECT-TYPE
      SYNTAX      WebserviceCredentialProviderEntry
      MAX-ACCESS  not-accessible
      STATUS      current
      DESCRIPTION "Generated SNMP Table Entry."
      INDEX { webserviceCredentialProviderIndex}
      ::= { webserviceCredentialProviderTable 1 }
      
   WebserviceCredentialProviderEntry ::=
      SEQUENCE
      {
         webserviceCredentialProviderIndex OCTET STRING,
         webserviceCredentialProviderObjectName OCTET STRING,
         webserviceCredentialProviderType OCTET STRING,
         webserviceCredentialProviderTokenType OCTET STRING,
         webserviceCredentialProviderName OCTET STRING,
         webserviceCredentialProviderClassName OCTET STRING,
         webserviceCredentialProviderTags OCTET STRING
      }
      
   
   webserviceCredentialProviderIndex OBJECT-TYPE
      SYNTAX      OCTET STRING
      MAX-ACCESS  not-accessible
      STATUS      current
      DESCRIPTION "Index column"
      ::= { webserviceCredentialProviderEntry 1  }
   
   
   webserviceCredentialProviderObjectName OBJECT-TYPE
      SYNTAX      OCTET STRING
      MAX-ACCESS  read-only
      STATUS      current
      DESCRIPTION "ObjectName column"
      ::= { webserviceCredentialProviderEntry 2  }
   
   
   webserviceCredentialProviderType OBJECT-TYPE
      SYNTAX      OCTET STRING
      MAX-ACCESS  read-only
      STATUS      current
      DESCRIPTION "Returns the type of the MBean. "
      ::= { webserviceCredentialProviderEntry 3  }
   
   
   webserviceCredentialProviderTokenType OBJECT-TYPE
      SYNTAX      OCTET STRING
      MAX-ACCESS  read-only
      STATUS      current
      DESCRIPTION "Specifies the type of token used for the particular credential provider or token handler.  WebLogic Server supports, by default, three types of tokens: X.509, UsernameToken, and SAML, as specified by the following WS-Security specifications:  Web Services Security: Username Token Profile Web Services Security: X.509 Token Profile Web Services Security: SAML Token Profile  To specify one of these out-of-the-box types, use these values respectively: 'ut', 'x509', or 'saml'.  "
      ::= { webserviceCredentialProviderEntry 4  }
   
   
   webserviceCredentialProviderName OBJECT-TYPE
      SYNTAX      OCTET STRING
      MAX-ACCESS  read-only
      STATUS      current
      DESCRIPTION "The user-specified name of this MBean instance.  This name is included as one of the key properties in the MBean's javax.management.ObjectName:  Name=user-specified-name "
      ::= { webserviceCredentialProviderEntry 5  }
   
   
   webserviceCredentialProviderClassName OBJECT-TYPE
      SYNTAX      OCTET STRING
      MAX-ACCESS  read-only
      STATUS      current
      DESCRIPTION "The fully qualified name of the class that implements a particular credential provider or token handler. "
      ::= { webserviceCredentialProviderEntry 6  }
   
   
   webserviceCredentialProviderTags OBJECT-TYPE
      SYNTAX      OCTET STRING
      MAX-ACCESS  read-only
      STATUS      current
      DESCRIPTION "Return all tags on this Configuration MBean "
      ::= { webserviceCredentialProviderEntry 7  }
   
   
   webserviceSecurityTable OBJECT-TYPE
      SYNTAX      SEQUENCE OF WebserviceSecurityEntry
      MAX-ACCESS  not-accessible
      STATUS      current
      DESCRIPTION "Encapsulates information about a Web Service security configuration. "
      ::= { wls 1175  }
      
   
   webserviceSecurityEntry OBJECT-TYPE
      SYNTAX      WebserviceSecurityEntry
      MAX-ACCESS  not-accessible
      STATUS      current
      DESCRIPTION "Generated SNMP Table Entry."
      INDEX { webserviceSecurityIndex}
      ::= { webserviceSecurityTable 1 }
      
   WebserviceSecurityEntry ::=
      SEQUENCE
      {
         webserviceSecurityIndex OCTET STRING,
         webserviceSecurityObjectName OCTET STRING,
         webserviceSecurityType OCTET STRING,
         webserviceSecurityDefaultCredentialProviderSTSURI OCTET STRING,
         webserviceSecurityName OCTET STRING,
         webserviceSecurityPolicySelectionPreference OCTET STRING,
         webserviceSecurityCompatibilityPreference OCTET STRING,
         webserviceSecurityCompatibilityOrderingPreference OCTET STRING,
         webserviceSecurityTags OCTET STRING
      }
      
   
   webserviceSecurityIndex OBJECT-TYPE
      SYNTAX      OCTET STRING
      MAX-ACCESS  not-accessible
      STATUS      current
      DESCRIPTION "Index column"
      ::= { webserviceSecurityEntry 1  }
   
   
   webserviceSecurityObjectName OBJECT-TYPE
      SYNTAX      OCTET STRING
      MAX-ACCESS  read-only
      STATUS      current
      DESCRIPTION "ObjectName column"
      ::= { webserviceSecurityEntry 2  }
   
   
   webserviceSecurityType OBJECT-TYPE
      SYNTAX      OCTET STRING
      MAX-ACCESS  read-only
      STATUS      current
      DESCRIPTION "Returns the type of the MBean. "
      ::= { webserviceSecurityEntry 3  }
   
   
   webserviceSecurityDefaultCredentialProviderSTSURI OBJECT-TYPE
      SYNTAX      OCTET STRING
      MAX-ACCESS  read-only
      STATUS      current
      DESCRIPTION "Gets the default STS endpoint URL for all WS-Trust enabled credential providers of this Web Service security configuration. "
      ::= { webserviceSecurityEntry 4  }
   
   
   webserviceSecurityName OBJECT-TYPE
      SYNTAX      OCTET STRING
      MAX-ACCESS  read-only
      STATUS      current
      DESCRIPTION "The user-specified name of this MBean instance.  This name is included as one of the key properties in the MBean's javax.management.ObjectName:  Name=user-specified-name "
      ::= { webserviceSecurityEntry 5  }
   
   
   webserviceSecurityPolicySelectionPreference OBJECT-TYPE
      SYNTAX      OCTET STRING
      MAX-ACCESS  read-only
      STATUS      current
      DESCRIPTION "Gets the value of the PolicySelectionPreference attribute.   The preference value can be one of the following:  NONE SCP SPC CSP CPS PCS PSC   Where: S: Security or functionality; C: Compatibility or Interoperability; P: Performance  If NONE is specified, no preference is applied - the first policy alternative is always chosen, and optional policy assertions are ignored. "
      ::= { webserviceSecurityEntry 6  }
   
   
   webserviceSecurityCompatibilityPreference OBJECT-TYPE
      SYNTAX      OCTET STRING
      MAX-ACCESS  read-only
      STATUS      current
      DESCRIPTION "Gets the value of the compatiblityPreference attribute. "
      ::= { webserviceSecurityEntry 7  }
   
   
   webserviceSecurityCompatibilityOrderingPreference OBJECT-TYPE
      SYNTAX      OCTET STRING
      MAX-ACCESS  read-only
      STATUS      current
      DESCRIPTION "Gets the value of the compatiblityOrderingPreference attribute. "
      ::= { webserviceSecurityEntry 8  }
   
   
   webserviceSecurityTags OBJECT-TYPE
      SYNTAX      OCTET STRING
      MAX-ACCESS  read-only
      STATUS      current
      DESCRIPTION "Return all tags on this Configuration MBean "
      ::= { webserviceSecurityEntry 9  }
   
   
   webserviceSecurityTokenTable OBJECT-TYPE
      SYNTAX      SEQUENCE OF WebserviceSecurityTokenEntry
      MAX-ACCESS  not-accessible
      STATUS      current
      DESCRIPTION "Encapsulates information about a particular token that has been configured for a Web Service security configuration. "
      ::= { wls 1180  }
      
   
   webserviceSecurityTokenEntry OBJECT-TYPE
      SYNTAX      WebserviceSecurityTokenEntry
      MAX-ACCESS  not-accessible
      STATUS      current
      DESCRIPTION "Generated SNMP Table Entry."
      INDEX { webserviceSecurityTokenIndex}
      ::= { webserviceSecurityTokenTable 1 }
      
   WebserviceSecurityTokenEntry ::=
      SEQUENCE
      {
         webserviceSecurityTokenIndex OCTET STRING,
         webserviceSecurityTokenObjectName OCTET STRING,
         webserviceSecurityTokenType OCTET STRING,
         webserviceSecurityTokenTokenType OCTET STRING,
         webserviceSecurityTokenName OCTET STRING,
         webserviceSecurityTokenClassName OCTET STRING,
         webserviceSecurityTokenTags OCTET STRING
      }
      
   
   webserviceSecurityTokenIndex OBJECT-TYPE
      SYNTAX      OCTET STRING
      MAX-ACCESS  not-accessible
      STATUS      current
      DESCRIPTION "Index column"
      ::= { webserviceSecurityTokenEntry 1  }
   
   
   webserviceSecurityTokenObjectName OBJECT-TYPE
      SYNTAX      OCTET STRING
      MAX-ACCESS  read-only
      STATUS      current
      DESCRIPTION "ObjectName column"
      ::= { webserviceSecurityTokenEntry 2  }
   
   
   webserviceSecurityTokenType OBJECT-TYPE
      SYNTAX      OCTET STRING
      MAX-ACCESS  read-only
      STATUS      current
      DESCRIPTION "Returns the type of the MBean. "
      ::= { webserviceSecurityTokenEntry 3  }
   
   
   webserviceSecurityTokenTokenType OBJECT-TYPE
      SYNTAX      OCTET STRING
      MAX-ACCESS  read-only
      STATUS      current
      DESCRIPTION "Specifies the type of token used for the particular credential provider or token handler.  WebLogic Server supports, by default, three types of tokens: X.509, UsernameToken, and SAML, as specified by the following WS-Security specifications:  Web Services Security: Username Token Profile Web Services Security: X.509 Token Profile Web Services Security: SAML Token Profile  To specify one of these out-of-the-box types, use these values respectively: 'ut', 'x509', or 'saml'.  "
      ::= { webserviceSecurityTokenEntry 4  }
   
   
   webserviceSecurityTokenName OBJECT-TYPE
      SYNTAX      OCTET STRING
      MAX-ACCESS  read-only
      STATUS      current
      DESCRIPTION "The user-specified name of this MBean instance.  This name is included as one of the key properties in the MBean's javax.management.ObjectName:  Name=user-specified-name "
      ::= { webserviceSecurityTokenEntry 5  }
   
   
   webserviceSecurityTokenClassName OBJECT-TYPE
      SYNTAX      OCTET STRING
      MAX-ACCESS  read-only
      STATUS      current
      DESCRIPTION "The fully qualified name of the class that implements a particular credential provider or token handler. "
      ::= { webserviceSecurityTokenEntry 6  }
   
   
   webserviceSecurityTokenTags OBJECT-TYPE
      SYNTAX      OCTET STRING
      MAX-ACCESS  read-only
      STATUS      current
      DESCRIPTION "Return all tags on this Configuration MBean "
      ::= { webserviceSecurityTokenEntry 7  }
   
   
   webserviceTimestampTable OBJECT-TYPE
      SYNTAX      SEQUENCE OF WebserviceTimestampEntry
      MAX-ACCESS  not-accessible
      STATUS      current
      DESCRIPTION "Encapsulates the timestamp information that is associated with a Web Service security configuration. "
      ::= { wls 1185  }
      
   
   webserviceTimestampEntry OBJECT-TYPE
      SYNTAX      WebserviceTimestampEntry
      MAX-ACCESS  not-accessible
      STATUS      current
      DESCRIPTION "Generated SNMP Table Entry."
      INDEX { webserviceTimestampIndex}
      ::= { webserviceTimestampTable 1 }
      
   WebserviceTimestampEntry ::=
      SEQUENCE
      {
         webserviceTimestampIndex OCTET STRING,
         webserviceTimestampObjectName OCTET STRING,
         webserviceTimestampType OCTET STRING,
         webserviceTimestampMaxProcessingDelay Counter64,
         webserviceTimestampClockSkew Counter64,
         webserviceTimestampClockSynchronized OCTET STRING,
         webserviceTimestampValidityPeriod Integer32,
         webserviceTimestampName OCTET STRING,
         webserviceTimestampTags OCTET STRING
      }
      
   
   webserviceTimestampIndex OBJECT-TYPE
      SYNTAX      OCTET STRING
      MAX-ACCESS  not-accessible
      STATUS      current
      DESCRIPTION "Index column"
      ::= { webserviceTimestampEntry 1  }
   
   
   webserviceTimestampObjectName OBJECT-TYPE
      SYNTAX      OCTET STRING
      MAX-ACCESS  read-only
      STATUS      current
      DESCRIPTION "ObjectName column"
      ::= { webserviceTimestampEntry 2  }
   
   
   webserviceTimestampType OBJECT-TYPE
      SYNTAX      OCTET STRING
      MAX-ACCESS  read-only
      STATUS      current
      DESCRIPTION "Returns the type of the MBean. "
      ::= { webserviceTimestampEntry 3  }
   
   
   webserviceTimestampMaxProcessingDelay OBJECT-TYPE
      SYNTAX      Counter64
      MAX-ACCESS  read-only
      STATUS      current
      DESCRIPTION "Specifies the freshness policy for received messages: the Web Service observes the processing delay by subtracting the Created time in the Timestamp from the current time.  If the observed processing delay is greater than maxProcessingDelay plus clockSkew, then the message is  rejected as stale.  This attribute is specified in milliseconds.  Setting maxProcessingDelay to NO_MAX_PROCESSING_DELAY disables to enforcement of the freshness policy. "
      ::= { webserviceTimestampEntry 4  }
   
   
   webserviceTimestampClockSkew OBJECT-TYPE
      SYNTAX      Counter64
      MAX-ACCESS  read-only
      STATUS      current
      DESCRIPTION "If clocks are synchronized, this attribute describes the accuracy of the synchronization between two clocks: the client and the server.  ClockSkew is expressed in milliseconds. Clock skew is enforced by rendering all times into milliseconds since a common time 0 and using these times for comparisons. For example, if your clocks are accurate to within 1 minute of each other, you would set your skew to 1 minute * 60 seconds * 1000 milliseconds or 60000.  "
      ::= { webserviceTimestampEntry 5  }
   
   
   webserviceTimestampClockSynchronized OBJECT-TYPE
      SYNTAX      OCTET STRING
      MAX-ACCESS  read-only
      STATUS      current
      DESCRIPTION "Specifies whether the Web Service assumes synchronized clocks.  If the clockSynchronized attribute is false, the Web Service rejects all inbound messages with that contain expirations, because this is the only safe way to ensure that the message hasn't already expired. In this case, the Web Service also does not enforce a freshness policy.  If this attribute is set to true, then the Web Service enforces expirations on inbound messages to the best of its ability and enforces an optional freshness policy (via maxProcessingDelay).  The default value of this attribute is true. "
      ::= { webserviceTimestampEntry 6  }
   
   
   webserviceTimestampValidityPeriod OBJECT-TYPE
      SYNTAX      Integer32
      MAX-ACCESS  read-only
      STATUS      current
      DESCRIPTION "Represents the length of time the sender wants the outbound message to be valid.   When the validityPeriod is positive, the TimestampHandler inserts an Expires element into the Timestamp header.   The validityPeriod is expressed in seconds:  the Expires time will be that many seconds ahead of the Timestamp's Created time. "
      ::= { webserviceTimestampEntry 8  }
   
   
   webserviceTimestampName OBJECT-TYPE
      SYNTAX      OCTET STRING
      MAX-ACCESS  read-only
      STATUS      current
      DESCRIPTION "The user-specified name of this MBean instance.  This name is included as one of the key properties in the MBean's javax.management.ObjectName:  Name=user-specified-name "
      ::= { webserviceTimestampEntry 10  }
   
   
   webserviceTimestampTags OBJECT-TYPE
      SYNTAX      OCTET STRING
      MAX-ACCESS  read-only
      STATUS      current
      DESCRIPTION "Return all tags on this Configuration MBean "
      ::= { webserviceTimestampEntry 11  }
   
   
   webserviceTokenHandlerTable OBJECT-TYPE
      SYNTAX      SEQUENCE OF WebserviceTokenHandlerEntry
      MAX-ACCESS  not-accessible
      STATUS      current
      DESCRIPTION "Encapsulates information about a particular token handler that has been configured for a Web Service security configuration. "
      ::= { wls 1190  }
      
   
   webserviceTokenHandlerEntry OBJECT-TYPE
      SYNTAX      WebserviceTokenHandlerEntry
      MAX-ACCESS  not-accessible
      STATUS      current
      DESCRIPTION "Generated SNMP Table Entry."
      INDEX { webserviceTokenHandlerIndex}
      ::= { webserviceTokenHandlerTable 1 }
      
   WebserviceTokenHandlerEntry ::=
      SEQUENCE
      {
         webserviceTokenHandlerIndex OCTET STRING,
         webserviceTokenHandlerObjectName OCTET STRING,
         webserviceTokenHandlerType OCTET STRING,
         webserviceTokenHandlerHandlingOrder Integer32,
         webserviceTokenHandlerTokenType OCTET STRING,
         webserviceTokenHandlerName OCTET STRING,
         webserviceTokenHandlerClassName OCTET STRING,
         webserviceTokenHandlerTags OCTET STRING
      }
      
   
   webserviceTokenHandlerIndex OBJECT-TYPE
      SYNTAX      OCTET STRING
      MAX-ACCESS  not-accessible
      STATUS      current
      DESCRIPTION "Index column"
      ::= { webserviceTokenHandlerEntry 1  }
   
   
   webserviceTokenHandlerObjectName OBJECT-TYPE
      SYNTAX      OCTET STRING
      MAX-ACCESS  read-only
      STATUS      current
      DESCRIPTION "ObjectName column"
      ::= { webserviceTokenHandlerEntry 2  }
   
   
   webserviceTokenHandlerType OBJECT-TYPE
      SYNTAX      OCTET STRING
      MAX-ACCESS  read-only
      STATUS      current
      DESCRIPTION "Returns the type of the MBean. "
      ::= { webserviceTokenHandlerEntry 3  }
   
   
   webserviceTokenHandlerHandlingOrder OBJECT-TYPE
      SYNTAX      Integer32
      MAX-ACCESS  read-only
      STATUS      current
      DESCRIPTION "Specifies the order in which the token handlers execute on a given token.  If you do not specify an order, it is determined by the order in which you added the token handlers.  "
      ::= { webserviceTokenHandlerEntry 4  }
   
   
   webserviceTokenHandlerTokenType OBJECT-TYPE
      SYNTAX      OCTET STRING
      MAX-ACCESS  read-only
      STATUS      current
      DESCRIPTION "Specifies the type of token used for the particular credential provider or token handler.  WebLogic Server supports, by default, three types of tokens: X.509, UsernameToken, and SAML, as specified by the following WS-Security specifications:  Web Services Security: Username Token Profile Web Services Security: X.509 Token Profile Web Services Security: SAML Token Profile  To specify one of these out-of-the-box types, use these values respectively: 'ut', 'x509', or 'saml'.  "
      ::= { webserviceTokenHandlerEntry 5  }
   
   
   webserviceTokenHandlerName OBJECT-TYPE
      SYNTAX      OCTET STRING
      MAX-ACCESS  read-only
      STATUS      current
      DESCRIPTION "The user-specified name of this MBean instance.  This name is included as one of the key properties in the MBean's javax.management.ObjectName:  Name=user-specified-name "
      ::= { webserviceTokenHandlerEntry 6  }
   
   
   webserviceTokenHandlerClassName OBJECT-TYPE
      SYNTAX      OCTET STRING
      MAX-ACCESS  read-only
      STATUS      current
      DESCRIPTION "The fully qualified name of the class that implements a particular credential provider or token handler. "
      ::= { webserviceTokenHandlerEntry 7  }
   
   
   webserviceTokenHandlerTags OBJECT-TYPE
      SYNTAX      OCTET STRING
      MAX-ACCESS  read-only
      STATUS      current
      DESCRIPTION "Return all tags on this Configuration MBean "
      ::= { webserviceTokenHandlerEntry 8  }
   
   
   workManagerTable OBJECT-TYPE
      SYNTAX      SEQUENCE OF WorkManagerEntry
      MAX-ACCESS  not-accessible
      STATUS      current
      DESCRIPTION "Configuration MBean representing WorkManager parameters. A WorkManager configuration can have a RequestClass(FairShare, ResponseTime, ContextBased), MinThreadsConstraint, MaxThreadsConstraint, Capacity and ShutdownTrigger. All these are optional and need to be configured as needed. An empty WorkManager without configuration gets its own default fair share. The default fair share value is 50. "
      ::= { wls 1195  }
      
   
   workManagerEntry OBJECT-TYPE
      SYNTAX      WorkManagerEntry
      MAX-ACCESS  not-accessible
      STATUS      current
      DESCRIPTION "Generated SNMP Table Entry."
      INDEX { workManagerIndex}
      ::= { workManagerTable 1 }
      
   WorkManagerEntry ::=
      SEQUENCE
      {
         workManagerIndex     OCTET STRING,
         workManagerObjectName OCTET STRING,
         workManagerType      OCTET STRING,
         workManagerDeploymentOrder Integer32,
         workManagerIgnoreStuckThreads OCTET STRING,
         workManagerName      OCTET STRING,
         workManagerApplicationScope OCTET STRING,
         workManagerTags      OCTET STRING
      }
      
   
   workManagerIndex OBJECT-TYPE
      SYNTAX      OCTET STRING
      MAX-ACCESS  not-accessible
      STATUS      current
      DESCRIPTION "Index column"
      ::= { workManagerEntry 1  }
   
   
   workManagerObjectName OBJECT-TYPE
      SYNTAX      OCTET STRING
      MAX-ACCESS  read-only
      STATUS      current
      DESCRIPTION "ObjectName column"
      ::= { workManagerEntry 2  }
   
   
   workManagerType OBJECT-TYPE
      SYNTAX      OCTET STRING
      MAX-ACCESS  read-only
      STATUS      current
      DESCRIPTION "Returns the type of the MBean. "
      ::= { workManagerEntry 3  }
   
   
   workManagerDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { workManagerEntry 4  }
   
   
   workManagerIgnoreStuckThreads OBJECT-TYPE
      SYNTAX      OCTET STRING
      MAX-ACCESS  read-only
      STATUS      current
      DESCRIPTION "Specifies whether this Work Manager ignores 'stuck' threads. Typically, stuck threads will cause the associated Work Manager to take some action: either switching the application to Admin mode, shutting down the server, or shutting down the Work Manager. If this flag is set, then no thread in this Work Manager is ever considered stuck.  If you do not explicitly specify IGNORE_STUCK_THREADS=TRUE, the default behavior is that upon encountering stuck threads, the server will take one of the aforementioned actions.  "
      ::= { workManagerEntry 5  }
   
   
   workManagerName OBJECT-TYPE
      SYNTAX      OCTET STRING
      MAX-ACCESS  read-only
      STATUS      current
      DESCRIPTION "The user-specified name of this MBean instance.  This name is included as one of the key properties in the MBean's javax.management.ObjectName:  Name=user-specified-name "
      ::= { workManagerEntry 6  }
   
   
   workManagerApplicationScope OBJECT-TYPE
      SYNTAX      OCTET STRING
      MAX-ACCESS  read-only
      STATUS      current
      DESCRIPTION "Specifies whether this work manager should be scoped to an application. By default, work managers are scoped to an application. Set this value to false if the work manager is to be scoped to a domain "
      ::= { workManagerEntry 7  }
   
   
   workManagerTags OBJECT-TYPE
      SYNTAX      OCTET STRING
      MAX-ACCESS  read-only
      STATUS      current
      DESCRIPTION "Return all tags on this Configuration MBean "
      ::= { workManagerEntry 8  }
   
   
   workManagerShutdownTriggerTable OBJECT-TYPE
      SYNTAX      SEQUENCE OF WorkManagerShutdownTriggerEntry
      MAX-ACCESS  not-accessible
      STATUS      current
      DESCRIPTION "This MBean is used to configure the trigger that shuts down the WorkManager. The trigger specifies the number of threads that need to be stuck for a certain amount of time for the trigger to shutdown the WorkManager automatically. A shutdown WorkManager refuses new work and completes pending work. "
      ::= { wls 1200  }
      
   
   workManagerShutdownTriggerEntry OBJECT-TYPE
      SYNTAX      WorkManagerShutdownTriggerEntry
      MAX-ACCESS  not-accessible
      STATUS      current
      DESCRIPTION "Generated SNMP Table Entry."
      INDEX { workManagerShutdownTriggerIndex}
      ::= { workManagerShutdownTriggerTable 1 }
      
   WorkManagerShutdownTriggerEntry ::=
      SEQUENCE
      {
         workManagerShutdownTriggerIndex OCTET STRING,
         workManagerShutdownTriggerObjectName OCTET STRING,
         workManagerShutdownTriggerType OCTET STRING,
         workManagerShutdownTriggerMaxStuckThreadTime Integer32,
         workManagerShutdownTriggerStuckThreadCount Integer32,
         workManagerShutdownTriggerName OCTET STRING,
         workManagerShutdownTriggerResumeWhenUnstuck OCTET STRING,
         workManagerShutdownTriggerTags OCTET STRING
      }
      
   
   workManagerShutdownTriggerIndex OBJECT-TYPE
      SYNTAX      OCTET STRING
      MAX-ACCESS  not-accessible
      STATUS      current
      DESCRIPTION "Index column"
      ::= { workManagerShutdownTriggerEntry 1  }
   
   
   workManagerShutdownTriggerObjectName OBJECT-TYPE
      SYNTAX      OCTET STRING
      MAX-ACCESS  read-only
      STATUS      current
      DESCRIPTION "ObjectName column"
      ::= { workManagerShutdownTriggerEntry 2  }
   
   
   workManagerShutdownTriggerType OBJECT-TYPE
      SYNTAX      OCTET STRING
      MAX-ACCESS  read-only
      STATUS      current
      DESCRIPTION "Returns the type of the MBean. "
      ::= { workManagerShutdownTriggerEntry 3  }
   
   
   workManagerShutdownTriggerMaxStuckThreadTime OBJECT-TYPE
      SYNTAX      Integer32
      MAX-ACCESS  read-only
      STATUS      current
      DESCRIPTION "Time after which a executing thread is declared as stuck. "
      ::= { workManagerShutdownTriggerEntry 4  }
   
   
   workManagerShutdownTriggerStuckThreadCount OBJECT-TYPE
      SYNTAX      Integer32
      MAX-ACCESS  read-only
      STATUS      current
      DESCRIPTION "Number of stuck threads after which the WorkManager is shutdown "
      ::= { workManagerShutdownTriggerEntry 5  }
   
   
   workManagerShutdownTriggerName OBJECT-TYPE
      SYNTAX      OCTET STRING
      MAX-ACCESS  read-only
      STATUS      current
      DESCRIPTION "The user-specified name of this MBean instance.  This name is included as one of the key properties in the MBean's javax.management.ObjectName:  Name=user-specified-name "
      ::= { workManagerShutdownTriggerEntry 6  }
   
   
   workManagerShutdownTriggerResumeWhenUnstuck OBJECT-TYPE
      SYNTAX      OCTET STRING
      MAX-ACCESS  read-only
      STATUS      current
      DESCRIPTION "Whether to resume work manager once the stuck threads were cleared "
      ::= { workManagerShutdownTriggerEntry 7  }
   
   
   workManagerShutdownTriggerTags OBJECT-TYPE
      SYNTAX      OCTET STRING
      MAX-ACCESS  read-only
      STATUS      current
      DESCRIPTION "Return all tags on this Configuration MBean "
      ::= { workManagerShutdownTriggerEntry 8  }
   
   
   appClientComponentRuntimeTable OBJECT-TYPE
      SYNTAX      SEQUENCE OF AppClientComponentRuntimeEntry
      MAX-ACCESS  not-accessible
      STATUS      current
      DESCRIPTION "This is the ComponentRuntimeMBean for Java EE Application Client Containers. "
      ::= { wls 1205  }
      
   
   appClientComponentRuntimeEntry OBJECT-TYPE
      SYNTAX      AppClientComponentRuntimeEntry
      MAX-ACCESS  not-accessible
      STATUS      current
      DESCRIPTION "Generated SNMP Table Entry."
      INDEX { appClientComponentRuntimeIndex}
      ::= { appClientComponentRuntimeTable 1 }
      
   AppClientComponentRuntimeEntry ::=
      SEQUENCE
      {
         appClientComponentRuntimeIndex OCTET STRING,
         appClientComponentRuntimeObjectName OCTET STRING,
         appClientComponentRuntimeType OCTET STRING,
         appClientComponentRuntimeModuleId OCTET STRING,
         appClientComponentRuntimeDeploymentState Integer32,
         appClientComponentRuntimeName OCTET STRING
      }
      
   
   appClientComponentRuntimeIndex OBJECT-TYPE
      SYNTAX      OCTET STRING
      MAX-ACCESS  not-accessible
      STATUS      current
      DESCRIPTION "Index column"
      ::= { appClientComponentRuntimeEntry 1  }
   
   
   appClientComponentRuntimeObjectName OBJECT-TYPE
      SYNTAX      OCTET STRING
      MAX-ACCESS  read-only
      STATUS      current
      DESCRIPTION "ObjectName column"
      ::= { appClientComponentRuntimeEntry 2  }
   
   
   appClientComponentRuntimeType OBJECT-TYPE
      SYNTAX      OCTET STRING
      MAX-ACCESS  read-only
      STATUS      current
      DESCRIPTION "Returns the type of the MBean. "
      ::= { appClientComponentRuntimeEntry 3  }
   
   
   appClientComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { appClientComponentRuntimeEntry 4  }
   
   
   appClientComponentRuntimeDeploymentState OBJECT-TYPE
      SYNTAX      Integer32
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { appClientComponentRuntimeEntry 5  }
   
   
   appClientComponentRuntimeName OBJECT-TYPE
      SYNTAX      OCTET STRING
      MAX-ACCESS  read-only
      STATUS      current
      DESCRIPTION "The name of this configuration. WebLogic Server uses an MBean to implement and persist the configuration. "
      ::= { appClientComponentRuntimeEntry 6  }
   
   
   appRuntimeStateRuntimeTable OBJECT-TYPE
      SYNTAX      SEQUENCE OF AppRuntimeStateRuntimeEntry
      MAX-ACCESS  not-accessible
      STATUS      current
      DESCRIPTION "Provides access to runtime state for deployed applications. "
      ::= { wls 1210  }
      
   
   appRuntimeStateRuntimeEntry OBJECT-TYPE
      SYNTAX      AppRuntimeStateRuntimeEntry
      MAX-ACCESS  not-accessible
      STATUS      current
      DESCRIPTION "Generated SNMP Table Entry."
      INDEX { appRuntimeStateRuntimeIndex}
      ::= { appRuntimeStateRuntimeTable 1 }
      
   AppRuntimeStateRuntimeEntry ::=
      SEQUENCE
      {
         appRuntimeStateRuntimeIndex OCTET STRING,
         appRuntimeStateRuntimeObjectName OCTET STRING,
         appRuntimeStateRuntimeType OCTET STRING,
         appRuntimeStateRuntimeName OCTET STRING,
         appRuntimeStateRuntimeApplicationIds OCTET STRING
      }
      
   
   appRuntimeStateRuntimeIndex OBJECT-TYPE
      SYNTAX      OCTET STRING
      MAX-ACCESS  not-accessible
      STATUS      current
      DESCRIPTION "Index column"
      ::= { appRuntimeStateRuntimeEntry 1  }
   
   
   appRuntimeStateRuntimeObjectName OBJECT-TYPE
      SYNTAX      OCTET STRING
      MAX-ACCESS  read-only
      STATUS      current
      DESCRIPTION "ObjectName column"
      ::= { appRuntimeStateRuntimeEntry 2  }
   
   
   appRuntimeStateRuntimeType OBJECT-TYPE
      SYNTAX      OCTET STRING
      MAX-ACCESS  read-only
      STATUS      current
      DESCRIPTION "Returns the type of the MBean. "
      ::= { appRuntimeStateRuntimeEntry 3  }
   
   
   appRuntimeStateRuntimeName OBJECT-TYPE
      SYNTAX      OCTET STRING
      MAX-ACCESS  read-only
      STATUS      current
      DESCRIPTION "The name of this configuration. WebLogic Server uses an MBean to implement and persist the configuration. "
      ::= { appRuntimeStateRuntimeEntry 4  }
   
   
   appRuntimeStateRuntimeApplicationIds OBJECT-TYPE
      SYNTAX      OCTET STRING
      MAX-ACCESS  read-only
      STATUS      current
      DESCRIPTION " "
      ::= { appRuntimeStateRuntimeEntry 5  }
   
   
   entityEJBRuntimeTable OBJECT-TYPE
      SYNTAX      SEQUENCE OF EntityEJBRuntimeEntry
      MAX-ACCESS  not-accessible
      STATUS      current
      DESCRIPTION "This interface contains accessor methods for all EJB runtime information collected for an Entity Bean. "
      ::= { wls 1220  }
      
   
   entityEJBRuntimeEntry OBJECT-TYPE
      SYNTAX      EntityEJBRuntimeEntry
      MAX-ACCESS  not-accessible
      STATUS      current
      DESCRIPTION "Generated SNMP Table Entry."
      INDEX { entityEJBRuntimeIndex}
      ::= { entityEJBRuntimeTable 1 }
      
   EntityEJBRuntimeEntry ::=
      SEQUENCE
      {
         entityEJBRuntimeIndex OCTET STRING,
         entityEJBRuntimeObjectName OCTET STRING,
         entityEJBRuntimeType OCTET STRING,
         entityEJBRuntimeEJBName OCTET STRING,
         entityEJBRuntimeName OCTET STRING
      }
      
   
   entityEJBRuntimeIndex OBJECT-TYPE
      SYNTAX      OCTET STRING
      MAX-ACCESS  not-accessible
      STATUS      current
      DESCRIPTION "Index column"
      ::= { entityEJBRuntimeEntry 1  }
   
   
   entityEJBRuntimeObjectName OBJECT-TYPE
      SYNTAX      OCTET STRING
      MAX-ACCESS  read-only
      STATUS      current
      DESCRIPTION "ObjectName column"
      ::= { entityEJBRuntimeEntry 2  }
   
   
   entityEJBRuntimeType OBJECT-TYPE
      SYNTAX      OCTET STRING
      MAX-ACCESS  read-only
      STATUS      current
      DESCRIPTION "Returns the type of the MBean. "
      ::= { entityEJBRuntimeEntry 3  }
   
   
   entityEJBRuntimeEJBName OBJECT-TYPE
      SYNTAX      OCTET STRING
      MAX-ACCESS  read-only
      STATUS      current
      DESCRIPTION "Provides the name for this EJB as defined in the javax.ejb.EJB annotation, or the ejb-name when * using the ejb-jar.xml deployment descriptor. "
      ::= { entityEJBRuntimeEntry 4  }
   
   
   entityEJBRuntimeName OBJECT-TYPE
      SYNTAX      OCTET STRING
      MAX-ACCESS  read-only
      STATUS      current
      DESCRIPTION "The name of this configuration. WebLogic Server uses an MBean to implement and persist the configuration. "
      ::= { entityEJBRuntimeEntry 5  }
   
   
   jdbcDataSourceTaskRuntimeTable OBJECT-TYPE
      SYNTAX      SEQUENCE OF JdbcDataSourceTaskRuntimeEntry
      MAX-ACCESS  not-accessible
      STATUS      current
      DESCRIPTION " "
      ::= { wls 1225  }
      
   
   jdbcDataSourceTaskRuntimeEntry OBJECT-TYPE
      SYNTAX      JdbcDataSourceTaskRuntimeEntry
      MAX-ACCESS  not-accessible
      STATUS      current
      DESCRIPTION "Generated SNMP Table Entry."
      INDEX { jdbcDataSourceTaskRuntimeIndex}
      ::= { jdbcDataSourceTaskRuntimeTable 1 }
      
   JdbcDataSourceTaskRuntimeEntry ::=
      SEQUENCE
      {
         jdbcDataSourceTaskRuntimeIndex OCTET STRING,
         jdbcDataSourceTaskRuntimeObjectName OCTET STRING,
         jdbcDataSourceTaskRuntimeType OCTET STRING,
         jdbcDataSourceTaskRuntimeStatus OCTET STRING,
         jdbcDataSourceTaskRuntimeRunning OCTET STRING,
         jdbcDataSourceTaskRuntimeBeginTime Counter64,
         jdbcDataSourceTaskRuntimeEndTime Counter64,
         jdbcDataSourceTaskRuntimeSystemTask OCTET STRING,
         jdbcDataSourceTaskRuntimeDescription OCTET STRING,
         jdbcDataSourceTaskRuntimeName OCTET STRING,
         jdbcDataSourceTaskRuntimeProgress OCTET STRING
      }
      
   
   jdbcDataSourceTaskRuntimeIndex OBJECT-TYPE
      SYNTAX      OCTET STRING
      MAX-ACCESS  not-accessible
      STATUS      current
      DESCRIPTION "Index column"
      ::= { jdbcDataSourceTaskRuntimeEntry 1  }
   
   
   jdbcDataSourceTaskRuntimeObjectName OBJECT-TYPE
      SYNTAX      OCTET STRING
      MAX-ACCESS  read-only
      STATUS      current
      DESCRIPTION "ObjectName column"
      ::= { jdbcDataSourceTaskRuntimeEntry 2  }
   
   
   jdbcDataSourceTaskRuntimeType OBJECT-TYPE
      SYNTAX      OCTET STRING
      MAX-ACCESS  read-only
      STATUS      current
      DESCRIPTION "Returns the type of the MBean. "
      ::= { jdbcDataSourceTaskRuntimeEntry 3  }
   
   
   jdbcDataSourceTaskRuntimeStatus OBJECT-TYPE
      SYNTAX      OCTET STRING
      MAX-ACCESS  read-only
      STATUS      current
      DESCRIPTION "The status of this task. "
      ::= { jdbcDataSourceTaskRuntimeEntry 4  }
   
   
   jdbcDataSourceTaskRuntimeRunning OBJECT-TYPE
      SYNTAX      OCTET STRING
      MAX-ACCESS  read-only
      STATUS      current
      DESCRIPTION "Indicates whether the task is still running. "
      ::= { jdbcDataSourceTaskRuntimeEntry 5  }
   
   
   jdbcDataSourceTaskRuntimeBeginTime OBJECT-TYPE
      SYNTAX      Counter64
      MAX-ACCESS  read-only
      STATUS      current
      DESCRIPTION "The time at which this task was started. "
      ::= { jdbcDataSourceTaskRuntimeEntry 6  }
   
   
   jdbcDataSourceTaskRuntimeEndTime OBJECT-TYPE
      SYNTAX      Counter64
      MAX-ACCESS  read-only
      STATUS      current
      DESCRIPTION "The time at which this task was completed.  A value of -1 indicates that the task is currently running. "
      ::= { jdbcDataSourceTaskRuntimeEntry 7  }
   
   
   jdbcDataSourceTaskRuntimeSystemTask OBJECT-TYPE
      SYNTAX      OCTET STRING
      MAX-ACCESS  read-only
      STATUS      current
      DESCRIPTION "Indicates whether this task was initiated by the server versus a user. "
      ::= { jdbcDataSourceTaskRuntimeEntry 8  }
   
   
   jdbcDataSourceTaskRuntimeDescription OBJECT-TYPE
      SYNTAX      OCTET STRING
      MAX-ACCESS  read-only
      STATUS      current
      DESCRIPTION "A description of this task. "
      ::= { jdbcDataSourceTaskRuntimeEntry 9  }
   
   
   jdbcDataSourceTaskRuntimeName OBJECT-TYPE
      SYNTAX      OCTET STRING
      MAX-ACCESS  read-only
      STATUS      current
      DESCRIPTION "The name of this configuration. WebLogic Server uses an MBean to implement and persist the configuration. "
      ::= { jdbcDataSourceTaskRuntimeEntry 10  }
   
   
   jdbcDataSourceTaskRuntimeProgress OBJECT-TYPE
      SYNTAX      OCTET STRING
      MAX-ACCESS  read-only
      STATUS      current
      DESCRIPTION "The progress of this task. "
      ::= { jdbcDataSourceTaskRuntimeEntry 11  }
   
   
   jdbcDriverRuntimeTable OBJECT-TYPE
      SYNTAX      SEQUENCE OF JdbcDriverRuntimeEntry
      MAX-ACCESS  not-accessible
      STATUS      current
      DESCRIPTION "This class maps to a JDBCDriver JMO "
      ::= { wls 1230  }
      
   
   jdbcDriverRuntimeEntry OBJECT-TYPE
      SYNTAX      JdbcDriverRuntimeEntry
      MAX-ACCESS  not-accessible
      STATUS      current
      DESCRIPTION "Generated SNMP Table Entry."
      INDEX { jdbcDriverRuntimeIndex}
      ::= { jdbcDriverRuntimeTable 1 }
      
   JdbcDriverRuntimeEntry ::=
      SEQUENCE
      {
         jdbcDriverRuntimeIndex OCTET STRING,
         jdbcDriverRuntimeObjectName OCTET STRING,
         jdbcDriverRuntimeType OCTET STRING,
         jdbcDriverRuntimeName OCTET STRING
      }
      
   
   jdbcDriverRuntimeIndex OBJECT-TYPE
      SYNTAX      OCTET STRING
      MAX-ACCESS  not-accessible
      STATUS      current
      DESCRIPTION "Index column"
      ::= { jdbcDriverRuntimeEntry 1  }
   
   
   jdbcDriverRuntimeObjectName OBJECT-TYPE
      SYNTAX      OCTET STRING
      MAX-ACCESS  read-only
      STATUS      current
      DESCRIPTION "ObjectName column"
      ::= { jdbcDriverRuntimeEntry 2  }
   
   
   jdbcDriverRuntimeType OBJECT-TYPE
      SYNTAX      OCTET STRING
      MAX-ACCESS  read-only
      STATUS      current
      DESCRIPTION "Returns the type of the MBean. "
      ::= { jdbcDriverRuntimeEntry 3  }
   
   
   jdbcDriverRuntimeName OBJECT-TYPE
      SYNTAX      OCTET STRING
      MAX-ACCESS  read-only
      STATUS      current
      DESCRIPTION "The name of this configuration. WebLogic Server uses an MBean to implement and persist the configuration. "
      ::= { jdbcDriverRuntimeEntry 4  }
   
   
   jdbcServiceRuntimeTable OBJECT-TYPE
      SYNTAX      SEQUENCE OF JdbcServiceRuntimeEntry
      MAX-ACCESS  not-accessible
      STATUS      current
      DESCRIPTION "This class is used for monitoring a WebLogic JDBC service. It maps to a JDBCResource JMO. "
      ::= { wls 1240  }
      
   
   jdbcServiceRuntimeEntry OBJECT-TYPE
      SYNTAX      JdbcServiceRuntimeEntry
      MAX-ACCESS  not-accessible
      STATUS      current
      DESCRIPTION "Generated SNMP Table Entry."
      INDEX { jdbcServiceRuntimeIndex}
      ::= { jdbcServiceRuntimeTable 1 }
      
   JdbcServiceRuntimeEntry ::=
      SEQUENCE
      {
         jdbcServiceRuntimeIndex OCTET STRING,
         jdbcServiceRuntimeObjectName OCTET STRING,
         jdbcServiceRuntimeType OCTET STRING,
         jdbcServiceRuntimeName OCTET STRING,
         jdbcServiceRuntimeHealthState OCTET STRING
      }
      
   
   jdbcServiceRuntimeIndex OBJECT-TYPE
      SYNTAX      OCTET STRING
      MAX-ACCESS  not-accessible
      STATUS      current
      DESCRIPTION "Index column"
      ::= { jdbcServiceRuntimeEntry 1  }
   
   
   jdbcServiceRuntimeObjectName OBJECT-TYPE
      SYNTAX      OCTET STRING
      MAX-ACCESS  read-only
      STATUS      current
      DESCRIPTION "ObjectName column"
      ::= { jdbcServiceRuntimeEntry 2  }
   
   
   jdbcServiceRuntimeType OBJECT-TYPE
      SYNTAX      OCTET STRING
      MAX-ACCESS  read-only
      STATUS      current
      DESCRIPTION "Returns the type of the MBean. "
      ::= { jdbcServiceRuntimeEntry 3  }
   
   
   jdbcServiceRuntimeName OBJECT-TYPE
      SYNTAX      OCTET STRING
      MAX-ACCESS  read-only
      STATUS      current
      DESCRIPTION "The name of this configuration. WebLogic Server uses an MBean to implement and persist the configuration. "
      ::= { jdbcServiceRuntimeEntry 4  }
   
   
   jdbcServiceRuntimeHealthState OBJECT-TYPE
      SYNTAX      OCTET STRING
      MAX-ACCESS  read-only
      STATUS      current
      DESCRIPTION "The health state of the JDBC subsystem. "
      ::= { jdbcServiceRuntimeEntry 5  }
   
   
   jmsRemoteEndpointRuntimeTable OBJECT-TYPE
      SYNTAX      SEQUENCE OF JmsRemoteEndpointRuntimeEntry
      MAX-ACCESS  not-accessible
      STATUS      current
      DESCRIPTION "This class is used for monitoring a WebLogic SAF remote endpoint for a JMS imported destination. "
      ::= { wls 1245  }
      
   
   jmsRemoteEndpointRuntimeEntry OBJECT-TYPE
      SYNTAX      JmsRemoteEndpointRuntimeEntry
      MAX-ACCESS  not-accessible
      STATUS      current
      DESCRIPTION "Generated SNMP Table Entry."
      INDEX { jmsRemoteEndpointRuntimeIndex}
      ::= { jmsRemoteEndpointRuntimeTable 1 }
      
   JmsRemoteEndpointRuntimeEntry ::=
      SEQUENCE
      {
         jmsRemoteEndpointRuntimeIndex OCTET STRING,
         jmsRemoteEndpointRuntimeObjectName OCTET STRING,
         jmsRemoteEndpointRuntimeType OCTET STRING,
         jmsRemoteEndpointRuntimeUptimeTotal Counter64,
         jmsRemoteEndpointRuntimeMessagesCurrentCount Counter64,
         jmsRemoteEndpointRuntimeDowntimeTotal Counter64,
         jmsRemoteEndpointRuntimeBytesReceivedCount Counter64,
         jmsRemoteEndpointRuntimeEndpointType OCTET STRING,
         jmsRemoteEndpointRuntimeFailedMessagesTotal Counter64,
         jmsRemoteEndpointRuntimeMessagesReceivedCount Counter64,
         jmsRemoteEndpointRuntimeURL OCTET STRING,
         jmsRemoteEndpointRuntimePausedForIncoming OCTET STRING,
         jmsRemoteEndpointRuntimeName OCTET STRING,
         jmsRemoteEndpointRuntimeBytesHighCount Counter64,
         jmsRemoteEndpointRuntimeUptimeHigh Counter64,
         jmsRemoteEndpointRuntimeBytesCurrentCount Counter64,
         jmsRemoteEndpointRuntimeMessagesPendingCount Counter64,
         jmsRemoteEndpointRuntimeDowntimeHigh Counter64,
         jmsRemoteEndpointRuntimeBytesThresholdTime Counter64,
         jmsRemoteEndpointRuntimeBytesPendingCount Counter64,
         jmsRemoteEndpointRuntimePausedForForwarding OCTET STRING,
         jmsRemoteEndpointRuntimeMessagesThresholdTime Counter64,
         jmsRemoteEndpointRuntimeMessagesHighCount Counter64,
         jmsRemoteEndpointRuntimeOperationState OCTET STRING,
         jmsRemoteEndpointRuntimeLastTimeFailedToConnect OCTET STRING,
         jmsRemoteEndpointRuntimeLastTimeConnected OCTET STRING
      }
      
   
   jmsRemoteEndpointRuntimeIndex OBJECT-TYPE
      SYNTAX      OCTET STRING
      MAX-ACCESS  not-accessible
      STATUS      current
      DESCRIPTION "Index column"
      ::= { jmsRemoteEndpointRuntimeEntry 1  }
   
   
   jmsRemoteEndpointRuntimeObjectName OBJECT-TYPE
      SYNTAX      OCTET STRING
      MAX-ACCESS  read-only
      STATUS      current
      DESCRIPTION "ObjectName column"
      ::= { jmsRemoteEndpointRuntimeEntry 2  }
   
   
   jmsRemoteEndpointRuntimeType OBJECT-TYPE
      SYNTAX      OCTET STRING
      MAX-ACCESS  read-only
      STATUS      current
      DESCRIPTION "Returns the type of the MBean. "
      ::= { jmsRemoteEndpointRuntimeEntry 3  }
   
   
   jmsRemoteEndpointRuntimeUptimeTotal OBJECT-TYPE
      SYNTAX      Counter64
      MAX-ACCESS  read-only
      STATUS      current
      DESCRIPTION "Specifies the total time, in seconds, that the remote endpoint has been available since the last reset. "
      ::= { jmsRemoteEndpointRuntimeEntry 4  }
   
   
   jmsRemoteEndpointRuntimeMessagesCurrentCount OBJECT-TYPE
      SYNTAX      Counter64
      MAX-ACCESS  read-only
      STATUS      current
      DESCRIPTION "Returns the current number of messages. This number includes the pending messages. "
      ::= { jmsRemoteEndpointRuntimeEntry 5  }
   
   
   jmsRemoteEndpointRuntimeDowntimeTotal OBJECT-TYPE
      SYNTAX      Counter64
      MAX-ACCESS  read-only
      STATUS      current
      DESCRIPTION "Specifies the total time, in seconds, that the remote endpoint has not been available since the last reset. "
      ::= { jmsRemoteEndpointRuntimeEntry 6  }
   
   
   jmsRemoteEndpointRuntimeBytesReceivedCount OBJECT-TYPE
      SYNTAX      Counter64
      MAX-ACCESS  read-only
      STATUS      current
      DESCRIPTION "The number of bytes received since the last reset. "
      ::= { jmsRemoteEndpointRuntimeEntry 7  }
   
   
   jmsRemoteEndpointRuntimeEndpointType OBJECT-TYPE
      SYNTAX      OCTET STRING
      MAX-ACCESS  read-only
      STATUS      current
      DESCRIPTION "Specifies if the remote endpoint is a JMS or Web Services (WSRM) destination. The possible values are: weblogic.management.runtime.SAFConstants.JMS_ENDPOINT or weblogic.management.runtime.SAFConstants.WS_ENDPOINT. "
      ::= { jmsRemoteEndpointRuntimeEntry 8  }
   
   
   jmsRemoteEndpointRuntimeFailedMessagesTotal OBJECT-TYPE
      SYNTAX      Counter64
      MAX-ACCESS  read-only
      STATUS      current
      DESCRIPTION "Returns the total number of messages that have failed to be forwarded since the last reset. "
      ::= { jmsRemoteEndpointRuntimeEntry 9  }
   
   
   jmsRemoteEndpointRuntimeMessagesReceivedCount OBJECT-TYPE
      SYNTAX      Counter64
      MAX-ACCESS  read-only
      STATUS      current
      DESCRIPTION "The number of messages received since the last reset. "
      ::= { jmsRemoteEndpointRuntimeEntry 10  }
   
   
   jmsRemoteEndpointRuntimeURL OBJECT-TYPE
      SYNTAX      OCTET STRING
      MAX-ACCESS  read-only
      STATUS      current
      DESCRIPTION "The URL of the remote endpoint. "
      ::= { jmsRemoteEndpointRuntimeEntry 11  }
   
   
   jmsRemoteEndpointRuntimePausedForIncoming OBJECT-TYPE
      SYNTAX      OCTET STRING
      MAX-ACCESS  read-only
      STATUS      current
      DESCRIPTION "Indicates if a remote endpoint is currently not accepting new messages. "
      ::= { jmsRemoteEndpointRuntimeEntry 12  }
   
   
   jmsRemoteEndpointRuntimeName OBJECT-TYPE
      SYNTAX      OCTET STRING
      MAX-ACCESS  read-only
      STATUS      current
      DESCRIPTION "The name of this configuration. WebLogic Server uses an MBean to implement and persist the configuration. "
      ::= { jmsRemoteEndpointRuntimeEntry 13  }
   
   
   jmsRemoteEndpointRuntimeBytesHighCount OBJECT-TYPE
      SYNTAX      Counter64
      MAX-ACCESS  read-only
      STATUS      current
      DESCRIPTION "Returns the peak number of bytes since the last reset. "
      ::= { jmsRemoteEndpointRuntimeEntry 14  }
   
   
   jmsRemoteEndpointRuntimeUptimeHigh OBJECT-TYPE
      SYNTAX      Counter64
      MAX-ACCESS  read-only
      STATUS      current
      DESCRIPTION "Specifies the longest time, in seconds, that the remote endpoint has been available since the last reset. "
      ::= { jmsRemoteEndpointRuntimeEntry 15  }
   
   
   jmsRemoteEndpointRuntimeBytesCurrentCount OBJECT-TYPE
      SYNTAX      Counter64
      MAX-ACCESS  read-only
      STATUS      current
      DESCRIPTION "Returns the current number of bytes. This number does not include the pending bytes. "
      ::= { jmsRemoteEndpointRuntimeEntry 16  }
   
   
   jmsRemoteEndpointRuntimeMessagesPendingCount OBJECT-TYPE
      SYNTAX      Counter64
      MAX-ACCESS  read-only
      STATUS      current
      DESCRIPTION "Returns the number of pending messages. Pending messages are over and above the current number of messages. A pending message is one that has either been sent in a transaction and not committed, or been forwarded but has not been acknowledged. "
      ::= { jmsRemoteEndpointRuntimeEntry 17  }
   
   
   jmsRemoteEndpointRuntimeDowntimeHigh OBJECT-TYPE
      SYNTAX      Counter64
      MAX-ACCESS  read-only
      STATUS      current
      DESCRIPTION "Specifies the longest time, in seconds, that the remote endpoint has not been available since the last reset. "
      ::= { jmsRemoteEndpointRuntimeEntry 18  }
   
   
   jmsRemoteEndpointRuntimeBytesThresholdTime OBJECT-TYPE
      SYNTAX      Counter64
      MAX-ACCESS  read-only
      STATUS      current
      DESCRIPTION "Returns the amount of time in the threshold condition since the last reset. "
      ::= { jmsRemoteEndpointRuntimeEntry 19  }
   
   
   jmsRemoteEndpointRuntimeBytesPendingCount OBJECT-TYPE
      SYNTAX      Counter64
      MAX-ACCESS  read-only
      STATUS      current
      DESCRIPTION "Returns the number of pending bytes. Pending bytes are over and above the current number of bytes. "
      ::= { jmsRemoteEndpointRuntimeEntry 20  }
   
   
   jmsRemoteEndpointRuntimePausedForForwarding OBJECT-TYPE
      SYNTAX      OCTET STRING
      MAX-ACCESS  read-only
      STATUS      current
      DESCRIPTION "Indicates if the remote endpoint is currently not forwarding messages. "
      ::= { jmsRemoteEndpointRuntimeEntry 21  }
   
   
   jmsRemoteEndpointRuntimeMessagesThresholdTime OBJECT-TYPE
      SYNTAX      Counter64
      MAX-ACCESS  read-only
      STATUS      current
      DESCRIPTION "Returns the amount of time in the threshold condition since the last reset. "
      ::= { jmsRemoteEndpointRuntimeEntry 22  }
   
   
   jmsRemoteEndpointRuntimeMessagesHighCount OBJECT-TYPE
      SYNTAX      Counter64
      MAX-ACCESS  read-only
      STATUS      current
      DESCRIPTION "Returns the peak number of messages since the last reset. "
      ::= { jmsRemoteEndpointRuntimeEntry 23  }
   
   
   jmsRemoteEndpointRuntimeOperationState OBJECT-TYPE
      SYNTAX      OCTET STRING
      MAX-ACCESS  read-only
      STATUS      current
      DESCRIPTION "Specifies the state of the most recent ExireAll operation. "
      ::= { jmsRemoteEndpointRuntimeEntry 24  }
   
   
   jmsRemoteEndpointRuntimeLastTimeFailedToConnect OBJECT-TYPE
      SYNTAX      OCTET STRING
      MAX-ACCESS  read-only
      STATUS      current
      DESCRIPTION "Specifies the last time that the remote endpoint failed to be connected. "
      ::= { jmsRemoteEndpointRuntimeEntry 25  }
   
   
   jmsRemoteEndpointRuntimeLastTimeConnected OBJECT-TYPE
      SYNTAX      OCTET STRING
      MAX-ACCESS  read-only
      STATUS      current
      DESCRIPTION "Specifies the last time that the remote endpoint was connected. "
      ::= { jmsRemoteEndpointRuntimeEntry 26  }
   
   
   jobRuntimeTable OBJECT-TYPE
      SYNTAX      SEQUENCE OF JobRuntimeEntry
      MAX-ACCESS  not-accessible
      STATUS      current
      DESCRIPTION "RuntimeMBean that provides information about a particular job. "
      ::= { wls 1250  }
      
   
   jobRuntimeEntry OBJECT-TYPE
      SYNTAX      JobRuntimeEntry
      MAX-ACCESS  not-accessible
      STATUS      current
      DESCRIPTION "Generated SNMP Table Entry."
      INDEX { jobRuntimeIndex}
      ::= { jobRuntimeTable 1 }
      
   JobRuntimeEntry ::=
      SEQUENCE
      {
         jobRuntimeIndex      OCTET STRING,
         jobRuntimeObjectName OCTET STRING,
         jobRuntimeType       OCTET STRING,
         jobRuntimeTimeout    Counter64,
         jobRuntimeLocalExecutionCount Counter64,
         jobRuntimeLastLocalExecutionTime Counter64,
         jobRuntimePeriod     Counter64,
         jobRuntimeDescription OCTET STRING,
         jobRuntimeName       OCTET STRING,
         jobRuntimeID         OCTET STRING,
         jobRuntimeState      OCTET STRING
      }
      
   
   jobRuntimeIndex OBJECT-TYPE
      SYNTAX      OCTET STRING
      MAX-ACCESS  not-accessible
      STATUS      current
      DESCRIPTION "Index column"
      ::= { jobRuntimeEntry 1  }
   
   
   jobRuntimeObjectName OBJECT-TYPE
      SYNTAX      OCTET STRING
      MAX-ACCESS  read-only
      STATUS      current
      DESCRIPTION "ObjectName column"
      ::= { jobRuntimeEntry 2  }
   
   
   jobRuntimeType OBJECT-TYPE
      SYNTAX      OCTET STRING
      MAX-ACCESS  read-only
      STATUS      current
      DESCRIPTION "Returns the type of the MBean. "
      ::= { jobRuntimeEntry 3  }
   
   
   jobRuntimeTimeout OBJECT-TYPE
      SYNTAX      Counter64
      MAX-ACCESS  read-only
      STATUS      current
      DESCRIPTION "Returns when the job will be executed next "
      ::= { jobRuntimeEntry 4  }
   
   
   jobRuntimeLocalExecutionCount OBJECT-TYPE
      SYNTAX      Counter64
      MAX-ACCESS  read-only
      STATUS      current
      DESCRIPTION "Returns the number of times this job was executed locally. Job executions are load-balanced across the cluster. This count specifies the number of executions of the job in the local server. "
      ::= { jobRuntimeEntry 5  }
   
   
   jobRuntimeLastLocalExecutionTime OBJECT-TYPE
      SYNTAX      Counter64
      MAX-ACCESS  read-only
      STATUS      current
      DESCRIPTION "Returns the most recent execution time of this job in the local server. Note that multiple executions of the same job are load-balanced across the cluster and this time indicates when the job was last executed locally. "
      ::= { jobRuntimeEntry 6  }
   
   
   jobRuntimePeriod OBJECT-TYPE
      SYNTAX      Counter64
      MAX-ACCESS  read-only
      STATUS      current
      DESCRIPTION "Returns the specified periodicity of this job "
      ::= { jobRuntimeEntry 7  }
   
   
   jobRuntimeDescription OBJECT-TYPE
      SYNTAX      OCTET STRING
      MAX-ACCESS  read-only
      STATUS      current
      DESCRIPTION "Get the description of the submitted commonj.timers.TimerListener. Returns commonj.timers.TimerListener#toString. "
      ::= { jobRuntimeEntry 8  }
   
   
   jobRuntimeName OBJECT-TYPE
      SYNTAX      OCTET STRING
      MAX-ACCESS  read-only
      STATUS      current
      DESCRIPTION "The name of this configuration. WebLogic Server uses an MBean to implement and persist the configuration. "
      ::= { jobRuntimeEntry 9  }
   
   
   jobRuntimeID OBJECT-TYPE
      SYNTAX      OCTET STRING
      MAX-ACCESS  read-only
      STATUS      current
      DESCRIPTION "The unique ID corresponding to this job "
      ::= { jobRuntimeEntry 10  }
   
   
   jobRuntimeState OBJECT-TYPE
      SYNTAX      OCTET STRING
      MAX-ACCESS  read-only
      STATUS      current
      DESCRIPTION "Returns the state of the task. A Job is either in running state or in cancelled state "
      ::= { jobRuntimeEntry 11  }
   
   
   jobSchedulerRuntimeTable OBJECT-TYPE
      SYNTAX      SEQUENCE OF JobSchedulerRuntimeEntry
      MAX-ACCESS  not-accessible
      STATUS      current
      DESCRIPTION "RuntimeMBean that provides information about jobs scheduled with the Job Scheduler. "
      ::= { wls 1255  }
      
   
   jobSchedulerRuntimeEntry OBJECT-TYPE
      SYNTAX      JobSchedulerRuntimeEntry
      MAX-ACCESS  not-accessible
      STATUS      current
      DESCRIPTION "Generated SNMP Table Entry."
      INDEX { jobSchedulerRuntimeIndex}
      ::= { jobSchedulerRuntimeTable 1 }
      
   JobSchedulerRuntimeEntry ::=
      SEQUENCE
      {
         jobSchedulerRuntimeIndex OCTET STRING,
         jobSchedulerRuntimeObjectName OCTET STRING,
         jobSchedulerRuntimeType OCTET STRING,
         jobSchedulerRuntimeName OCTET STRING
      }
      
   
   jobSchedulerRuntimeIndex OBJECT-TYPE
      SYNTAX      OCTET STRING
      MAX-ACCESS  not-accessible
      STATUS      current
      DESCRIPTION "Index column"
      ::= { jobSchedulerRuntimeEntry 1  }
   
   
   jobSchedulerRuntimeObjectName OBJECT-TYPE
      SYNTAX      OCTET STRING
      MAX-ACCESS  read-only
      STATUS      current
      DESCRIPTION "ObjectName column"
      ::= { jobSchedulerRuntimeEntry 2  }
   
   
   jobSchedulerRuntimeType OBJECT-TYPE
      SYNTAX      OCTET STRING
      MAX-ACCESS  read-only
      STATUS      current
      DESCRIPTION "Returns the type of the MBean. "
      ::= { jobSchedulerRuntimeEntry 3  }
   
   
   jobSchedulerRuntimeName OBJECT-TYPE
      SYNTAX      OCTET STRING
      MAX-ACCESS  read-only
      STATUS      current
      DESCRIPTION "The name of this configuration. WebLogic Server uses an MBean to implement and persist the configuration. "
      ::= { jobSchedulerRuntimeEntry 4  }
   
   
   kodoDataCacheRuntimeTable OBJECT-TYPE
      SYNTAX      SEQUENCE OF KodoDataCacheRuntimeEntry
      MAX-ACCESS  not-accessible
      STATUS      current
      DESCRIPTION "Base class for all runtime mbeans that provide status of running modules. "
      ::= { wls 1260  }
      
   
   kodoDataCacheRuntimeEntry OBJECT-TYPE
      SYNTAX      KodoDataCacheRuntimeEntry
      MAX-ACCESS  not-accessible
      STATUS      current
      DESCRIPTION "Generated SNMP Table Entry."
      INDEX { kodoDataCacheRuntimeIndex}
      ::= { kodoDataCacheRuntimeTable 1 }
      
   KodoDataCacheRuntimeEntry ::=
      SEQUENCE
      {
         kodoDataCacheRuntimeIndex OCTET STRING,
         kodoDataCacheRuntimeObjectName OCTET STRING,
         kodoDataCacheRuntimeType OCTET STRING,
         kodoDataCacheRuntimeCacheHitCount Integer32,
         kodoDataCacheRuntimeTotalCurrentEntries Integer32,
         kodoDataCacheRuntimeCacheMissCount Integer32,
         kodoDataCacheRuntimeCacheHitRatio OCTET STRING,
         kodoDataCacheRuntimeName OCTET STRING,
         kodoDataCacheRuntimeStatistics OCTET STRING
      }
      
   
   kodoDataCacheRuntimeIndex OBJECT-TYPE
      SYNTAX      OCTET STRING
      MAX-ACCESS  not-accessible
      STATUS      current
      DESCRIPTION "Index column"
      ::= { kodoDataCacheRuntimeEntry 1  }
   
   
   kodoDataCacheRuntimeObjectName OBJECT-TYPE
      SYNTAX      OCTET STRING
      MAX-ACCESS  read-only
      STATUS      current
      DESCRIPTION "ObjectName column"
      ::= { kodoDataCacheRuntimeEntry 2  }
   
   
   kodoDataCacheRuntimeType OBJECT-TYPE
      SYNTAX      OCTET STRING
      MAX-ACCESS  read-only
      STATUS      current
      DESCRIPTION "Returns the type of the MBean. "
      ::= { kodoDataCacheRuntimeEntry 3  }
   
   
   kodoDataCacheRuntimeCacheHitCount OBJECT-TYPE
      SYNTAX      Integer32
      MAX-ACCESS  read-only
      STATUS      current
      DESCRIPTION " "
      ::= { kodoDataCacheRuntimeEntry 4  }
   
   
   kodoDataCacheRuntimeTotalCurrentEntries OBJECT-TYPE
      SYNTAX      Integer32
      MAX-ACCESS  read-only
      STATUS      current
      DESCRIPTION " "
      ::= { kodoDataCacheRuntimeEntry 5  }
   
   
   kodoDataCacheRuntimeCacheMissCount OBJECT-TYPE
      SYNTAX      Integer32
      MAX-ACCESS  read-only
      STATUS      current
      DESCRIPTION " "
      ::= { kodoDataCacheRuntimeEntry 6  }
   
   
   kodoDataCacheRuntimeCacheHitRatio OBJECT-TYPE
      SYNTAX      OCTET STRING
      MAX-ACCESS  read-only
      STATUS      current
      DESCRIPTION " "
      ::= { kodoDataCacheRuntimeEntry 7  }
   
   
   kodoDataCacheRuntimeName OBJECT-TYPE
      SYNTAX      OCTET STRING
      MAX-ACCESS  read-only
      STATUS      current
      DESCRIPTION "The name of this configuration. WebLogic Server uses an MBean to implement and persist the configuration. "
      ::= { kodoDataCacheRuntimeEntry 8  }
   
   
   kodoDataCacheRuntimeStatistics OBJECT-TYPE
      SYNTAX      OCTET STRING
      MAX-ACCESS  read-only
      STATUS      current
      DESCRIPTION " "
      ::= { kodoDataCacheRuntimeEntry 9  }
   
   
   kodoPersistenceUnitRuntimeTable OBJECT-TYPE
      SYNTAX      SEQUENCE OF KodoPersistenceUnitRuntimeEntry
      MAX-ACCESS  not-accessible
      STATUS      current
      DESCRIPTION "Base class for all runtime mbeans that provide status of running modules. "
      ::= { wls 1265  }
      
   
   kodoPersistenceUnitRuntimeEntry OBJECT-TYPE
      SYNTAX      KodoPersistenceUnitRuntimeEntry
      MAX-ACCESS  not-accessible
      STATUS      current
      DESCRIPTION "Generated SNMP Table Entry."
      INDEX { kodoPersistenceUnitRuntimeIndex}
      ::= { kodoPersistenceUnitRuntimeTable 1 }
      
   KodoPersistenceUnitRuntimeEntry ::=
      SEQUENCE
      {
         kodoPersistenceUnitRuntimeIndex OCTET STRING,
         kodoPersistenceUnitRuntimeObjectName OCTET STRING,
         kodoPersistenceUnitRuntimeType OCTET STRING,
         kodoPersistenceUnitRuntimePersistenceUnitName OCTET STRING,
         kodoPersistenceUnitRuntimeName OCTET STRING
      }
      
   
   kodoPersistenceUnitRuntimeIndex OBJECT-TYPE
      SYNTAX      OCTET STRING
      MAX-ACCESS  not-accessible
      STATUS      current
      DESCRIPTION "Index column"
      ::= { kodoPersistenceUnitRuntimeEntry 1  }
   
   
   kodoPersistenceUnitRuntimeObjectName OBJECT-TYPE
      SYNTAX      OCTET STRING
      MAX-ACCESS  read-only
      STATUS      current
      DESCRIPTION "ObjectName column"
      ::= { kodoPersistenceUnitRuntimeEntry 2  }
   
   
   kodoPersistenceUnitRuntimeType OBJECT-TYPE
      SYNTAX      OCTET STRING
      MAX-ACCESS  read-only
      STATUS      current
      DESCRIPTION "Returns the type of the MBean. "
      ::= { kodoPersistenceUnitRuntimeEntry 3  }
   
   
   kodoPersistenceUnitRuntimePersistenceUnitName OBJECT-TYPE
      SYNTAX      OCTET STRING
      MAX-ACCESS  read-only
      STATUS      current
      DESCRIPTION " "
      ::= { kodoPersistenceUnitRuntimeEntry 4  }
   
   
   kodoPersistenceUnitRuntimeName OBJECT-TYPE
      SYNTAX      OCTET STRING
      MAX-ACCESS  read-only
      STATUS      current
      DESCRIPTION "The name of this configuration. WebLogic Server uses an MBean to implement and persist the configuration. "
      ::= { kodoPersistenceUnitRuntimeEntry 5  }
   
   
   kodoQueryCacheRuntimeTable OBJECT-TYPE
      SYNTAX      SEQUENCE OF KodoQueryCacheRuntimeEntry
      MAX-ACCESS  not-accessible
      STATUS      current
      DESCRIPTION "Base class for all runtime mbeans that provide status of running modules. "
      ::= { wls 1270  }
      
   
   kodoQueryCacheRuntimeEntry OBJECT-TYPE
      SYNTAX      KodoQueryCacheRuntimeEntry
      MAX-ACCESS  not-accessible
      STATUS      current
      DESCRIPTION "Generated SNMP Table Entry."
      INDEX { kodoQueryCacheRuntimeIndex}
      ::= { kodoQueryCacheRuntimeTable 1 }
      
   KodoQueryCacheRuntimeEntry ::=
      SEQUENCE
      {
         kodoQueryCacheRuntimeIndex OCTET STRING,
         kodoQueryCacheRuntimeObjectName OCTET STRING,
         kodoQueryCacheRuntimeType OCTET STRING,
         kodoQueryCacheRuntimeCacheHitCount Integer32,
         kodoQueryCacheRuntimeTotalCurrentEntries Integer32,
         kodoQueryCacheRuntimeCacheMissCount Integer32,
         kodoQueryCacheRuntimeCacheHitRatio OCTET STRING,
         kodoQueryCacheRuntimeName OCTET STRING,
         kodoQueryCacheRuntimeStatistics OCTET STRING
      }
      
   
   kodoQueryCacheRuntimeIndex OBJECT-TYPE
      SYNTAX      OCTET STRING
      MAX-ACCESS  not-accessible
      STATUS      current
      DESCRIPTION "Index column"
      ::= { kodoQueryCacheRuntimeEntry 1  }
   
   
   kodoQueryCacheRuntimeObjectName OBJECT-TYPE
      SYNTAX      OCTET STRING
      MAX-ACCESS  read-only
      STATUS      current
      DESCRIPTION "ObjectName column"
      ::= { kodoQueryCacheRuntimeEntry 2  }
   
   
   kodoQueryCacheRuntimeType OBJECT-TYPE
      SYNTAX      OCTET STRING
      MAX-ACCESS  read-only
      STATUS      current
      DESCRIPTION "Returns the type of the MBean. "
      ::= { kodoQueryCacheRuntimeEntry 3  }
   
   
   kodoQueryCacheRuntimeCacheHitCount OBJECT-TYPE
      SYNTAX      Integer32
      MAX-ACCESS  read-only
      STATUS      current
      DESCRIPTION " "
      ::= { kodoQueryCacheRuntimeEntry 4  }
   
   
   kodoQueryCacheRuntimeTotalCurrentEntries OBJECT-TYPE
      SYNTAX      Integer32
      MAX-ACCESS  read-only
      STATUS      current
      DESCRIPTION " "
      ::= { kodoQueryCacheRuntimeEntry 5  }
   
   
   kodoQueryCacheRuntimeCacheMissCount OBJECT-TYPE
      SYNTAX      Integer32
      MAX-ACCESS  read-only
      STATUS      current
      DESCRIPTION " "
      ::= { kodoQueryCacheRuntimeEntry 6  }
   
   
   kodoQueryCacheRuntimeCacheHitRatio OBJECT-TYPE
      SYNTAX      OCTET STRING
      MAX-ACCESS  read-only
      STATUS      current
      DESCRIPTION " "
      ::= { kodoQueryCacheRuntimeEntry 7  }
   
   
   kodoQueryCacheRuntimeName OBJECT-TYPE
      SYNTAX      OCTET STRING
      MAX-ACCESS  read-only
      STATUS      current
      DESCRIPTION "The name of this configuration. WebLogic Server uses an MBean to implement and persist the configuration. "
      ::= { kodoQueryCacheRuntimeEntry 8  }
   
   
   kodoQueryCacheRuntimeStatistics OBJECT-TYPE
      SYNTAX      OCTET STRING
      MAX-ACCESS  read-only
      STATUS      current
      DESCRIPTION " "
      ::= { kodoQueryCacheRuntimeEntry 9  }
   
   
   kodoQueryCompilationCacheRuntimeTable OBJECT-TYPE
      SYNTAX      SEQUENCE OF KodoQueryCompilationCacheRuntimeEntry
      MAX-ACCESS  not-accessible
      STATUS      current
      DESCRIPTION "Base class for all runtime mbeans that provide status of running modules. "
      ::= { wls 1275  }
      
   
   kodoQueryCompilationCacheRuntimeEntry OBJECT-TYPE
      SYNTAX      KodoQueryCompilationCacheRuntimeEntry
      MAX-ACCESS  not-accessible
      STATUS      current
      DESCRIPTION "Generated SNMP Table Entry."
      INDEX { kodoQueryCompilationCacheRuntimeIndex}
      ::= { kodoQueryCompilationCacheRuntimeTable 1 }
      
   KodoQueryCompilationCacheRuntimeEntry ::=
      SEQUENCE
      {
         kodoQueryCompilationCacheRuntimeIndex OCTET STRING,
         kodoQueryCompilationCacheRuntimeObjectName OCTET STRING,
         kodoQueryCompilationCacheRuntimeType OCTET STRING,
         kodoQueryCompilationCacheRuntimeTotalCurrentEntries Integer32,
         kodoQueryCompilationCacheRuntimeName OCTET STRING
      }
      
   
   kodoQueryCompilationCacheRuntimeIndex OBJECT-TYPE
      SYNTAX      OCTET STRING
      MAX-ACCESS  not-accessible
      STATUS      current
      DESCRIPTION "Index column"
      ::= { kodoQueryCompilationCacheRuntimeEntry 1  }
   
   
   kodoQueryCompilationCacheRuntimeObjectName OBJECT-TYPE
      SYNTAX      OCTET STRING
      MAX-ACCESS  read-only
      STATUS      current
      DESCRIPTION "ObjectName column"
      ::= { kodoQueryCompilationCacheRuntimeEntry 2  }
   
   
   kodoQueryCompilationCacheRuntimeType OBJECT-TYPE
      SYNTAX      OCTET STRING
      MAX-ACCESS  read-only
      STATUS      current
      DESCRIPTION "Returns the type of the MBean. "
      ::= { kodoQueryCompilationCacheRuntimeEntry 3  }
   
   
   kodoQueryCompilationCacheRuntimeTotalCurrentEntries OBJECT-TYPE
      SYNTAX      Integer32
      MAX-ACCESS  read-only
      STATUS      current
      DESCRIPTION " "
      ::= { kodoQueryCompilationCacheRuntimeEntry 4  }
   
   
   kodoQueryCompilationCacheRuntimeName OBJECT-TYPE
      SYNTAX      OCTET STRING
      MAX-ACCESS  read-only
      STATUS      current
      DESCRIPTION "The name of this configuration. WebLogic Server uses an MBean to implement and persist the configuration. "
      ::= { kodoQueryCompilationCacheRuntimeEntry 5  }
   
   
   mailSessionRuntimeTable OBJECT-TYPE
      SYNTAX      SEQUENCE OF MailSessionRuntimeEntry
      MAX-ACCESS  not-accessible
      STATUS      current
      DESCRIPTION "RuntimeMBean for JavaMail Sessions "
      ::= { wls 1280  }
      
   
   mailSessionRuntimeEntry OBJECT-TYPE
      SYNTAX      MailSessionRuntimeEntry
      MAX-ACCESS  not-accessible
      STATUS      current
      DESCRIPTION "Generated SNMP Table Entry."
      INDEX { mailSessionRuntimeIndex}
      ::= { mailSessionRuntimeTable 1 }
      
   MailSessionRuntimeEntry ::=
      SEQUENCE
      {
         mailSessionRuntimeIndex OCTET STRING,
         mailSessionRuntimeObjectName OCTET STRING,
         mailSessionRuntimeType OCTET STRING,
         mailSessionRuntimeName OCTET STRING
      }
      
   
   mailSessionRuntimeIndex OBJECT-TYPE
      SYNTAX      OCTET STRING
      MAX-ACCESS  not-accessible
      STATUS      current
      DESCRIPTION "Index column"
      ::= { mailSessionRuntimeEntry 1  }
   
   
   mailSessionRuntimeObjectName OBJECT-TYPE
      SYNTAX      OCTET STRING
      MAX-ACCESS  read-only
      STATUS      current
      DESCRIPTION "ObjectName column"
      ::= { mailSessionRuntimeEntry 2  }
   
   
   mailSessionRuntimeType OBJECT-TYPE
      SYNTAX      OCTET STRING
      MAX-ACCESS  read-only
      STATUS      current
      DESCRIPTION "Returns the type of the MBean. "
      ::= { mailSessionRuntimeEntry 3  }
   
   
   mailSessionRuntimeName OBJECT-TYPE
      SYNTAX      OCTET STRING
      MAX-ACCESS  read-only
      STATUS      current
      DESCRIPTION "The name of this configuration. WebLogic Server uses an MBean to implement and persist the configuration. "
      ::= { mailSessionRuntimeEntry 4  }
   
   
   messageDrivenControlEJBRuntimeTable OBJECT-TYPE
      SYNTAX      SEQUENCE OF MessageDrivenControlEJBRuntimeEntry
      MAX-ACCESS  not-accessible
      STATUS      current
      DESCRIPTION "This interface contains controls to suspend and resume the MDBs. This RuntimeMBean is deployed only on the AdminServer. "
      ::= { wls 1285  }
      
   
   messageDrivenControlEJBRuntimeEntry OBJECT-TYPE
      SYNTAX      MessageDrivenControlEJBRuntimeEntry
      MAX-ACCESS  not-accessible
      STATUS      current
      DESCRIPTION "Generated SNMP Table Entry."
      INDEX { messageDrivenControlEJBRuntimeIndex}
      ::= { messageDrivenControlEJBRuntimeTable 1 }
      
   MessageDrivenControlEJBRuntimeEntry ::=
      SEQUENCE
      {
         messageDrivenControlEJBRuntimeIndex OCTET STRING,
         messageDrivenControlEJBRuntimeObjectName OCTET STRING,
         messageDrivenControlEJBRuntimeType OCTET STRING,
         messageDrivenControlEJBRuntimeName OCTET STRING
      }
      
   
   messageDrivenControlEJBRuntimeIndex OBJECT-TYPE
      SYNTAX      OCTET STRING
      MAX-ACCESS  not-accessible
      STATUS      current
      DESCRIPTION "Index column"
      ::= { messageDrivenControlEJBRuntimeEntry 1  }
   
   
   messageDrivenControlEJBRuntimeObjectName OBJECT-TYPE
      SYNTAX      OCTET STRING
      MAX-ACCESS  read-only
      STATUS      current
      DESCRIPTION "ObjectName column"
      ::= { messageDrivenControlEJBRuntimeEntry 2  }
   
   
   messageDrivenControlEJBRuntimeType OBJECT-TYPE
      SYNTAX      OCTET STRING
      MAX-ACCESS  read-only
      STATUS      current
      DESCRIPTION "Returns the type of the MBean. "
      ::= { messageDrivenControlEJBRuntimeEntry 3  }
   
   
   messageDrivenControlEJBRuntimeName OBJECT-TYPE
      SYNTAX      OCTET STRING
      MAX-ACCESS  read-only
      STATUS      current
      DESCRIPTION "The name of this configuration. WebLogic Server uses an MBean to implement and persist the configuration. "
      ::= { messageDrivenControlEJBRuntimeEntry 4  }
   
   
   migratableServiceCoordinatorRuntimeTable OBJECT-TYPE
      SYNTAX      SEQUENCE OF MigratableServiceCoordinatorRuntimeEntry
      MAX-ACCESS  not-accessible
      STATUS      current
      DESCRIPTION "This class is used for monitoring the Migratable Service Coordinator. "
      ::= { wls 1290  }
      
   
   migratableServiceCoordinatorRuntimeEntry OBJECT-TYPE
      SYNTAX      MigratableServiceCoordinatorRuntimeEntry
      MAX-ACCESS  not-accessible
      STATUS      current
      DESCRIPTION "Generated SNMP Table Entry."
      INDEX { migratableServiceCoordinatorRuntimeIndex}
      ::= { migratableServiceCoordinatorRuntimeTable 1 }
      
   MigratableServiceCoordinatorRuntimeEntry ::=
      SEQUENCE
      {
         migratableServiceCoordinatorRuntimeIndex OCTET STRING,
         migratableServiceCoordinatorRuntimeObjectName OCTET STRING,
         migratableServiceCoordinatorRuntimeType OCTET STRING,
         migratableServiceCoordinatorRuntimeName OCTET STRING
      }
      
   
   migratableServiceCoordinatorRuntimeIndex OBJECT-TYPE
      SYNTAX      OCTET STRING
      MAX-ACCESS  not-accessible
      STATUS      current
      DESCRIPTION "Index column"
      ::= { migratableServiceCoordinatorRuntimeEntry 1  }
   
   
   migratableServiceCoordinatorRuntimeObjectName OBJECT-TYPE
      SYNTAX      OCTET STRING
      MAX-ACCESS  read-only
      STATUS      current
      DESCRIPTION "ObjectName column"
      ::= { migratableServiceCoordinatorRuntimeEntry 2  }
   
   
   migratableServiceCoordinatorRuntimeType OBJECT-TYPE
      SYNTAX      OCTET STRING
      MAX-ACCESS  read-only
      STATUS      current
      DESCRIPTION "Returns the type of the MBean. "
      ::= { migratableServiceCoordinatorRuntimeEntry 3  }
   
   
   migratableServiceCoordinatorRuntimeName OBJECT-TYPE
      SYNTAX      OCTET STRING
      MAX-ACCESS  read-only
      STATUS      current
      DESCRIPTION "The name of this configuration. WebLogic Server uses an MBean to implement and persist the configuration. "
      ::= { migratableServiceCoordinatorRuntimeEntry 4  }
   
   
   migrationDataRuntimeTable OBJECT-TYPE
      SYNTAX      SEQUENCE OF MigrationDataRuntimeEntry
      MAX-ACCESS  not-accessible
      STATUS      current
      DESCRIPTION "Runtime information about one past or ongoing migration. "
      ::= { wls 1295  }
      
   
   migrationDataRuntimeEntry OBJECT-TYPE
      SYNTAX      MigrationDataRuntimeEntry
      MAX-ACCESS  not-accessible
      STATUS      current
      DESCRIPTION "Generated SNMP Table Entry."
      INDEX { migrationDataRuntimeIndex}
      ::= { migrationDataRuntimeTable 1 }
      
   MigrationDataRuntimeEntry ::=
      SEQUENCE
      {
         migrationDataRuntimeIndex OCTET STRING,
         migrationDataRuntimeObjectName OCTET STRING,
         migrationDataRuntimeType OCTET STRING,
         migrationDataRuntimeStatus Integer32,
         migrationDataRuntimeMigrationStartTime Counter64,
         migrationDataRuntimeClusterMasterName OCTET STRING,
         migrationDataRuntimeServerName OCTET STRING,
         migrationDataRuntimeMachineMigratedFrom OCTET STRING,
         migrationDataRuntimeMigrationEndTime Counter64,
         migrationDataRuntimeClusterName OCTET STRING,
         migrationDataRuntimeName OCTET STRING,
         migrationDataRuntimeMachineMigratedTo OCTET STRING,
         migrationDataRuntimeMachinesAttempted OCTET STRING
      }
      
   
   migrationDataRuntimeIndex OBJECT-TYPE
      SYNTAX      OCTET STRING
      MAX-ACCESS  not-accessible
      STATUS      current
      DESCRIPTION "Index column"
      ::= { migrationDataRuntimeEntry 1  }
   
   
   migrationDataRuntimeObjectName OBJECT-TYPE
      SYNTAX      OCTET STRING
      MAX-ACCESS  read-only
      STATUS      current
      DESCRIPTION "ObjectName column"
      ::= { migrationDataRuntimeEntry 2  }
   
   
   migrationDataRuntimeType OBJECT-TYPE
      SYNTAX      OCTET STRING
      MAX-ACCESS  read-only
      STATUS      current
      DESCRIPTION "Returns the type of the MBean. "
      ::= { migrationDataRuntimeEntry 3  }
   
   
   migrationDataRuntimeStatus OBJECT-TYPE
      SYNTAX      Integer32
      MAX-ACCESS  read-only
      STATUS      current
      DESCRIPTION "Name of the server migrated "
      ::= { migrationDataRuntimeEntry 4  }
   
   
   migrationDataRuntimeMigrationStartTime OBJECT-TYPE
      SYNTAX      Counter64
      MAX-ACCESS  read-only
      STATUS      current
      DESCRIPTION "Start time of migration "
      ::= { migrationDataRuntimeEntry 5  }
   
   
   migrationDataRuntimeClusterMasterName OBJECT-TYPE
      SYNTAX      OCTET STRING
      MAX-ACCESS  read-only
      STATUS      current
      DESCRIPTION "Name of the server that acted as the cluster master for this migration. "
      ::= { migrationDataRuntimeEntry 6  }
   
   
   migrationDataRuntimeServerName OBJECT-TYPE
      SYNTAX      OCTET STRING
      MAX-ACCESS  read-only
      STATUS      current
      DESCRIPTION "Name of the server migrated "
      ::= { migrationDataRuntimeEntry 7  }
   
   
   migrationDataRuntimeMachineMigratedFrom OBJECT-TYPE
      SYNTAX      OCTET STRING
      MAX-ACCESS  read-only
      STATUS      current
      DESCRIPTION "Machine from which the server was migrated from "
      ::= { migrationDataRuntimeEntry 8  }
   
   
   migrationDataRuntimeMigrationEndTime OBJECT-TYPE
      SYNTAX      Counter64
      MAX-ACCESS  read-only
      STATUS      current
      DESCRIPTION "End time of migration "
      ::= { migrationDataRuntimeEntry 9  }
   
   
   migrationDataRuntimeClusterName OBJECT-TYPE
      SYNTAX      OCTET STRING
      MAX-ACCESS  read-only
      STATUS      current
      DESCRIPTION "Name of the server that acted as the cluster master for this migration. "
      ::= { migrationDataRuntimeEntry 10  }
   
   
   migrationDataRuntimeName OBJECT-TYPE
      SYNTAX      OCTET STRING
      MAX-ACCESS  read-only
      STATUS      current
      DESCRIPTION "The name of this configuration. WebLogic Server uses an MBean to implement and persist the configuration. "
      ::= { migrationDataRuntimeEntry 11  }
   
   
   migrationDataRuntimeMachineMigratedTo OBJECT-TYPE
      SYNTAX      OCTET STRING
      MAX-ACCESS  read-only
      STATUS      current
      DESCRIPTION "Machine to which the server was migrated to or is in the process of being migrated to. "
      ::= { migrationDataRuntimeEntry 12  }
   
   
   migrationDataRuntimeMachinesAttempted OBJECT-TYPE
      SYNTAX      OCTET STRING
      MAX-ACCESS  read-only
      STATUS      current
      DESCRIPTION "Get all the machines attempted for migration. "
      ::= { migrationDataRuntimeEntry 13  }
   
   
   psAssemblyRuntimeTable OBJECT-TYPE
      SYNTAX      SEQUENCE OF PsAssemblyRuntimeEntry
      MAX-ACCESS  not-accessible
      STATUS      current
      DESCRIPTION "This interface is used for accessing a WebLogic path service entity "
      ::= { wls 1305  }
      
   
   psAssemblyRuntimeEntry OBJECT-TYPE
      SYNTAX      PsAssemblyRuntimeEntry
      MAX-ACCESS  not-accessible
      STATUS      current
      DESCRIPTION "Generated SNMP Table Entry."
      INDEX { psAssemblyRuntimeIndex}
      ::= { psAssemblyRuntimeTable 1 }
      
   PsAssemblyRuntimeEntry ::=
      SEQUENCE
      {
         psAssemblyRuntimeIndex OCTET STRING,
         psAssemblyRuntimeObjectName OCTET STRING,
         psAssemblyRuntimeType OCTET STRING,
         psAssemblyRuntimeMapEntries OCTET STRING,
         psAssemblyRuntimeName OCTET STRING
      }
      
   
   psAssemblyRuntimeIndex OBJECT-TYPE
      SYNTAX      OCTET STRING
      MAX-ACCESS  not-accessible
      STATUS      current
      DESCRIPTION "Index column"
      ::= { psAssemblyRuntimeEntry 1  }
   
   
   psAssemblyRuntimeObjectName OBJECT-TYPE
      SYNTAX      OCTET STRING
      MAX-ACCESS  read-only
      STATUS      current
      DESCRIPTION "ObjectName column"
      ::= { psAssemblyRuntimeEntry 2  }
   
   
   psAssemblyRuntimeType OBJECT-TYPE
      SYNTAX      OCTET STRING
      MAX-ACCESS  read-only
      STATUS      current
      DESCRIPTION "Returns the type of the MBean. "
      ::= { psAssemblyRuntimeEntry 3  }
   
   
   psAssemblyRuntimeMapEntries OBJECT-TYPE
      SYNTAX      OCTET STRING
      MAX-ACCESS  read-only
      STATUS      current
      DESCRIPTION "Returns all entries in a persistent map's assembly. "
      ::= { psAssemblyRuntimeEntry 4  }
   
   
   psAssemblyRuntimeName OBJECT-TYPE
      SYNTAX      OCTET STRING
      MAX-ACCESS  read-only
      STATUS      current
      DESCRIPTION "The name of this configuration. WebLogic Server uses an MBean to implement and persist the configuration. "
      ::= { psAssemblyRuntimeEntry 5  }
   
   
   pageFlowActionRuntimeTable OBJECT-TYPE
      SYNTAX      SEQUENCE OF PageFlowActionRuntimeEntry
      MAX-ACCESS  not-accessible
      STATUS      current
      DESCRIPTION "This MBean represents the statistics for a single action of a PageFlow "
      ::= { wls 1310  }
      
   
   pageFlowActionRuntimeEntry OBJECT-TYPE
      SYNTAX      PageFlowActionRuntimeEntry
      MAX-ACCESS  not-accessible
      STATUS      current
      DESCRIPTION "Generated SNMP Table Entry."
      INDEX { pageFlowActionRuntimeIndex}
      ::= { pageFlowActionRuntimeTable 1 }
      
   PageFlowActionRuntimeEntry ::=
      SEQUENCE
      {
         pageFlowActionRuntimeIndex OCTET STRING,
         pageFlowActionRuntimeObjectName OCTET STRING,
         pageFlowActionRuntimeType OCTET STRING,
         pageFlowActionRuntimeName OCTET STRING,
         pageFlowActionRuntimeActionName OCTET STRING,
         pageFlowActionRuntimeSuccessDispatchTimeTotal Counter64,
         pageFlowActionRuntimeSuccessDispatchTimeHigh Counter64,
         pageFlowActionRuntimeSuccessDispatchTimeLow Counter64,
         pageFlowActionRuntimeSuccessCount Counter64,
         pageFlowActionRuntimeHandledExceptionDispatchTimeHigh Counter64,
         pageFlowActionRuntimeExceptionCount Counter64,
         pageFlowActionRuntimeHandledExceptionDispatchTimeLow Counter64,
         pageFlowActionRuntimeHandledExceptionCount Counter64,
         pageFlowActionRuntimeHandledExceptionDispatchTimeAverage Counter64,
         pageFlowActionRuntimeHandledExceptionDispatchTimeTotal Counter64,
         pageFlowActionRuntimeSuccessDispatchTimeAverage Counter64
      }
      
   
   pageFlowActionRuntimeIndex OBJECT-TYPE
      SYNTAX      OCTET STRING
      MAX-ACCESS  not-accessible
      STATUS      current
      DESCRIPTION "Index column"
      ::= { pageFlowActionRuntimeEntry 1  }
   
   
   pageFlowActionRuntimeObjectName OBJECT-TYPE
      SYNTAX      OCTET STRING
      MAX-ACCESS  read-only
      STATUS      current
      DESCRIPTION "ObjectName column"
      ::= { pageFlowActionRuntimeEntry 2  }
   
   
   pageFlowActionRuntimeType OBJECT-TYPE
      SYNTAX      OCTET STRING
      MAX-ACCESS  read-only
      STATUS      current
      DESCRIPTION "Returns the type of the MBean. "
      ::= { pageFlowActionRuntimeEntry 3  }
   
   
   pageFlowActionRuntimeName OBJECT-TYPE
      SYNTAX      OCTET STRING
      MAX-ACCESS  read-only
      STATUS      current
      DESCRIPTION "The name of this configuration. WebLogic Server uses an MBean to implement and persist the configuration. "
      ::= { pageFlowActionRuntimeEntry 4  }
   
   
   pageFlowActionRuntimeActionName OBJECT-TYPE
      SYNTAX      OCTET STRING
      MAX-ACCESS  read-only
      STATUS      current
      DESCRIPTION " "
      ::= { pageFlowActionRuntimeEntry 5  }
   
   
   pageFlowActionRuntimeSuccessDispatchTimeTotal OBJECT-TYPE
      SYNTAX      Counter64
      MAX-ACCESS  read-only
      STATUS      current
      DESCRIPTION " "
      ::= { pageFlowActionRuntimeEntry 6  }
   
   
   pageFlowActionRuntimeSuccessDispatchTimeHigh OBJECT-TYPE
      SYNTAX      Counter64
      MAX-ACCESS  read-only
      STATUS      current
      DESCRIPTION " "
      ::= { pageFlowActionRuntimeEntry 7  }
   
   
   pageFlowActionRuntimeSuccessDispatchTimeLow OBJECT-TYPE
      SYNTAX      Counter64
      MAX-ACCESS  read-only
      STATUS      current
      DESCRIPTION " "
      ::= { pageFlowActionRuntimeEntry 8  }
   
   
   pageFlowActionRuntimeSuccessCount OBJECT-TYPE
      SYNTAX      Counter64
      MAX-ACCESS  read-only
      STATUS      current
      DESCRIPTION " "
      ::= { pageFlowActionRuntimeEntry 9  }
   
   
   pageFlowActionRuntimeHandledExceptionDispatchTimeHigh OBJECT-TYPE
      SYNTAX      Counter64
      MAX-ACCESS  read-only
      STATUS      current
      DESCRIPTION " "
      ::= { pageFlowActionRuntimeEntry 10  }
   
   
   pageFlowActionRuntimeExceptionCount OBJECT-TYPE
      SYNTAX      Counter64
      MAX-ACCESS  read-only
      STATUS      current
      DESCRIPTION " "
      ::= { pageFlowActionRuntimeEntry 11  }
   
   
   pageFlowActionRuntimeHandledExceptionDispatchTimeLow OBJECT-TYPE
      SYNTAX      Counter64
      MAX-ACCESS  read-only
      STATUS      current
      DESCRIPTION " "
      ::= { pageFlowActionRuntimeEntry 12  }
   
   
   pageFlowActionRuntimeHandledExceptionCount OBJECT-TYPE
      SYNTAX      Counter64
      MAX-ACCESS  read-only
      STATUS      current
      DESCRIPTION " "
      ::= { pageFlowActionRuntimeEntry 13  }
   
   
   pageFlowActionRuntimeHandledExceptionDispatchTimeAverage OBJECT-TYPE
      SYNTAX      Counter64
      MAX-ACCESS  read-only
      STATUS      current
      DESCRIPTION " "
      ::= { pageFlowActionRuntimeEntry 14  }
   
   
   pageFlowActionRuntimeHandledExceptionDispatchTimeTotal OBJECT-TYPE
      SYNTAX      Counter64
      MAX-ACCESS  read-only
      STATUS      current
      DESCRIPTION " "
      ::= { pageFlowActionRuntimeEntry 15  }
   
   
   pageFlowActionRuntimeSuccessDispatchTimeAverage OBJECT-TYPE
      SYNTAX      Counter64
      MAX-ACCESS  read-only
      STATUS      current
      DESCRIPTION " "
      ::= { pageFlowActionRuntimeEntry 16  }
   
   
   pageFlowRuntimeTable OBJECT-TYPE
      SYNTAX      SEQUENCE OF PageFlowRuntimeEntry
      MAX-ACCESS  not-accessible
      STATUS      current
      DESCRIPTION "This MBean represents a PageFlow type. "
      ::= { wls 1315  }
      
   
   pageFlowRuntimeEntry OBJECT-TYPE
      SYNTAX      PageFlowRuntimeEntry
      MAX-ACCESS  not-accessible
      STATUS      current
      DESCRIPTION "Generated SNMP Table Entry."
      INDEX { pageFlowRuntimeIndex}
      ::= { pageFlowRuntimeTable 1 }
      
   PageFlowRuntimeEntry ::=
      SEQUENCE
      {
         pageFlowRuntimeIndex OCTET STRING,
         pageFlowRuntimeObjectName OCTET STRING,
         pageFlowRuntimeType  OCTET STRING,
         pageFlowRuntimeName  OCTET STRING,
         pageFlowRuntimeCreateCount Counter64,
         pageFlowRuntimeLastResetTime Counter64,
         pageFlowRuntimeDestroyCount Counter64,
         pageFlowRuntimeClassName OCTET STRING
      }
      
   
   pageFlowRuntimeIndex OBJECT-TYPE
      SYNTAX      OCTET STRING
      MAX-ACCESS  not-accessible
      STATUS      current
      DESCRIPTION "Index column"
      ::= { pageFlowRuntimeEntry 1  }
   
   
   pageFlowRuntimeObjectName OBJECT-TYPE
      SYNTAX      OCTET STRING
      MAX-ACCESS  read-only
      STATUS      current
      DESCRIPTION "ObjectName column"
      ::= { pageFlowRuntimeEntry 2  }
   
   
   pageFlowRuntimeType OBJECT-TYPE
      SYNTAX      OCTET STRING
      MAX-ACCESS  read-only
      STATUS      current
      DESCRIPTION "Returns the type of the MBean. "
      ::= { pageFlowRuntimeEntry 3  }
   
   
   pageFlowRuntimeName OBJECT-TYPE
      SYNTAX      OCTET STRING
      MAX-ACCESS  read-only
      STATUS      current
      DESCRIPTION "The name of this configuration. WebLogic Server uses an MBean to implement and persist the configuration. "
      ::= { pageFlowRuntimeEntry 4  }
   
   
   pageFlowRuntimeCreateCount OBJECT-TYPE
      SYNTAX      Counter64
      MAX-ACCESS  read-only
      STATUS      current
      DESCRIPTION " "
      ::= { pageFlowRuntimeEntry 5  }
   
   
   pageFlowRuntimeLastResetTime OBJECT-TYPE
      SYNTAX      Counter64
      MAX-ACCESS  read-only
      STATUS      current
      DESCRIPTION " "
      ::= { pageFlowRuntimeEntry 6  }
   
   
   pageFlowRuntimeDestroyCount OBJECT-TYPE
      SYNTAX      Counter64
      MAX-ACCESS  read-only
      STATUS      current
      DESCRIPTION " "
      ::= { pageFlowRuntimeEntry 7  }
   
   
   pageFlowRuntimeClassName OBJECT-TYPE
      SYNTAX      OCTET STRING
      MAX-ACCESS  read-only
      STATUS      current
      DESCRIPTION " "
      ::= { pageFlowRuntimeEntry 8  }
   
   
   pageFlowsRuntimeTable OBJECT-TYPE
      SYNTAX      SEQUENCE OF PageFlowsRuntimeEntry
      MAX-ACCESS  not-accessible
      STATUS      current
      DESCRIPTION "This MBean just hides the lazy construction of PageFlowRuntimeMBeans and provides a top-level reset() operation for all PageFlows in the webapp. It also minimizes the impact on the WebAppRuntimeMBean. "
      ::= { wls 1320  }
      
   
   pageFlowsRuntimeEntry OBJECT-TYPE
      SYNTAX      PageFlowsRuntimeEntry
      MAX-ACCESS  not-accessible
      STATUS      current
      DESCRIPTION "Generated SNMP Table Entry."
      INDEX { pageFlowsRuntimeIndex}
      ::= { pageFlowsRuntimeTable 1 }
      
   PageFlowsRuntimeEntry ::=
      SEQUENCE
      {
         pageFlowsRuntimeIndex OCTET STRING,
         pageFlowsRuntimeObjectName OCTET STRING,
         pageFlowsRuntimeType OCTET STRING,
         pageFlowsRuntimeName OCTET STRING,
         pageFlowsRuntimeServerName OCTET STRING,
         pageFlowsRuntimeHttpServerName OCTET STRING,
         pageFlowsRuntimeContextPath OCTET STRING,
         pageFlowsRuntimeAppName OCTET STRING
      }
      
   
   pageFlowsRuntimeIndex OBJECT-TYPE
      SYNTAX      OCTET STRING
      MAX-ACCESS  not-accessible
      STATUS      current
      DESCRIPTION "Index column"
      ::= { pageFlowsRuntimeEntry 1  }
   
   
   pageFlowsRuntimeObjectName OBJECT-TYPE
      SYNTAX      OCTET STRING
      MAX-ACCESS  read-only
      STATUS      current
      DESCRIPTION "ObjectName column"
      ::= { pageFlowsRuntimeEntry 2  }
   
   
   pageFlowsRuntimeType OBJECT-TYPE
      SYNTAX      OCTET STRING
      MAX-ACCESS  read-only
      STATUS      current
      DESCRIPTION "Returns the type of the MBean. "
      ::= { pageFlowsRuntimeEntry 3  }
   
   
   pageFlowsRuntimeName OBJECT-TYPE
      SYNTAX      OCTET STRING
      MAX-ACCESS  read-only
      STATUS      current
      DESCRIPTION "The name of this configuration. WebLogic Server uses an MBean to implement and persist the configuration. "
      ::= { pageFlowsRuntimeEntry 4  }
   
   
   pageFlowsRuntimeServerName OBJECT-TYPE
      SYNTAX      OCTET STRING
      MAX-ACCESS  read-only
      STATUS      current
      DESCRIPTION " "
      ::= { pageFlowsRuntimeEntry 5  }
   
   
   pageFlowsRuntimeHttpServerName OBJECT-TYPE
      SYNTAX      OCTET STRING
      MAX-ACCESS  read-only
      STATUS      current
      DESCRIPTION " "
      ::= { pageFlowsRuntimeEntry 6  }
   
   
   pageFlowsRuntimeContextPath OBJECT-TYPE
      SYNTAX      OCTET STRING
      MAX-ACCESS  read-only
      STATUS      current
      DESCRIPTION " "
      ::= { pageFlowsRuntimeEntry 7  }
   
   
   pageFlowsRuntimeAppName OBJECT-TYPE
      SYNTAX      OCTET STRING
      MAX-ACCESS  read-only
      STATUS      current
      DESCRIPTION " "
      ::= { pageFlowsRuntimeEntry 8  }
   
   
   pathServiceRuntimeTable OBJECT-TYPE
      SYNTAX      SEQUENCE OF PathServiceRuntimeEntry
      MAX-ACCESS  not-accessible
      STATUS      current
      DESCRIPTION "This interface is used for accessing a WebLogic path service entity "
      ::= { wls 1325  }
      
   
   pathServiceRuntimeEntry OBJECT-TYPE
      SYNTAX      PathServiceRuntimeEntry
      MAX-ACCESS  not-accessible
      STATUS      current
      DESCRIPTION "Generated SNMP Table Entry."
      INDEX { pathServiceRuntimeIndex}
      ::= { pathServiceRuntimeTable 1 }
      
   PathServiceRuntimeEntry ::=
      SEQUENCE
      {
         pathServiceRuntimeIndex OCTET STRING,
         pathServiceRuntimeObjectName OCTET STRING,
         pathServiceRuntimeType OCTET STRING,
         pathServiceRuntimeName OCTET STRING
      }
      
   
   pathServiceRuntimeIndex OBJECT-TYPE
      SYNTAX      OCTET STRING
      MAX-ACCESS  not-accessible
      STATUS      current
      DESCRIPTION "Index column"
      ::= { pathServiceRuntimeEntry 1  }
   
   
   pathServiceRuntimeObjectName OBJECT-TYPE
      SYNTAX      OCTET STRING
      MAX-ACCESS  read-only
      STATUS      current
      DESCRIPTION "ObjectName column"
      ::= { pathServiceRuntimeEntry 2  }
   
   
   pathServiceRuntimeType OBJECT-TYPE
      SYNTAX      OCTET STRING
      MAX-ACCESS  read-only
      STATUS      current
      DESCRIPTION "Returns the type of the MBean. "
      ::= { pathServiceRuntimeEntry 3  }
   
   
   pathServiceRuntimeName OBJECT-TYPE
      SYNTAX      OCTET STRING
      MAX-ACCESS  read-only
      STATUS      current
      DESCRIPTION "The name of this configuration. WebLogic Server uses an MBean to implement and persist the configuration. "
      ::= { pathServiceRuntimeEntry 4  }
   
   
   realmRuntimeTable OBJECT-TYPE
      SYNTAX      SEQUENCE OF RealmRuntimeEntry
      MAX-ACCESS  not-accessible
      STATUS      current
      DESCRIPTION "This class is used to monitor and manage per security realm runtime information. "
      ::= { wls 1330  }
      
   
   realmRuntimeEntry OBJECT-TYPE
      SYNTAX      RealmRuntimeEntry
      MAX-ACCESS  not-accessible
      STATUS      current
      DESCRIPTION "Generated SNMP Table Entry."
      INDEX { realmRuntimeIndex}
      ::= { realmRuntimeTable 1 }
      
   RealmRuntimeEntry ::=
      SEQUENCE
      {
         realmRuntimeIndex    OCTET STRING,
         realmRuntimeObjectName OCTET STRING,
         realmRuntimeType     OCTET STRING,
         realmRuntimeName     OCTET STRING
      }
      
   
   realmRuntimeIndex OBJECT-TYPE
      SYNTAX      OCTET STRING
      MAX-ACCESS  not-accessible
      STATUS      current
      DESCRIPTION "Index column"
      ::= { realmRuntimeEntry 1  }
   
   
   realmRuntimeObjectName OBJECT-TYPE
      SYNTAX      OCTET STRING
      MAX-ACCESS  read-only
      STATUS      current
      DESCRIPTION "ObjectName column"
      ::= { realmRuntimeEntry 2  }
   
   
   realmRuntimeType OBJECT-TYPE
      SYNTAX      OCTET STRING
      MAX-ACCESS  read-only
      STATUS      current
      DESCRIPTION "Returns the type of the MBean. "
      ::= { realmRuntimeEntry 3  }
   
   
   realmRuntimeName OBJECT-TYPE
      SYNTAX      OCTET STRING
      MAX-ACCESS  read-only
      STATUS      current
      DESCRIPTION "The user-specified name of this MBean instance.  This name is included as one of the key properties in the MBean's javax.management.ObjectName:  Name=user-specified-name "
      ::= { realmRuntimeEntry 4  }
   
   
   safRuntimeTable OBJECT-TYPE
      SYNTAX      SEQUENCE OF SafRuntimeEntry
      MAX-ACCESS  not-accessible
      STATUS      current
      DESCRIPTION "This class is used for monitoring a WebLogic SAF service. "
      ::= { wls 1335  }
      
   
   safRuntimeEntry OBJECT-TYPE
      SYNTAX      SafRuntimeEntry
      MAX-ACCESS  not-accessible
      STATUS      current
      DESCRIPTION "Generated SNMP Table Entry."
      INDEX { safRuntimeIndex}
      ::= { safRuntimeTable 1 }
      
   SafRuntimeEntry ::=
      SEQUENCE
      {
         safRuntimeIndex      OCTET STRING,
         safRuntimeObjectName OCTET STRING,
         safRuntimeType       OCTET STRING,
         safRuntimeName       OCTET STRING,
         safRuntimeHealthState OCTET STRING
      }
      
   
   safRuntimeIndex OBJECT-TYPE
      SYNTAX      OCTET STRING
      MAX-ACCESS  not-accessible
      STATUS      current
      DESCRIPTION "Index column"
      ::= { safRuntimeEntry 1  }
   
   
   safRuntimeObjectName OBJECT-TYPE
      SYNTAX      OCTET STRING
      MAX-ACCESS  read-only
      STATUS      current
      DESCRIPTION "ObjectName column"
      ::= { safRuntimeEntry 2  }
   
   
   safRuntimeType OBJECT-TYPE
      SYNTAX      OCTET STRING
      MAX-ACCESS  read-only
      STATUS      current
      DESCRIPTION "Returns the type of the MBean. "
      ::= { safRuntimeEntry 3  }
   
   
   safRuntimeName OBJECT-TYPE
      SYNTAX      OCTET STRING
      MAX-ACCESS  read-only
      STATUS      current
      DESCRIPTION "The name of this configuration. WebLogic Server uses an MBean to implement and persist the configuration. "
      ::= { safRuntimeEntry 4  }
   
   
   safRuntimeHealthState OBJECT-TYPE
      SYNTAX      OCTET STRING
      MAX-ACCESS  read-only
      STATUS      current
      DESCRIPTION "The health state of SAF service. "
      ::= { safRuntimeEntry 5  }
   
   
   wlssnmpAgentRuntimeTable OBJECT-TYPE
      SYNTAX      SEQUENCE OF WlssnmpAgentRuntimeEntry
      MAX-ACCESS  not-accessible
      STATUS      current
      DESCRIPTION "Runtime information for an SNMP agent that is running in the current WebLogic Server domain. "
      ::= { wls 1340  }
      
   
   wlssnmpAgentRuntimeEntry OBJECT-TYPE
      SYNTAX      WlssnmpAgentRuntimeEntry
      MAX-ACCESS  not-accessible
      STATUS      current
      DESCRIPTION "Generated SNMP Table Entry."
      INDEX { wlssnmpAgentRuntimeIndex}
      ::= { wlssnmpAgentRuntimeTable 1 }
      
   WlssnmpAgentRuntimeEntry ::=
      SEQUENCE
      {
         wlssnmpAgentRuntimeIndex OCTET STRING,
         wlssnmpAgentRuntimeObjectName OCTET STRING,
         wlssnmpAgentRuntimeType OCTET STRING,
         wlssnmpAgentRuntimeUDPListenPort Integer32,
         wlssnmpAgentRuntimeLogMessageTrapCount Counter64,
         wlssnmpAgentRuntimeFailedAuthorizationCount Integer32,
         wlssnmpAgentRuntimeRunning OCTET STRING,
         wlssnmpAgentRuntimeStringMonitorTrapCount Counter64,
         wlssnmpAgentRuntimeMonitorTrapCount Counter64,
         wlssnmpAgentRuntimeMasterAgentXPort Integer32,
         wlssnmpAgentRuntimeGaugeMonitorTrapCount Counter64,
         wlssnmpAgentRuntimeServerStopTrapCount Counter64,
         wlssnmpAgentRuntimeAttributeChangeTrapCount Counter64,
         wlssnmpAgentRuntimeServerStartTrapCount Counter64,
         wlssnmpAgentRuntimeFailedAuthenticationCount Integer32,
         wlssnmpAgentRuntimeCounterMonitorTrapCount Counter64,
         wlssnmpAgentRuntimeName OCTET STRING,
         wlssnmpAgentRuntimeFailedEncryptionCount Integer32,
         wlssnmpAgentRuntimeSNMPAgentName OCTET STRING
      }
      
   
   wlssnmpAgentRuntimeIndex OBJECT-TYPE
      SYNTAX      OCTET STRING
      MAX-ACCESS  not-accessible
      STATUS      current
      DESCRIPTION "Index column"
      ::= { wlssnmpAgentRuntimeEntry 1  }
   
   
   wlssnmpAgentRuntimeObjectName OBJECT-TYPE
      SYNTAX      OCTET STRING
      MAX-ACCESS  read-only
      STATUS      current
      DESCRIPTION "ObjectName column"
      ::= { wlssnmpAgentRuntimeEntry 2  }
   
   
   wlssnmpAgentRuntimeType OBJECT-TYPE
      SYNTAX      OCTET STRING
      MAX-ACCESS  read-only
      STATUS      current
      DESCRIPTION "Returns the type of the MBean. "
      ::= { wlssnmpAgentRuntimeEntry 3  }
   
   
   wlssnmpAgentRuntimeUDPListenPort OBJECT-TYPE
      SYNTAX      Integer32
      MAX-ACCESS  read-only
      STATUS      current
      DESCRIPTION "The UDP port on which this SNMP agent is listening for incoming requests from SNMP managers. SNMP agents can also communicate through the host server's TCP listen port (7001 by default) or through a TCP port that is configured by a custom network channel. "
      ::= { wlssnmpAgentRuntimeEntry 4  }
   
   
   wlssnmpAgentRuntimeLogMessageTrapCount OBJECT-TYPE
      SYNTAX      Counter64
      MAX-ACCESS  read-only
      STATUS      current
      DESCRIPTION "The number of log message notifications that this SNMP agent has sent to all trap destinations since the agent's host server was started. "
      ::= { wlssnmpAgentRuntimeEntry 5  }
   
   
   wlssnmpAgentRuntimeFailedAuthorizationCount OBJECT-TYPE
      SYNTAX      Integer32
      MAX-ACCESS  read-only
      STATUS      current
      DESCRIPTION "The number of requests that this agent has rejected because an authenticated user does not have sufficient privileges to view the requested information. You use the WebLogic Server security realm to assign privileges to users. "
      ::= { wlssnmpAgentRuntimeEntry 6  }
   
   
   wlssnmpAgentRuntimeRunning OBJECT-TYPE
      SYNTAX      OCTET STRING
      MAX-ACCESS  read-only
      STATUS      current
      DESCRIPTION "Indicates whether this SNMP agent is running. "
      ::= { wlssnmpAgentRuntimeEntry 7  }
   
   
   wlssnmpAgentRuntimeStringMonitorTrapCount OBJECT-TYPE
      SYNTAX      Counter64
      MAX-ACCESS  read-only
      STATUS      current
      DESCRIPTION "The number of string monitor notifications that this SNMP agent has sent to all trap destinations since the agent's host server was started. "
      ::= { wlssnmpAgentRuntimeEntry 8  }
   
   
   wlssnmpAgentRuntimeMonitorTrapCount OBJECT-TYPE
      SYNTAX      Counter64
      MAX-ACCESS  read-only
      STATUS      current
      DESCRIPTION "The total number of all notifications that this SNMP agent has sent to all trap destinations since the agent's host server was started. "
      ::= { wlssnmpAgentRuntimeEntry 9  }
   
   
   wlssnmpAgentRuntimeMasterAgentXPort OBJECT-TYPE
      SYNTAX      Integer32
      MAX-ACCESS  read-only
      STATUS      current
      DESCRIPTION "The port that this SNMP agent uses to communicate with subagents. The agent uses subagents to provide access to custom MBeans (MBeans that you create and register) and to other Oracle software components. WebLogic Server SNMP agents do not enable users to register their own subagents. "
      ::= { wlssnmpAgentRuntimeEntry 10  }
   
   
   wlssnmpAgentRuntimeGaugeMonitorTrapCount OBJECT-TYPE
      SYNTAX      Counter64
      MAX-ACCESS  read-only
      STATUS      current
      DESCRIPTION "The number of gauge monitor notifications that this SNMP agent has sent to all trap destinations since the agent's host server was started. "
      ::= { wlssnmpAgentRuntimeEntry 11  }
   
   
   wlssnmpAgentRuntimeServerStopTrapCount OBJECT-TYPE
      SYNTAX      Counter64
      MAX-ACCESS  read-only
      STATUS      current
      DESCRIPTION "The number of serverShutdown notifications that this SNMP agent has sent to all trap destinations since the agent's host server was started. "
      ::= { wlssnmpAgentRuntimeEntry 12  }
   
   
   wlssnmpAgentRuntimeAttributeChangeTrapCount OBJECT-TYPE
      SYNTAX      Counter64
      MAX-ACCESS  read-only
      STATUS      current
      DESCRIPTION "The number of attribute change notifications that this SNMP agent has sent to all trap destinations since the agent's host server was started. "
      ::= { wlssnmpAgentRuntimeEntry 13  }
   
   
   wlssnmpAgentRuntimeServerStartTrapCount OBJECT-TYPE
      SYNTAX      Counter64
      MAX-ACCESS  read-only
      STATUS      current
      DESCRIPTION "The number of serverStart notifications that this SNMP agent has sent to all trap destinations since the agent's host server was started. "
      ::= { wlssnmpAgentRuntimeEntry 14  }
   
   
   wlssnmpAgentRuntimeFailedAuthenticationCount OBJECT-TYPE
      SYNTAX      Integer32
      MAX-ACCESS  read-only
      STATUS      current
      DESCRIPTION "The number of requests that this agent has rejected because of incorrect user credentials. "
      ::= { wlssnmpAgentRuntimeEntry 15  }
   
   
   wlssnmpAgentRuntimeCounterMonitorTrapCount OBJECT-TYPE
      SYNTAX      Counter64
      MAX-ACCESS  read-only
      STATUS      current
      DESCRIPTION "The number of counter monitor notifications that this SNMP agent has sent to all trap destinations since the agent's host server was started. "
      ::= { wlssnmpAgentRuntimeEntry 16  }
   
   
   wlssnmpAgentRuntimeName OBJECT-TYPE
      SYNTAX      OCTET STRING
      MAX-ACCESS  read-only
      STATUS      current
      DESCRIPTION "The name of this configuration. WebLogic Server uses an MBean to implement and persist the configuration. "
      ::= { wlssnmpAgentRuntimeEntry 17  }
   
   
   wlssnmpAgentRuntimeFailedEncryptionCount OBJECT-TYPE
      SYNTAX      Integer32
      MAX-ACCESS  read-only
      STATUS      current
      DESCRIPTION "The number of requests that this agent has rejected because of incorrect privacy (encryption) credentials "
      ::= { wlssnmpAgentRuntimeEntry 18  }
   
   
   wlssnmpAgentRuntimeSNMPAgentName OBJECT-TYPE
      SYNTAX      OCTET STRING
      MAX-ACCESS  read-only
      STATUS      current
      DESCRIPTION "Gets the name of the SNMPAgent MBean configuration that is currently active. Returns null if no SNMPAgent configuration is currently active on this Server. "
      ::= { wlssnmpAgentRuntimeEntry 19  }
   
   
   serverLifeCycleTaskRuntimeTable OBJECT-TYPE
      SYNTAX      SEQUENCE OF ServerLifeCycleTaskRuntimeEntry
      MAX-ACCESS  not-accessible
      STATUS      current
      DESCRIPTION "Exposes monitoring information about a server's lifecycle. Remote clients as well as clients running within a server can access this information.  An operation (task) to change a server's state will fork a separate thread to perform the actual work and immediately return an instance of this MBean to the caller. The caller can then use this MBean to track the task's progress as desired. "
      ::= { wls 1345  }
      
   
   serverLifeCycleTaskRuntimeEntry OBJECT-TYPE
      SYNTAX      ServerLifeCycleTaskRuntimeEntry
      MAX-ACCESS  not-accessible
      STATUS      current
      DESCRIPTION "Generated SNMP Table Entry."
      INDEX { serverLifeCycleTaskRuntimeIndex}
      ::= { serverLifeCycleTaskRuntimeTable 1 }
      
   ServerLifeCycleTaskRuntimeEntry ::=
      SEQUENCE
      {
         serverLifeCycleTaskRuntimeIndex OCTET STRING,
         serverLifeCycleTaskRuntimeObjectName OCTET STRING,
         serverLifeCycleTaskRuntimeType OCTET STRING,
         serverLifeCycleTaskRuntimeStatus OCTET STRING,
         serverLifeCycleTaskRuntimeRunning OCTET STRING,
         serverLifeCycleTaskRuntimeBeginTime Counter64,
         serverLifeCycleTaskRuntimeOperation OCTET STRING,
         serverLifeCycleTaskRuntimeEndTime Counter64,
         serverLifeCycleTaskRuntimeServerName OCTET STRING,
         serverLifeCycleTaskRuntimeSystemTask OCTET STRING,
         serverLifeCycleTaskRuntimeDescription OCTET STRING,
         serverLifeCycleTaskRuntimeName OCTET STRING,
         serverLifeCycleTaskRuntimeProgress OCTET STRING
      }
      
   
   serverLifeCycleTaskRuntimeIndex OBJECT-TYPE
      SYNTAX      OCTET STRING
      MAX-ACCESS  not-accessible
      STATUS      current
      DESCRIPTION "Index column"
      ::= { serverLifeCycleTaskRuntimeEntry 1  }
   
   
   serverLifeCycleTaskRuntimeObjectName OBJECT-TYPE
      SYNTAX      OCTET STRING
      MAX-ACCESS  read-only
      STATUS      current
      DESCRIPTION "ObjectName column"
      ::= { serverLifeCycleTaskRuntimeEntry 2  }
   
   
   serverLifeCycleTaskRuntimeType OBJECT-TYPE
      SYNTAX      OCTET STRING
      MAX-ACCESS  read-only
      STATUS      current
      DESCRIPTION "Returns the type of the MBean. "
      ::= { serverLifeCycleTaskRuntimeEntry 3  }
   
   
   serverLifeCycleTaskRuntimeStatus OBJECT-TYPE
      SYNTAX      OCTET STRING
      MAX-ACCESS  read-only
      STATUS      current
      DESCRIPTION "The status of this task. "
      ::= { serverLifeCycleTaskRuntimeEntry 4  }
   
   
   serverLifeCycleTaskRuntimeRunning OBJECT-TYPE
      SYNTAX      OCTET STRING
      MAX-ACCESS  read-only
      STATUS      current
      DESCRIPTION "Indicates whether the task is still running. "
      ::= { serverLifeCycleTaskRuntimeEntry 5  }
   
   
   serverLifeCycleTaskRuntimeBeginTime OBJECT-TYPE
      SYNTAX      Counter64
      MAX-ACCESS  read-only
      STATUS      current
      DESCRIPTION "The time at which this task was started. "
      ::= { serverLifeCycleTaskRuntimeEntry 6  }
   
   
   serverLifeCycleTaskRuntimeOperation OBJECT-TYPE
      SYNTAX      OCTET STRING
      MAX-ACCESS  read-only
      STATUS      current
      DESCRIPTION "Gets the name of the method that was invoked on the ServerLifeCycleRuntime to initiate this task. "
      ::= { serverLifeCycleTaskRuntimeEntry 7  }
   
   
   serverLifeCycleTaskRuntimeEndTime OBJECT-TYPE
      SYNTAX      Counter64
      MAX-ACCESS  read-only
      STATUS      current
      DESCRIPTION "The time at which this task was completed.  A value of -1 indicates that the task is currently running. "
      ::= { serverLifeCycleTaskRuntimeEntry 8  }
   
   
   serverLifeCycleTaskRuntimeServerName OBJECT-TYPE
      SYNTAX      OCTET STRING
      MAX-ACCESS  read-only
      STATUS      current
      DESCRIPTION "The name of the server. "
      ::= { serverLifeCycleTaskRuntimeEntry 9  }
   
   
   serverLifeCycleTaskRuntimeSystemTask OBJECT-TYPE
      SYNTAX      OCTET STRING
      MAX-ACCESS  read-only
      STATUS      current
      DESCRIPTION "Indicates whether this task was initiated by the server versus a user. "
      ::= { serverLifeCycleTaskRuntimeEntry 10  }
   
   
   serverLifeCycleTaskRuntimeDescription OBJECT-TYPE
      SYNTAX      OCTET STRING
      MAX-ACCESS  read-only
      STATUS      current
      DESCRIPTION "A description of this task. "
      ::= { serverLifeCycleTaskRuntimeEntry 11  }
   
   
   serverLifeCycleTaskRuntimeName OBJECT-TYPE
      SYNTAX      OCTET STRING
      MAX-ACCESS  read-only
      STATUS      current
      DESCRIPTION "The name of this configuration. WebLogic Server uses an MBean to implement and persist the configuration. "
      ::= { serverLifeCycleTaskRuntimeEntry 12  }
   
   
   serverLifeCycleTaskRuntimeProgress OBJECT-TYPE
      SYNTAX      OCTET STRING
      MAX-ACCESS  read-only
      STATUS      current
      DESCRIPTION "The progress of this task. "
      ::= { serverLifeCycleTaskRuntimeEntry 13  }
   
   
   serverMigrationRuntimeTable OBJECT-TYPE
      SYNTAX      SEQUENCE OF ServerMigrationRuntimeEntry
      MAX-ACCESS  not-accessible
      STATUS      current
      DESCRIPTION "ServerMigrationRuntimeMBean provides runtime monitoring information about the past migrations performed by this server as the cluster master. If this server was never the cluster master then no information would be available. This RuntimeMBean would be hosted on all cluster members and can be queried for the location of the cluster master which is just another peer in the cluster. JMX clients can make another call to the server hosting the cluster master functionality to get the migration history.  Please note that the migration history is not persisted and is lost when a server is shutdown.  "
      ::= { wls 1350  }
      
   
   serverMigrationRuntimeEntry OBJECT-TYPE
      SYNTAX      ServerMigrationRuntimeEntry
      MAX-ACCESS  not-accessible
      STATUS      current
      DESCRIPTION "Generated SNMP Table Entry."
      INDEX { serverMigrationRuntimeIndex}
      ::= { serverMigrationRuntimeTable 1 }
      
   ServerMigrationRuntimeEntry ::=
      SEQUENCE
      {
         serverMigrationRuntimeIndex OCTET STRING,
         serverMigrationRuntimeObjectName OCTET STRING,
         serverMigrationRuntimeType OCTET STRING,
         serverMigrationRuntimeClusterMaster OCTET STRING,
         serverMigrationRuntimeClusterMasterName OCTET STRING,
         serverMigrationRuntimeName OCTET STRING
      }
      
   
   serverMigrationRuntimeIndex OBJECT-TYPE
      SYNTAX      OCTET STRING
      MAX-ACCESS  not-accessible
      STATUS      current
      DESCRIPTION "Index column"
      ::= { serverMigrationRuntimeEntry 1  }
   
   
   serverMigrationRuntimeObjectName OBJECT-TYPE
      SYNTAX      OCTET STRING
      MAX-ACCESS  read-only
      STATUS      current
      DESCRIPTION "ObjectName column"
      ::= { serverMigrationRuntimeEntry 2  }
   
   
   serverMigrationRuntimeType OBJECT-TYPE
      SYNTAX      OCTET STRING
      MAX-ACCESS  read-only
      STATUS      current
      DESCRIPTION "Returns the type of the MBean. "
      ::= { serverMigrationRuntimeEntry 3  }
   
   
   serverMigrationRuntimeClusterMaster OBJECT-TYPE
      SYNTAX      OCTET STRING
      MAX-ACCESS  read-only
      STATUS      current
      DESCRIPTION "Is the current server the cluster master? "
      ::= { serverMigrationRuntimeEntry 4  }
   
   
   serverMigrationRuntimeClusterMasterName OBJECT-TYPE
      SYNTAX      OCTET STRING
      MAX-ACCESS  read-only
      STATUS      current
      DESCRIPTION "Returns the server name who is the cluster master. Migration history is only available from the cluster master. "
      ::= { serverMigrationRuntimeEntry 5  }
   
   
   serverMigrationRuntimeName OBJECT-TYPE
      SYNTAX      OCTET STRING
      MAX-ACCESS  read-only
      STATUS      current
      DESCRIPTION "The name of this configuration. WebLogic Server uses an MBean to implement and persist the configuration. "
      ::= { serverMigrationRuntimeEntry 6  }
   
   
   serviceMigrationDataRuntimeTable OBJECT-TYPE
      SYNTAX      SEQUENCE OF ServiceMigrationDataRuntimeEntry
      MAX-ACCESS  not-accessible
      STATUS      current
      DESCRIPTION "Runtime information about one past or ongoing migration. "
      ::= { wls 1355  }
      
   
   serviceMigrationDataRuntimeEntry OBJECT-TYPE
      SYNTAX      ServiceMigrationDataRuntimeEntry
      MAX-ACCESS  not-accessible
      STATUS      current
      DESCRIPTION "Generated SNMP Table Entry."
      INDEX { serviceMigrationDataRuntimeIndex}
      ::= { serviceMigrationDataRuntimeTable 1 }
      
   ServiceMigrationDataRuntimeEntry ::=
      SEQUENCE
      {
         serviceMigrationDataRuntimeIndex OCTET STRING,
         serviceMigrationDataRuntimeObjectName OCTET STRING,
         serviceMigrationDataRuntimeType OCTET STRING,
         serviceMigrationDataRuntimeStatus Integer32,
         serviceMigrationDataRuntimeMigrationStartTime Counter64,
         serviceMigrationDataRuntimeMigratedFrom OCTET STRING,
         serviceMigrationDataRuntimeServerName OCTET STRING,
         serviceMigrationDataRuntimeMigratedTo OCTET STRING,
         serviceMigrationDataRuntimeMigrationEndTime Counter64,
         serviceMigrationDataRuntimeClusterName OCTET STRING,
         serviceMigrationDataRuntimeName OCTET STRING,
         serviceMigrationDataRuntimeCoordinatorName OCTET STRING,
         serviceMigrationDataRuntimeDestinationsAttempted OCTET STRING
      }
      
   
   serviceMigrationDataRuntimeIndex OBJECT-TYPE
      SYNTAX      OCTET STRING
      MAX-ACCESS  not-accessible
      STATUS      current
      DESCRIPTION "Index column"
      ::= { serviceMigrationDataRuntimeEntry 1  }
   
   
   serviceMigrationDataRuntimeObjectName OBJECT-TYPE
      SYNTAX      OCTET STRING
      MAX-ACCESS  read-only
      STATUS      current
      DESCRIPTION "ObjectName column"
      ::= { serviceMigrationDataRuntimeEntry 2  }
   
   
   serviceMigrationDataRuntimeType OBJECT-TYPE
      SYNTAX      OCTET STRING
      MAX-ACCESS  read-only
      STATUS      current
      DESCRIPTION "Returns the type of the MBean. "
      ::= { serviceMigrationDataRuntimeEntry 3  }
   
   
   serviceMigrationDataRuntimeStatus OBJECT-TYPE
      SYNTAX      Integer32
      MAX-ACCESS  read-only
      STATUS      current
      DESCRIPTION "Status of the migration (SUCCESSFUL, IN_PROGRESS, or FAILED) "
      ::= { serviceMigrationDataRuntimeEntry 4  }
   
   
   serviceMigrationDataRuntimeMigrationStartTime OBJECT-TYPE
      SYNTAX      Counter64
      MAX-ACCESS  read-only
      STATUS      current
      DESCRIPTION "Start time of migration "
      ::= { serviceMigrationDataRuntimeEntry 5  }
   
   
   serviceMigrationDataRuntimeMigratedFrom OBJECT-TYPE
      SYNTAX      OCTET STRING
      MAX-ACCESS  read-only
      STATUS      current
      DESCRIPTION "Where this object was migrated from "
      ::= { serviceMigrationDataRuntimeEntry 6  }
   
   
   serviceMigrationDataRuntimeServerName OBJECT-TYPE
      SYNTAX      OCTET STRING
      MAX-ACCESS  read-only
      STATUS      current
      DESCRIPTION "Name of the object migrated "
      ::= { serviceMigrationDataRuntimeEntry 7  }
   
   
   serviceMigrationDataRuntimeMigratedTo OBJECT-TYPE
      SYNTAX      OCTET STRING
      MAX-ACCESS  read-only
      STATUS      current
      DESCRIPTION "Where this object was migrated to "
      ::= { serviceMigrationDataRuntimeEntry 8  }
   
   
   serviceMigrationDataRuntimeMigrationEndTime OBJECT-TYPE
      SYNTAX      Counter64
      MAX-ACCESS  read-only
      STATUS      current
      DESCRIPTION "End time of migration "
      ::= { serviceMigrationDataRuntimeEntry 9  }
   
   
   serviceMigrationDataRuntimeClusterName OBJECT-TYPE
      SYNTAX      OCTET STRING
      MAX-ACCESS  read-only
      STATUS      current
      DESCRIPTION "Name of the cluster "
      ::= { serviceMigrationDataRuntimeEntry 10  }
   
   
   serviceMigrationDataRuntimeName OBJECT-TYPE
      SYNTAX      OCTET STRING
      MAX-ACCESS  read-only
      STATUS      current
      DESCRIPTION "The name of this configuration. WebLogic Server uses an MBean to implement and persist the configuration. "
      ::= { serviceMigrationDataRuntimeEntry 11  }
   
   
   serviceMigrationDataRuntimeCoordinatorName OBJECT-TYPE
      SYNTAX      OCTET STRING
      MAX-ACCESS  read-only
      STATUS      current
      DESCRIPTION "Name of the server that acted as the coordinator for this migration. "
      ::= { serviceMigrationDataRuntimeEntry 12  }
   
   
   serviceMigrationDataRuntimeDestinationsAttempted OBJECT-TYPE
      SYNTAX      OCTET STRING
      MAX-ACCESS  read-only
      STATUS      current
      DESCRIPTION "Get all the destinations attempted for migration. "
      ::= { serviceMigrationDataRuntimeEntry 13  }
   
   
   serviceMigrationRuntimeTable OBJECT-TYPE
      SYNTAX      SEQUENCE OF ServiceMigrationRuntimeEntry
      MAX-ACCESS  not-accessible
      STATUS      current
      DESCRIPTION "ServiceMigrationRuntimeMBean provides runtime monitoring information about the past migrations performed by this server as the cluster master. If this server was never the cluster master then no information would be available. This RuntimeMBean would be hosted on all cluster members and can be queried for the location of the cluster master which is just another peer in the cluster. JMX clients can make another call to the server hosting the cluster master functionality to get the migration history.  Please note that the migration history is not persisted and is lost when a server is shutdown.  "
      ::= { wls 1360  }
      
   
   serviceMigrationRuntimeEntry OBJECT-TYPE
      SYNTAX      ServiceMigrationRuntimeEntry
      MAX-ACCESS  not-accessible
      STATUS      current
      DESCRIPTION "Generated SNMP Table Entry."
      INDEX { serviceMigrationRuntimeIndex}
      ::= { serviceMigrationRuntimeTable 1 }
      
   ServiceMigrationRuntimeEntry ::=
      SEQUENCE
      {
         serviceMigrationRuntimeIndex OCTET STRING,
         serviceMigrationRuntimeObjectName OCTET STRING,
         serviceMigrationRuntimeType OCTET STRING,
         serviceMigrationRuntimeClusterMaster OCTET STRING,
         serviceMigrationRuntimeClusterMasterName OCTET STRING,
         serviceMigrationRuntimeName OCTET STRING
      }
      
   
   serviceMigrationRuntimeIndex OBJECT-TYPE
      SYNTAX      OCTET STRING
      MAX-ACCESS  not-accessible
      STATUS      current
      DESCRIPTION "Index column"
      ::= { serviceMigrationRuntimeEntry 1  }
   
   
   serviceMigrationRuntimeObjectName OBJECT-TYPE
      SYNTAX      OCTET STRING
      MAX-ACCESS  read-only
      STATUS      current
      DESCRIPTION "ObjectName column"
      ::= { serviceMigrationRuntimeEntry 2  }
   
   
   serviceMigrationRuntimeType OBJECT-TYPE
      SYNTAX      OCTET STRING
      MAX-ACCESS  read-only
      STATUS      current
      DESCRIPTION "Returns the type of the MBean. "
      ::= { serviceMigrationRuntimeEntry 3  }
   
   
   serviceMigrationRuntimeClusterMaster OBJECT-TYPE
      SYNTAX      OCTET STRING
      MAX-ACCESS  read-only
      STATUS      current
      DESCRIPTION "Is the current server the cluster master? "
      ::= { serviceMigrationRuntimeEntry 4  }
   
   
   serviceMigrationRuntimeClusterMasterName OBJECT-TYPE
      SYNTAX      OCTET STRING
      MAX-ACCESS  read-only
      STATUS      current
      DESCRIPTION "Returns the server name who is the cluster master. Migration history is only available from the cluster master. "
      ::= { serviceMigrationRuntimeEntry 5  }
   
   
   serviceMigrationRuntimeName OBJECT-TYPE
      SYNTAX      OCTET STRING
      MAX-ACCESS  read-only
      STATUS      current
      DESCRIPTION "The name of this configuration. WebLogic Server uses an MBean to implement and persist the configuration. "
      ::= { serviceMigrationRuntimeEntry 6  }
   
   
   singleSignOnServicesRuntimeTable OBJECT-TYPE
      SYNTAX      SEQUENCE OF SingleSignOnServicesRuntimeEntry
      MAX-ACCESS  not-accessible
      STATUS      current
      DESCRIPTION "This interface is used to publish SAML 2.0 local site meta-data for single sign-on services. "
      ::= { wls 1365  }
      
   
   singleSignOnServicesRuntimeEntry OBJECT-TYPE
      SYNTAX      SingleSignOnServicesRuntimeEntry
      MAX-ACCESS  not-accessible
      STATUS      current
      DESCRIPTION "Generated SNMP Table Entry."
      INDEX { singleSignOnServicesRuntimeIndex}
      ::= { singleSignOnServicesRuntimeTable 1 }
      
   SingleSignOnServicesRuntimeEntry ::=
      SEQUENCE
      {
         singleSignOnServicesRuntimeIndex OCTET STRING,
         singleSignOnServicesRuntimeObjectName OCTET STRING,
         singleSignOnServicesRuntimeType OCTET STRING,
         singleSignOnServicesRuntimeName OCTET STRING
      }
      
   
   singleSignOnServicesRuntimeIndex OBJECT-TYPE
      SYNTAX      OCTET STRING
      MAX-ACCESS  not-accessible
      STATUS      current
      DESCRIPTION "Index column"
      ::= { singleSignOnServicesRuntimeEntry 1  }
   
   
   singleSignOnServicesRuntimeObjectName OBJECT-TYPE
      SYNTAX      OCTET STRING
      MAX-ACCESS  read-only
      STATUS      current
      DESCRIPTION "ObjectName column"
      ::= { singleSignOnServicesRuntimeEntry 2  }
   
   
   singleSignOnServicesRuntimeType OBJECT-TYPE
      SYNTAX      OCTET STRING
      MAX-ACCESS  read-only
      STATUS      current
      DESCRIPTION "Returns the type of the MBean. "
      ::= { singleSignOnServicesRuntimeEntry 3  }
   
   
   singleSignOnServicesRuntimeName OBJECT-TYPE
      SYNTAX      OCTET STRING
      MAX-ACCESS  read-only
      STATUS      current
      DESCRIPTION "The name of this configuration. WebLogic Server uses an MBean to implement and persist the configuration. "
      ::= { singleSignOnServicesRuntimeEntry 4  }
   
   
   springRuntimeTable OBJECT-TYPE
      SYNTAX      SEQUENCE OF SpringRuntimeEntry
      MAX-ACCESS  not-accessible
      STATUS      current
      DESCRIPTION " "
      ::= { wls 1385  }
      
   
   springRuntimeEntry OBJECT-TYPE
      SYNTAX      SpringRuntimeEntry
      MAX-ACCESS  not-accessible
      STATUS      current
      DESCRIPTION "Generated SNMP Table Entry."
      INDEX { springRuntimeIndex}
      ::= { springRuntimeTable 1 }
      
   SpringRuntimeEntry ::=
      SEQUENCE
      {
         springRuntimeIndex   OCTET STRING,
         springRuntimeObjectName OCTET STRING,
         springRuntimeType    OCTET STRING,
         springRuntimeName    OCTET STRING,
         springRuntimeSpringVersion OCTET STRING
      }
      
   
   springRuntimeIndex OBJECT-TYPE
      SYNTAX      OCTET STRING
      MAX-ACCESS  not-accessible
      STATUS      current
      DESCRIPTION "Index column"
      ::= { springRuntimeEntry 1  }
   
   
   springRuntimeObjectName OBJECT-TYPE
      SYNTAX      OCTET STRING
      MAX-ACCESS  read-only
      STATUS      current
      DESCRIPTION "ObjectName column"
      ::= { springRuntimeEntry 2  }
   
   
   springRuntimeType OBJECT-TYPE
      SYNTAX      OCTET STRING
      MAX-ACCESS  read-only
      STATUS      current
      DESCRIPTION "Returns the type of the MBean. "
      ::= { springRuntimeEntry 3  }
   
   
   springRuntimeName OBJECT-TYPE
      SYNTAX      OCTET STRING
      MAX-ACCESS  read-only
      STATUS      current
      DESCRIPTION "The name of this configuration. WebLogic Server uses an MBean to implement and persist the configuration. "
      ::= { springRuntimeEntry 4  }
   
   
   springRuntimeSpringVersion OBJECT-TYPE
      SYNTAX      OCTET STRING
      MAX-ACCESS  read-only
      STATUS      current
      DESCRIPTION "Get the version number of the Spring Framework. "
      ::= { springRuntimeEntry 5  }
   
   
   springTransactionManagerRuntimeTable OBJECT-TYPE
      SYNTAX      SEQUENCE OF SpringTransactionManagerRuntimeEntry
      MAX-ACCESS  not-accessible
      STATUS      current
      DESCRIPTION "This MBean represents statistics gathered for org.springframework.transaction.support.AbstractPlatformTransactionManager "
      ::= { wls 1390  }
      
   
   springTransactionManagerRuntimeEntry OBJECT-TYPE
      SYNTAX      SpringTransactionManagerRuntimeEntry
      MAX-ACCESS  not-accessible
      STATUS      current
      DESCRIPTION "Generated SNMP Table Entry."
      INDEX { springTransactionManagerRuntimeIndex}
      ::= { springTransactionManagerRuntimeTable 1 }
      
   SpringTransactionManagerRuntimeEntry ::=
      SEQUENCE
      {
         springTransactionManagerRuntimeIndex OCTET STRING,
         springTransactionManagerRuntimeObjectName OCTET STRING,
         springTransactionManagerRuntimeType OCTET STRING,
         springTransactionManagerRuntimeBeanId OCTET STRING,
         springTransactionManagerRuntimeName OCTET STRING,
         springTransactionManagerRuntimeSuspendCount Counter64,
         springTransactionManagerRuntimeApplicationContextDisplayName OCTET STRING,
         springTransactionManagerRuntimeCommitCount Counter64,
         springTransactionManagerRuntimeResumeCount Counter64,
         springTransactionManagerRuntimeRollbackCount Counter64
      }
      
   
   springTransactionManagerRuntimeIndex OBJECT-TYPE
      SYNTAX      OCTET STRING
      MAX-ACCESS  not-accessible
      STATUS      current
      DESCRIPTION "Index column"
      ::= { springTransactionManagerRuntimeEntry 1  }
   
   
   springTransactionManagerRuntimeObjectName OBJECT-TYPE
      SYNTAX      OCTET STRING
      MAX-ACCESS  read-only
      STATUS      current
      DESCRIPTION "ObjectName column"
      ::= { springTransactionManagerRuntimeEntry 2  }
   
   
   springTransactionManagerRuntimeType OBJECT-TYPE
      SYNTAX      OCTET STRING
      MAX-ACCESS  read-only
      STATUS      current
      DESCRIPTION "Returns the type of the MBean. "
      ::= { springTransactionManagerRuntimeEntry 3  }
   
   
   springTransactionManagerRuntimeBeanId OBJECT-TYPE
      SYNTAX      OCTET STRING
      MAX-ACCESS  read-only
      STATUS      current
      DESCRIPTION "Name of the Spring bean. "
      ::= { springTransactionManagerRuntimeEntry 13  }
   
   
   springTransactionManagerRuntimeName OBJECT-TYPE
      SYNTAX      OCTET STRING
      MAX-ACCESS  read-only
      STATUS      current
      DESCRIPTION "The name of this configuration. WebLogic Server uses an MBean to implement and persist the configuration. "
      ::= { springTransactionManagerRuntimeEntry 17  }
   
   
   springTransactionManagerRuntimeSuspendCount OBJECT-TYPE
      SYNTAX      Counter64
      MAX-ACCESS  read-only
      STATUS      current
      DESCRIPTION "This returns the number of time suspend was called "
      ::= { springTransactionManagerRuntimeEntry 19  }
   
   
   springTransactionManagerRuntimeApplicationContextDisplayName OBJECT-TYPE
      SYNTAX      OCTET STRING
      MAX-ACCESS  read-only
      STATUS      current
      DESCRIPTION "The display name of the Application Context that this bean is from "
      ::= { springTransactionManagerRuntimeEntry 20  }
   
   
   springTransactionManagerRuntimeCommitCount OBJECT-TYPE
      SYNTAX      Counter64
      MAX-ACCESS  read-only
      STATUS      current
      DESCRIPTION "This returns the number of time commit was called "
      ::= { springTransactionManagerRuntimeEntry 21  }
   
   
   springTransactionManagerRuntimeResumeCount OBJECT-TYPE
      SYNTAX      Counter64
      MAX-ACCESS  read-only
      STATUS      current
      DESCRIPTION "This returns the number of time resume was called "
      ::= { springTransactionManagerRuntimeEntry 22  }
   
   
   springTransactionManagerRuntimeRollbackCount OBJECT-TYPE
      SYNTAX      Counter64
      MAX-ACCESS  read-only
      STATUS      current
      DESCRIPTION "This returns the number of time rollback was called "
      ::= { springTransactionManagerRuntimeEntry 23  }
   
   
   statefulEJBRuntimeTable OBJECT-TYPE
      SYNTAX      SEQUENCE OF StatefulEJBRuntimeEntry
      MAX-ACCESS  not-accessible
      STATUS      current
      DESCRIPTION "This interface contains accessor methods for all EJB runtime information collected for a Stateful Session Bean. "
      ::= { wls 1395  }
      
   
   statefulEJBRuntimeEntry OBJECT-TYPE
      SYNTAX      StatefulEJBRuntimeEntry
      MAX-ACCESS  not-accessible
      STATUS      current
      DESCRIPTION "Generated SNMP Table Entry."
      INDEX { statefulEJBRuntimeIndex}
      ::= { statefulEJBRuntimeTable 1 }
      
   StatefulEJBRuntimeEntry ::=
      SEQUENCE
      {
         statefulEJBRuntimeIndex OCTET STRING,
         statefulEJBRuntimeObjectName OCTET STRING,
         statefulEJBRuntimeType OCTET STRING,
         statefulEJBRuntimeEJBName OCTET STRING,
         statefulEJBRuntimeName OCTET STRING
      }
      
   
   statefulEJBRuntimeIndex OBJECT-TYPE
      SYNTAX      OCTET STRING
      MAX-ACCESS  not-accessible
      STATUS      current
      DESCRIPTION "Index column"
      ::= { statefulEJBRuntimeEntry 1  }
   
   
   statefulEJBRuntimeObjectName OBJECT-TYPE
      SYNTAX      OCTET STRING
      MAX-ACCESS  read-only
      STATUS      current
      DESCRIPTION "ObjectName column"
      ::= { statefulEJBRuntimeEntry 2  }
   
   
   statefulEJBRuntimeType OBJECT-TYPE
      SYNTAX      OCTET STRING
      MAX-ACCESS  read-only
      STATUS      current
      DESCRIPTION "Returns the type of the MBean. "
      ::= { statefulEJBRuntimeEntry 3  }
   
   
   statefulEJBRuntimeEJBName OBJECT-TYPE
      SYNTAX      OCTET STRING
      MAX-ACCESS  read-only
      STATUS      current
      DESCRIPTION "Provides the name for this EJB as defined in the javax.ejb.EJB annotation, or the ejb-name when * using the ejb-jar.xml deployment descriptor. "
      ::= { statefulEJBRuntimeEntry 4  }
   
   
   statefulEJBRuntimeName OBJECT-TYPE
      SYNTAX      OCTET STRING
      MAX-ACCESS  read-only
      STATUS      current
      DESCRIPTION "The name of this configuration. WebLogic Server uses an MBean to implement and persist the configuration. "
      ::= { statefulEJBRuntimeEntry 5  }
   
   
   statelessEJBRuntimeTable OBJECT-TYPE
      SYNTAX      SEQUENCE OF StatelessEJBRuntimeEntry
      MAX-ACCESS  not-accessible
      STATUS      current
      DESCRIPTION "This interface contains accessor methods for all EJB runtime information collected for a Stateless Session Bean. "
      ::= { wls 1400  }
      
   
   statelessEJBRuntimeEntry OBJECT-TYPE
      SYNTAX      StatelessEJBRuntimeEntry
      MAX-ACCESS  not-accessible
      STATUS      current
      DESCRIPTION "Generated SNMP Table Entry."
      INDEX { statelessEJBRuntimeIndex}
      ::= { statelessEJBRuntimeTable 1 }
      
   StatelessEJBRuntimeEntry ::=
      SEQUENCE
      {
         statelessEJBRuntimeIndex OCTET STRING,
         statelessEJBRuntimeObjectName OCTET STRING,
         statelessEJBRuntimeType OCTET STRING,
         statelessEJBRuntimeEJBName OCTET STRING,
         statelessEJBRuntimeName OCTET STRING
      }
      
   
   statelessEJBRuntimeIndex OBJECT-TYPE
      SYNTAX      OCTET STRING
      MAX-ACCESS  not-accessible
      STATUS      current
      DESCRIPTION "Index column"
      ::= { statelessEJBRuntimeEntry 1  }
   
   
   statelessEJBRuntimeObjectName OBJECT-TYPE
      SYNTAX      OCTET STRING
      MAX-ACCESS  read-only
      STATUS      current
      DESCRIPTION "ObjectName column"
      ::= { statelessEJBRuntimeEntry 2  }
   
   
   statelessEJBRuntimeType OBJECT-TYPE
      SYNTAX      OCTET STRING
      MAX-ACCESS  read-only
      STATUS      current
      DESCRIPTION "Returns the type of the MBean. "
      ::= { statelessEJBRuntimeEntry 3  }
   
   
   statelessEJBRuntimeEJBName OBJECT-TYPE
      SYNTAX      OCTET STRING
      MAX-ACCESS  read-only
      STATUS      current
      DESCRIPTION "Provides the name for this EJB as defined in the javax.ejb.EJB annotation, or the ejb-name when * using the ejb-jar.xml deployment descriptor. "
      ::= { statelessEJBRuntimeEntry 4  }
   
   
   statelessEJBRuntimeName OBJECT-TYPE
      SYNTAX      OCTET STRING
      MAX-ACCESS  read-only
      STATUS      current
      DESCRIPTION "The name of this configuration. WebLogic Server uses an MBean to implement and persist the configuration. "
      ::= { statelessEJBRuntimeEntry 5  }
   
   
   timerRuntimeTable OBJECT-TYPE
      SYNTAX      SEQUENCE OF TimerRuntimeEntry
      MAX-ACCESS  not-accessible
      STATUS      current
      DESCRIPTION "This RuntimeMBean exposes information about all active timers present in the WebLogic timer implementation. "
      ::= { wls 1410  }
      
   
   timerRuntimeEntry OBJECT-TYPE
      SYNTAX      TimerRuntimeEntry
      MAX-ACCESS  not-accessible
      STATUS      current
      DESCRIPTION "Generated SNMP Table Entry."
      INDEX { timerRuntimeIndex}
      ::= { timerRuntimeTable 1 }
      
   TimerRuntimeEntry ::=
      SEQUENCE
      {
         timerRuntimeIndex    OCTET STRING,
         timerRuntimeObjectName OCTET STRING,
         timerRuntimeType     OCTET STRING,
         timerRuntimeName     OCTET STRING
      }
      
   
   timerRuntimeIndex OBJECT-TYPE
      SYNTAX      OCTET STRING
      MAX-ACCESS  not-accessible
      STATUS      current
      DESCRIPTION "Index column"
      ::= { timerRuntimeEntry 1  }
   
   
   timerRuntimeObjectName OBJECT-TYPE
      SYNTAX      OCTET STRING
      MAX-ACCESS  read-only
      STATUS      current
      DESCRIPTION "ObjectName column"
      ::= { timerRuntimeEntry 2  }
   
   
   timerRuntimeType OBJECT-TYPE
      SYNTAX      OCTET STRING
      MAX-ACCESS  read-only
      STATUS      current
      DESCRIPTION "Returns the type of the MBean. "
      ::= { timerRuntimeEntry 3  }
   
   
   timerRuntimeName OBJECT-TYPE
      SYNTAX      OCTET STRING
      MAX-ACCESS  read-only
      STATUS      current
      DESCRIPTION "The name of this configuration. WebLogic Server uses an MBean to implement and persist the configuration. "
      ::= { timerRuntimeEntry 4  }
   
   
   unicastMessagingRuntimeTable OBJECT-TYPE
      SYNTAX      SEQUENCE OF UnicastMessagingRuntimeEntry
      MAX-ACCESS  not-accessible
      STATUS      current
      DESCRIPTION "Monitoring information when unicast messaging is turned on "
      ::= { wls 1420  }
      
   
   unicastMessagingRuntimeEntry OBJECT-TYPE
      SYNTAX      UnicastMessagingRuntimeEntry
      MAX-ACCESS  not-accessible
      STATUS      current
      DESCRIPTION "Generated SNMP Table Entry."
      INDEX { unicastMessagingRuntimeIndex}
      ::= { unicastMessagingRuntimeTable 1 }
      
   UnicastMessagingRuntimeEntry ::=
      SEQUENCE
      {
         unicastMessagingRuntimeIndex OCTET STRING,
         unicastMessagingRuntimeObjectName OCTET STRING,
         unicastMessagingRuntimeType OCTET STRING,
         unicastMessagingRuntimeRemoteGroupsDiscoveredCount Integer32,
         unicastMessagingRuntimeTotalGroupsCount Integer32,
         unicastMessagingRuntimeLocalGroupLeaderName OCTET STRING,
         unicastMessagingRuntimeGroups OCTET STRING,
         unicastMessagingRuntimeName OCTET STRING,
         unicastMessagingRuntimeDiscoveredGroupLeaders OCTET STRING
      }
      
   
   unicastMessagingRuntimeIndex OBJECT-TYPE
      SYNTAX      OCTET STRING
      MAX-ACCESS  not-accessible
      STATUS      current
      DESCRIPTION "Index column"
      ::= { unicastMessagingRuntimeEntry 1  }
   
   
   unicastMessagingRuntimeObjectName OBJECT-TYPE
      SYNTAX      OCTET STRING
      MAX-ACCESS  read-only
      STATUS      current
      DESCRIPTION "ObjectName column"
      ::= { unicastMessagingRuntimeEntry 2  }
   
   
   unicastMessagingRuntimeType OBJECT-TYPE
      SYNTAX      OCTET STRING
      MAX-ACCESS  read-only
      STATUS      current
      DESCRIPTION "Returns the type of the MBean. "
      ::= { unicastMessagingRuntimeEntry 3  }
   
   
   unicastMessagingRuntimeRemoteGroupsDiscoveredCount OBJECT-TYPE
      SYNTAX      Integer32
      MAX-ACCESS  read-only
      STATUS      current
      DESCRIPTION "Returns the total groups discovered by this server "
      ::= { unicastMessagingRuntimeEntry 4  }
   
   
   unicastMessagingRuntimeTotalGroupsCount OBJECT-TYPE
      SYNTAX      Integer32
      MAX-ACCESS  read-only
      STATUS      current
      DESCRIPTION "Total configured groups - running and not running "
      ::= { unicastMessagingRuntimeEntry 5  }
   
   
   unicastMessagingRuntimeLocalGroupLeaderName OBJECT-TYPE
      SYNTAX      OCTET STRING
      MAX-ACCESS  read-only
      STATUS      current
      DESCRIPTION "Name of the local group leader "
      ::= { unicastMessagingRuntimeEntry 6  }
   
   
   unicastMessagingRuntimeGroups OBJECT-TYPE
      SYNTAX      OCTET STRING
      MAX-ACCESS  read-only
      STATUS      current
      DESCRIPTION "Formatted group list "
      ::= { unicastMessagingRuntimeEntry 7  }
   
   
   unicastMessagingRuntimeName OBJECT-TYPE
      SYNTAX      OCTET STRING
      MAX-ACCESS  read-only
      STATUS      current
      DESCRIPTION "The name of this configuration. WebLogic Server uses an MBean to implement and persist the configuration. "
      ::= { unicastMessagingRuntimeEntry 8  }
   
   
   unicastMessagingRuntimeDiscoveredGroupLeaders OBJECT-TYPE
      SYNTAX      OCTET STRING
      MAX-ACCESS  read-only
      STATUS      current
      DESCRIPTION "Running group leader names "
      ::= { unicastMessagingRuntimeEntry 9  }
   
   
   wldfAccessRuntimeTable OBJECT-TYPE
      SYNTAX      SEQUENCE OF WldfAccessRuntimeEntry
      MAX-ACCESS  not-accessible
      STATUS      current
      DESCRIPTION "Use this interface to access the different types of diagnostic data generated by a server. "
      ::= { wls 1425  }
      
   
   wldfAccessRuntimeEntry OBJECT-TYPE
      SYNTAX      WldfAccessRuntimeEntry
      MAX-ACCESS  not-accessible
      STATUS      current
      DESCRIPTION "Generated SNMP Table Entry."
      INDEX { wldfAccessRuntimeIndex}
      ::= { wldfAccessRuntimeTable 1 }
      
   WldfAccessRuntimeEntry ::=
      SEQUENCE
      {
         wldfAccessRuntimeIndex OCTET STRING,
         wldfAccessRuntimeObjectName OCTET STRING,
         wldfAccessRuntimeType OCTET STRING,
         wldfAccessRuntimeName OCTET STRING,
         wldfAccessRuntimeAvailableDiagnosticDataAccessorNames OCTET STRING
      }
      
   
   wldfAccessRuntimeIndex OBJECT-TYPE
      SYNTAX      OCTET STRING
      MAX-ACCESS  not-accessible
      STATUS      current
      DESCRIPTION "Index column"
      ::= { wldfAccessRuntimeEntry 1  }
   
   
   wldfAccessRuntimeObjectName OBJECT-TYPE
      SYNTAX      OCTET STRING
      MAX-ACCESS  read-only
      STATUS      current
      DESCRIPTION "ObjectName column"
      ::= { wldfAccessRuntimeEntry 2  }
   
   
   wldfAccessRuntimeType OBJECT-TYPE
      SYNTAX      OCTET STRING
      MAX-ACCESS  read-only
      STATUS      current
      DESCRIPTION "Returns the type of the MBean. "
      ::= { wldfAccessRuntimeEntry 3  }
   
   
   wldfAccessRuntimeName OBJECT-TYPE
      SYNTAX      OCTET STRING
      MAX-ACCESS  read-only
      STATUS      current
      DESCRIPTION "The name of this configuration. WebLogic Server uses an MBean to implement and persist the configuration. "
      ::= { wldfAccessRuntimeEntry 4  }
   
   
   wldfAccessRuntimeAvailableDiagnosticDataAccessorNames OBJECT-TYPE
      SYNTAX      OCTET STRING
      MAX-ACCESS  read-only
      STATUS      current
      DESCRIPTION " "
      ::= { wldfAccessRuntimeEntry 5  }
   
   
   wldfDataAccessRuntimeTable OBJECT-TYPE
      SYNTAX      SEQUENCE OF WldfDataAccessRuntimeEntry
      MAX-ACCESS  not-accessible
      STATUS      current
      DESCRIPTION "Use this interface to access the specific type of diagnostic data from an underlying log for which this instance is created. "
      ::= { wls 1430  }
      
   
   wldfDataAccessRuntimeEntry OBJECT-TYPE
      SYNTAX      WldfDataAccessRuntimeEntry
      MAX-ACCESS  not-accessible
      STATUS      current
      DESCRIPTION "Generated SNMP Table Entry."
      INDEX { wldfDataAccessRuntimeIndex}
      ::= { wldfDataAccessRuntimeTable 1 }
      
   WldfDataAccessRuntimeEntry ::=
      SEQUENCE
      {
         wldfDataAccessRuntimeIndex OCTET STRING,
         wldfDataAccessRuntimeObjectName OCTET STRING,
         wldfDataAccessRuntimeType OCTET STRING,
         wldfDataAccessRuntimeEarliestAvailableTimestamp Counter64,
         wldfDataAccessRuntimeLatestAvailableTimestamp Counter64,
         wldfDataAccessRuntimeTimestampAvailable OCTET STRING,
         wldfDataAccessRuntimeName OCTET STRING,
         wldfDataAccessRuntimeLatestRecordId Counter64
      }
      
   
   wldfDataAccessRuntimeIndex OBJECT-TYPE
      SYNTAX      OCTET STRING
      MAX-ACCESS  not-accessible
      STATUS      current
      DESCRIPTION "Index column"
      ::= { wldfDataAccessRuntimeEntry 1  }
   
   
   wldfDataAccessRuntimeObjectName OBJECT-TYPE
      SYNTAX      OCTET STRING
      MAX-ACCESS  read-only
      STATUS      current
      DESCRIPTION "ObjectName column"
      ::= { wldfDataAccessRuntimeEntry 2  }
   
   
   wldfDataAccessRuntimeType OBJECT-TYPE
      SYNTAX      OCTET STRING
      MAX-ACCESS  read-only
      STATUS      current
      DESCRIPTION "Returns the type of the MBean. "
      ::= { wldfDataAccessRuntimeEntry 3  }
   
   
   wldfDataAccessRuntimeEarliestAvailableTimestamp OBJECT-TYPE
      SYNTAX      Counter64
      MAX-ACCESS  read-only
      STATUS      current
      DESCRIPTION " "
      ::= { wldfDataAccessRuntimeEntry 4  }
   
   
   wldfDataAccessRuntimeLatestAvailableTimestamp OBJECT-TYPE
      SYNTAX      Counter64
      MAX-ACCESS  read-only
      STATUS      current
      DESCRIPTION " "
      ::= { wldfDataAccessRuntimeEntry 5  }
   
   
   wldfDataAccessRuntimeTimestampAvailable OBJECT-TYPE
      SYNTAX      OCTET STRING
      MAX-ACCESS  read-only
      STATUS      current
      DESCRIPTION " "
      ::= { wldfDataAccessRuntimeEntry 6  }
   
   
   wldfDataAccessRuntimeName OBJECT-TYPE
      SYNTAX      OCTET STRING
      MAX-ACCESS  read-only
      STATUS      current
      DESCRIPTION "The name of this configuration. WebLogic Server uses an MBean to implement and persist the configuration. "
      ::= { wldfDataAccessRuntimeEntry 7  }
   
   
   wldfDataAccessRuntimeLatestRecordId OBJECT-TYPE
      SYNTAX      Counter64
      MAX-ACCESS  read-only
      STATUS      current
      DESCRIPTION " "
      ::= { wldfDataAccessRuntimeEntry 8  }
   
   
   wldfDataRetirementTaskRuntimeTable OBJECT-TYPE
      SYNTAX      SEQUENCE OF WldfDataRetirementTaskRuntimeEntry
      MAX-ACCESS  not-accessible
      STATUS      current
      DESCRIPTION "Exposes monitoring information about a potentially long-running request for the data retirement task. Remote clients, as well as clients running within a server, can access this information. "
      ::= { wls 1435  }
      
   
   wldfDataRetirementTaskRuntimeEntry OBJECT-TYPE
      SYNTAX      WldfDataRetirementTaskRuntimeEntry
      MAX-ACCESS  not-accessible
      STATUS      current
      DESCRIPTION "Generated SNMP Table Entry."
      INDEX { wldfDataRetirementTaskRuntimeIndex}
      ::= { wldfDataRetirementTaskRuntimeTable 1 }
      
   WldfDataRetirementTaskRuntimeEntry ::=
      SEQUENCE
      {
         wldfDataRetirementTaskRuntimeIndex OCTET STRING,
         wldfDataRetirementTaskRuntimeObjectName OCTET STRING,
         wldfDataRetirementTaskRuntimeType OCTET STRING,
         wldfDataRetirementTaskRuntimeStatus OCTET STRING,
         wldfDataRetirementTaskRuntimeRetiredRecordsCount Counter64,
         wldfDataRetirementTaskRuntimeRunning OCTET STRING,
         wldfDataRetirementTaskRuntimeBeginTime Counter64,
         wldfDataRetirementTaskRuntimeEndTime Counter64,
         wldfDataRetirementTaskRuntimeSystemTask OCTET STRING,
         wldfDataRetirementTaskRuntimeDescription OCTET STRING,
         wldfDataRetirementTaskRuntimeName OCTET STRING,
         wldfDataRetirementTaskRuntimeProgress OCTET STRING
      }
      
   
   wldfDataRetirementTaskRuntimeIndex OBJECT-TYPE
      SYNTAX      OCTET STRING
      MAX-ACCESS  not-accessible
      STATUS      current
      DESCRIPTION "Index column"
      ::= { wldfDataRetirementTaskRuntimeEntry 1  }
   
   
   wldfDataRetirementTaskRuntimeObjectName OBJECT-TYPE
      SYNTAX      OCTET STRING
      MAX-ACCESS  read-only
      STATUS      current
      DESCRIPTION "ObjectName column"
      ::= { wldfDataRetirementTaskRuntimeEntry 2  }
   
   
   wldfDataRetirementTaskRuntimeType OBJECT-TYPE
      SYNTAX      OCTET STRING
      MAX-ACCESS  read-only
      STATUS      current
      DESCRIPTION "Returns the type of the MBean. "
      ::= { wldfDataRetirementTaskRuntimeEntry 3  }
   
   
   wldfDataRetirementTaskRuntimeStatus OBJECT-TYPE
      SYNTAX      OCTET STRING
      MAX-ACCESS  read-only
      STATUS      current
      DESCRIPTION "The status of this task. "
      ::= { wldfDataRetirementTaskRuntimeEntry 4  }
   
   
   wldfDataRetirementTaskRuntimeRetiredRecordsCount OBJECT-TYPE
      SYNTAX      Counter64
      MAX-ACCESS  read-only
      STATUS      current
      DESCRIPTION " "
      ::= { wldfDataRetirementTaskRuntimeEntry 5  }
   
   
   wldfDataRetirementTaskRuntimeRunning OBJECT-TYPE
      SYNTAX      OCTET STRING
      MAX-ACCESS  read-only
      STATUS      current
      DESCRIPTION "Indicates whether the task is still running. "
      ::= { wldfDataRetirementTaskRuntimeEntry 6  }
   
   
   wldfDataRetirementTaskRuntimeBeginTime OBJECT-TYPE
      SYNTAX      Counter64
      MAX-ACCESS  read-only
      STATUS      current
      DESCRIPTION "The time at which this task was started. "
      ::= { wldfDataRetirementTaskRuntimeEntry 7  }
   
   
   wldfDataRetirementTaskRuntimeEndTime OBJECT-TYPE
      SYNTAX      Counter64
      MAX-ACCESS  read-only
      STATUS      current
      DESCRIPTION "The time at which this task was completed.  A value of -1 indicates that the task is currently running. "
      ::= { wldfDataRetirementTaskRuntimeEntry 8  }
   
   
   wldfDataRetirementTaskRuntimeSystemTask OBJECT-TYPE
      SYNTAX      OCTET STRING
      MAX-ACCESS  read-only
      STATUS      current
      DESCRIPTION "Indicates whether this task was initiated by the server versus a user. "
      ::= { wldfDataRetirementTaskRuntimeEntry 9  }
   
   
   wldfDataRetirementTaskRuntimeDescription OBJECT-TYPE
      SYNTAX      OCTET STRING
      MAX-ACCESS  read-only
      STATUS      current
      DESCRIPTION "A description of this task. "
      ::= { wldfDataRetirementTaskRuntimeEntry 10  }
   
   
   wldfDataRetirementTaskRuntimeName OBJECT-TYPE
      SYNTAX      OCTET STRING
      MAX-ACCESS  read-only
      STATUS      current
      DESCRIPTION "The name of this configuration. WebLogic Server uses an MBean to implement and persist the configuration. "
      ::= { wldfDataRetirementTaskRuntimeEntry 11  }
   
   
   wldfDataRetirementTaskRuntimeProgress OBJECT-TYPE
      SYNTAX      OCTET STRING
      MAX-ACCESS  read-only
      STATUS      current
      DESCRIPTION "The progress of this task. "
      ::= { wldfDataRetirementTaskRuntimeEntry 12  }
   
   
   wldfImageCreationTaskRuntimeTable OBJECT-TYPE
      SYNTAX      SEQUENCE OF WldfImageCreationTaskRuntimeEntry
      MAX-ACCESS  not-accessible
      STATUS      current
      DESCRIPTION "Exposes monitoring information about a potentially long-running request for the generation of a diagnostic image. Remote clients, as well as clients running within a server, can access this information.  {@link weblogic.management.runtime.WLDFImageRuntimeMBean WLDFImageRuntimeMBean} supports operations to request the generation of a diagnostic image for capturing a running server's internal state information.  These operations will fork a separate thread to perform the actual work and immediately return an instance of this MBean to the caller. The caller can then use that instance to track the task's progress. "
      ::= { wls 1440  }
      
   
   wldfImageCreationTaskRuntimeEntry OBJECT-TYPE
      SYNTAX      WldfImageCreationTaskRuntimeEntry
      MAX-ACCESS  not-accessible
      STATUS      current
      DESCRIPTION "Generated SNMP Table Entry."
      INDEX { wldfImageCreationTaskRuntimeIndex}
      ::= { wldfImageCreationTaskRuntimeTable 1 }
      
   WldfImageCreationTaskRuntimeEntry ::=
      SEQUENCE
      {
         wldfImageCreationTaskRuntimeIndex OCTET STRING,
         wldfImageCreationTaskRuntimeObjectName OCTET STRING,
         wldfImageCreationTaskRuntimeType OCTET STRING,
         wldfImageCreationTaskRuntimeStatus OCTET STRING,
         wldfImageCreationTaskRuntimeRunning OCTET STRING,
         wldfImageCreationTaskRuntimeBeginTime Counter64,
         wldfImageCreationTaskRuntimeEndTime Counter64,
         wldfImageCreationTaskRuntimeSystemTask OCTET STRING,
         wldfImageCreationTaskRuntimeDescription OCTET STRING,
         wldfImageCreationTaskRuntimeName OCTET STRING,
         wldfImageCreationTaskRuntimeProgress OCTET STRING,
         wldfImageCreationTaskRuntimeImageFileName OCTET STRING
      }
      
   
   wldfImageCreationTaskRuntimeIndex OBJECT-TYPE
      SYNTAX      OCTET STRING
      MAX-ACCESS  not-accessible
      STATUS      current
      DESCRIPTION "Index column"
      ::= { wldfImageCreationTaskRuntimeEntry 1  }
   
   
   wldfImageCreationTaskRuntimeObjectName OBJECT-TYPE
      SYNTAX      OCTET STRING
      MAX-ACCESS  read-only
      STATUS      current
      DESCRIPTION "ObjectName column"
      ::= { wldfImageCreationTaskRuntimeEntry 2  }
   
   
   wldfImageCreationTaskRuntimeType OBJECT-TYPE
      SYNTAX      OCTET STRING
      MAX-ACCESS  read-only
      STATUS      current
      DESCRIPTION "Returns the type of the MBean. "
      ::= { wldfImageCreationTaskRuntimeEntry 3  }
   
   
   wldfImageCreationTaskRuntimeStatus OBJECT-TYPE
      SYNTAX      OCTET STRING
      MAX-ACCESS  read-only
      STATUS      current
      DESCRIPTION "The status of this task. "
      ::= { wldfImageCreationTaskRuntimeEntry 4  }
   
   
   wldfImageCreationTaskRuntimeRunning OBJECT-TYPE
      SYNTAX      OCTET STRING
      MAX-ACCESS  read-only
      STATUS      current
      DESCRIPTION "Indicates whether the task is still running. "
      ::= { wldfImageCreationTaskRuntimeEntry 5  }
   
   
   wldfImageCreationTaskRuntimeBeginTime OBJECT-TYPE
      SYNTAX      Counter64
      MAX-ACCESS  read-only
      STATUS      current
      DESCRIPTION "The time at which this task was started. "
      ::= { wldfImageCreationTaskRuntimeEntry 6  }
   
   
   wldfImageCreationTaskRuntimeEndTime OBJECT-TYPE
      SYNTAX      Counter64
      MAX-ACCESS  read-only
      STATUS      current
      DESCRIPTION "The time at which this task was completed.  A value of -1 indicates that the task is currently running. "
      ::= { wldfImageCreationTaskRuntimeEntry 7  }
   
   
   wldfImageCreationTaskRuntimeSystemTask OBJECT-TYPE
      SYNTAX      OCTET STRING
      MAX-ACCESS  read-only
      STATUS      current
      DESCRIPTION "Indicates whether this task was initiated by the server versus a user. "
      ::= { wldfImageCreationTaskRuntimeEntry 8  }
   
   
   wldfImageCreationTaskRuntimeDescription OBJECT-TYPE
      SYNTAX      OCTET STRING
      MAX-ACCESS  read-only
      STATUS      current
      DESCRIPTION "A description of this task. "
      ::= { wldfImageCreationTaskRuntimeEntry 9  }
   
   
   wldfImageCreationTaskRuntimeName OBJECT-TYPE
      SYNTAX      OCTET STRING
      MAX-ACCESS  read-only
      STATUS      current
      DESCRIPTION "The name of this configuration. WebLogic Server uses an MBean to implement and persist the configuration. "
      ::= { wldfImageCreationTaskRuntimeEntry 10  }
   
   
   wldfImageCreationTaskRuntimeProgress OBJECT-TYPE
      SYNTAX      OCTET STRING
      MAX-ACCESS  read-only
      STATUS      current
      DESCRIPTION "The progress of this task. "
      ::= { wldfImageCreationTaskRuntimeEntry 11  }
   
   
   wldfImageCreationTaskRuntimeImageFileName OBJECT-TYPE
      SYNTAX      OCTET STRING
      MAX-ACCESS  read-only
      STATUS      current
      DESCRIPTION "Retrieve the name of the image file that was created. If the name is not yet known at the time this is called, this may return null. "
      ::= { wldfImageCreationTaskRuntimeEntry 12  }
   
   
   wldfImageRuntimeTable OBJECT-TYPE
      SYNTAX      SEQUENCE OF WldfImageRuntimeEntry
      MAX-ACCESS  not-accessible
      STATUS      current
      DESCRIPTION "This interface controls diagnostic image creation, and provides access to run-time information about past and current diagnostic image capture requests. "
      ::= { wls 1445  }
      
   
   wldfImageRuntimeEntry OBJECT-TYPE
      SYNTAX      WldfImageRuntimeEntry
      MAX-ACCESS  not-accessible
      STATUS      current
      DESCRIPTION "Generated SNMP Table Entry."
      INDEX { wldfImageRuntimeIndex}
      ::= { wldfImageRuntimeTable 1 }
      
   WldfImageRuntimeEntry ::=
      SEQUENCE
      {
         wldfImageRuntimeIndex OCTET STRING,
         wldfImageRuntimeObjectName OCTET STRING,
         wldfImageRuntimeType OCTET STRING,
         wldfImageRuntimeName OCTET STRING,
         wldfImageRuntimeAvailableCapturedImages OCTET STRING,
         wldfImageRuntimeImageTimeout INTEGER,
         wldfImageRuntimeImageDir OCTET STRING
      }
      
   
   wldfImageRuntimeIndex OBJECT-TYPE
      SYNTAX      OCTET STRING
      MAX-ACCESS  not-accessible
      STATUS      current
      DESCRIPTION "Index column"
      ::= { wldfImageRuntimeEntry 1  }
   
   
   wldfImageRuntimeObjectName OBJECT-TYPE
      SYNTAX      OCTET STRING
      MAX-ACCESS  read-only
      STATUS      current
      DESCRIPTION "ObjectName column"
      ::= { wldfImageRuntimeEntry 2  }
   
   
   wldfImageRuntimeType OBJECT-TYPE
      SYNTAX      OCTET STRING
      MAX-ACCESS  read-only
      STATUS      current
      DESCRIPTION "Returns the type of the MBean. "
      ::= { wldfImageRuntimeEntry 3  }
   
   
   wldfImageRuntimeName OBJECT-TYPE
      SYNTAX      OCTET STRING
      MAX-ACCESS  read-only
      STATUS      current
      DESCRIPTION "The name of this configuration. WebLogic Server uses an MBean to implement and persist the configuration. "
      ::= { wldfImageRuntimeEntry 4  }
   
   
   wldfImageRuntimeAvailableCapturedImages OBJECT-TYPE
      SYNTAX      OCTET STRING
      MAX-ACCESS  read-only
      STATUS      current
      DESCRIPTION " Returns a list of captured images that are available on the Server. "
      ::= { wldfImageRuntimeEntry 5  }
   
   
   wldfImageRuntimeImageTimeout OBJECT-TYPE
      SYNTAX      INTEGER
      MAX-ACCESS  read-only
      STATUS      current
      DESCRIPTION "The default timeout period, in minutes, that the server uses to delay future diagnostic image-capture requests. "
      ::= { wldfImageRuntimeEntry 6  }
   
   
   wldfImageRuntimeImageDir OBJECT-TYPE
      SYNTAX      OCTET STRING
      MAX-ACCESS  read-only
      STATUS      current
      DESCRIPTION "The default directory where the server stores captured diagnostic images. "
      ::= { wldfImageRuntimeEntry 7  }
   
   
   wldfRuntimeTable OBJECT-TYPE
      SYNTAX      SEQUENCE OF WldfRuntimeEntry
      MAX-ACCESS  not-accessible
      STATUS      current
      DESCRIPTION "This interface provides access to all the runtime MBeans for the WebLogic Diagnostic Framework (WLDF). "
      ::= { wls 1450  }
      
   
   wldfRuntimeEntry OBJECT-TYPE
      SYNTAX      WldfRuntimeEntry
      MAX-ACCESS  not-accessible
      STATUS      current
      DESCRIPTION "Generated SNMP Table Entry."
      INDEX { wldfRuntimeIndex}
      ::= { wldfRuntimeTable 1 }
      
   WldfRuntimeEntry ::=
      SEQUENCE
      {
         wldfRuntimeIndex     OCTET STRING,
         wldfRuntimeObjectName OCTET STRING,
         wldfRuntimeType      OCTET STRING,
         wldfRuntimeName      OCTET STRING
      }
      
   
   wldfRuntimeIndex OBJECT-TYPE
      SYNTAX      OCTET STRING
      MAX-ACCESS  not-accessible
      STATUS      current
      DESCRIPTION "Index column"
      ::= { wldfRuntimeEntry 1  }
   
   
   wldfRuntimeObjectName OBJECT-TYPE
      SYNTAX      OCTET STRING
      MAX-ACCESS  read-only
      STATUS      current
      DESCRIPTION "ObjectName column"
      ::= { wldfRuntimeEntry 2  }
   
   
   wldfRuntimeType OBJECT-TYPE
      SYNTAX      OCTET STRING
      MAX-ACCESS  read-only
      STATUS      current
      DESCRIPTION "Returns the type of the MBean. "
      ::= { wldfRuntimeEntry 3  }
   
   
   wldfRuntimeName OBJECT-TYPE
      SYNTAX      OCTET STRING
      MAX-ACCESS  read-only
      STATUS      current
      DESCRIPTION "The name of this configuration. WebLogic Server uses an MBean to implement and persist the configuration. "
      ::= { wldfRuntimeEntry 4  }
   
   
   wldfWatchJMXNotificationRuntimeTable OBJECT-TYPE
      SYNTAX      SEQUENCE OF WldfWatchJMXNotificationRuntimeEntry
      MAX-ACCESS  not-accessible
      STATUS      current
      DESCRIPTION "Attaches a notification listener in order to receive watch notification events when a watch evaluates to true. Note that the listener will receive all notifications; the caller must filter the output."
      ::= { wls 1455  }
      
   
   wldfWatchJMXNotificationRuntimeEntry OBJECT-TYPE
      SYNTAX      WldfWatchJMXNotificationRuntimeEntry
      MAX-ACCESS  not-accessible
      STATUS      current
      DESCRIPTION "Generated SNMP Table Entry."
      INDEX { wldfWatchJMXNotificationRuntimeIndex}
      ::= { wldfWatchJMXNotificationRuntimeTable 1 }
      
   WldfWatchJMXNotificationRuntimeEntry ::=
      SEQUENCE
      {
         wldfWatchJMXNotificationRuntimeIndex OCTET STRING,
         wldfWatchJMXNotificationRuntimeObjectName OCTET STRING,
         wldfWatchJMXNotificationRuntimeType OCTET STRING,
         wldfWatchJMXNotificationRuntimeName OCTET STRING
      }
      
   
   wldfWatchJMXNotificationRuntimeIndex OBJECT-TYPE
      SYNTAX      OCTET STRING
      MAX-ACCESS  not-accessible
      STATUS      current
      DESCRIPTION "Index column"
      ::= { wldfWatchJMXNotificationRuntimeEntry 1  }
   
   
   wldfWatchJMXNotificationRuntimeObjectName OBJECT-TYPE
      SYNTAX      OCTET STRING
      MAX-ACCESS  read-only
      STATUS      current
      DESCRIPTION "ObjectName column"
      ::= { wldfWatchJMXNotificationRuntimeEntry 2  }
   
   
   wldfWatchJMXNotificationRuntimeType OBJECT-TYPE
      SYNTAX      OCTET STRING
      MAX-ACCESS  read-only
      STATUS      current
      DESCRIPTION "Returns the type of the MBean."
      ::= { wldfWatchJMXNotificationRuntimeEntry 3  }
   
   
   wldfWatchJMXNotificationRuntimeName OBJECT-TYPE
      SYNTAX      OCTET STRING
      MAX-ACCESS  read-only
      STATUS      current
      DESCRIPTION "The name of this configuration. WebLogic Server uses an MBean to implement and persist the configuration."
      ::= { wldfWatchJMXNotificationRuntimeEntry 4  }
   
   
   wsrmRemoteEndpointRuntimeTable OBJECT-TYPE
      SYNTAX      SEQUENCE OF WsrmRemoteEndpointRuntimeEntry
      MAX-ACCESS  not-accessible
      STATUS      current
      DESCRIPTION "This class is used for monitoring a WebLogic SAF remote endpoint for WebServices Reliable Messaging. "
      ::= { wls 1460  }
      
   
   wsrmRemoteEndpointRuntimeEntry OBJECT-TYPE
      SYNTAX      WsrmRemoteEndpointRuntimeEntry
      MAX-ACCESS  not-accessible
      STATUS      current
      DESCRIPTION "Generated SNMP Table Entry."
      INDEX { wsrmRemoteEndpointRuntimeIndex}
      ::= { wsrmRemoteEndpointRuntimeTable 1 }
      
   WsrmRemoteEndpointRuntimeEntry ::=
      SEQUENCE
      {
         wsrmRemoteEndpointRuntimeIndex OCTET STRING,
         wsrmRemoteEndpointRuntimeObjectName OCTET STRING,
         wsrmRemoteEndpointRuntimeType OCTET STRING,
         wsrmRemoteEndpointRuntimeUptimeTotal Counter64,
         wsrmRemoteEndpointRuntimeMessagesCurrentCount Counter64,
         wsrmRemoteEndpointRuntimeDowntimeTotal Counter64,
         wsrmRemoteEndpointRuntimeBytesReceivedCount Counter64,
         wsrmRemoteEndpointRuntimeEndpointType OCTET STRING,
         wsrmRemoteEndpointRuntimeFailedMessagesTotal Counter64,
         wsrmRemoteEndpointRuntimeMessagesReceivedCount Counter64,
         wsrmRemoteEndpointRuntimeURL OCTET STRING,
         wsrmRemoteEndpointRuntimePausedForIncoming OCTET STRING,
         wsrmRemoteEndpointRuntimeName OCTET STRING,
         wsrmRemoteEndpointRuntimeBytesHighCount Counter64,
         wsrmRemoteEndpointRuntimeUptimeHigh Counter64,
         wsrmRemoteEndpointRuntimeBytesCurrentCount Counter64,
         wsrmRemoteEndpointRuntimeMessagesPendingCount Counter64,
         wsrmRemoteEndpointRuntimeConversationsCurrentCount Counter64,
         wsrmRemoteEndpointRuntimeConversationsHighCount Counter64,
         wsrmRemoteEndpointRuntimeConversationsTotalCount Counter64,
         wsrmRemoteEndpointRuntimeDowntimeHigh Counter64,
         wsrmRemoteEndpointRuntimeBytesThresholdTime Counter64,
         wsrmRemoteEndpointRuntimeBytesPendingCount Counter64,
         wsrmRemoteEndpointRuntimePausedForForwarding OCTET STRING,
         wsrmRemoteEndpointRuntimeMessagesThresholdTime Counter64,
         wsrmRemoteEndpointRuntimeMessagesHighCount Counter64,
         wsrmRemoteEndpointRuntimeOperationState OCTET STRING,
         wsrmRemoteEndpointRuntimeLastTimeFailedToConnect OCTET STRING,
         wsrmRemoteEndpointRuntimeLastTimeConnected OCTET STRING
      }
      
   
   wsrmRemoteEndpointRuntimeIndex OBJECT-TYPE
      SYNTAX      OCTET STRING
      MAX-ACCESS  not-accessible
      STATUS      current
      DESCRIPTION "Index column"
      ::= { wsrmRemoteEndpointRuntimeEntry 1  }
   
   
   wsrmRemoteEndpointRuntimeObjectName OBJECT-TYPE
      SYNTAX      OCTET STRING
      MAX-ACCESS  read-only
      STATUS      current
      DESCRIPTION "ObjectName column"
      ::= { wsrmRemoteEndpointRuntimeEntry 2  }
   
   
   wsrmRemoteEndpointRuntimeType OBJECT-TYPE
      SYNTAX      OCTET STRING
      MAX-ACCESS  read-only
      STATUS      current
      DESCRIPTION "Returns the type of the MBean. "
      ::= { wsrmRemoteEndpointRuntimeEntry 3  }
   
   
   wsrmRemoteEndpointRuntimeUptimeTotal OBJECT-TYPE
      SYNTAX      Counter64
      MAX-ACCESS  read-only
      STATUS      current
      DESCRIPTION "Specifies the total time, in seconds, that the remote endpoint has been available since the last reset. "
      ::= { wsrmRemoteEndpointRuntimeEntry 4  }
   
   
   wsrmRemoteEndpointRuntimeMessagesCurrentCount OBJECT-TYPE
      SYNTAX      Counter64
      MAX-ACCESS  read-only
      STATUS      current
      DESCRIPTION "Returns the current number of messages. This number includes the pending messages. "
      ::= { wsrmRemoteEndpointRuntimeEntry 5  }
   
   
   wsrmRemoteEndpointRuntimeDowntimeTotal OBJECT-TYPE
      SYNTAX      Counter64
      MAX-ACCESS  read-only
      STATUS      current
      DESCRIPTION "Specifies the total time, in seconds, that the remote endpoint has not been available since the last reset. "
      ::= { wsrmRemoteEndpointRuntimeEntry 6  }
   
   
   wsrmRemoteEndpointRuntimeBytesReceivedCount OBJECT-TYPE
      SYNTAX      Counter64
      MAX-ACCESS  read-only
      STATUS      current
      DESCRIPTION "The number of bytes received since the last reset. "
      ::= { wsrmRemoteEndpointRuntimeEntry 7  }
   
   
   wsrmRemoteEndpointRuntimeEndpointType OBJECT-TYPE
      SYNTAX      OCTET STRING
      MAX-ACCESS  read-only
      STATUS      current
      DESCRIPTION "Specifies if the remote endpoint is a JMS or Web Services (WSRM) destination. The possible values are: weblogic.management.runtime.SAFConstants.JMS_ENDPOINT or weblogic.management.runtime.SAFConstants.WS_ENDPOINT. "
      ::= { wsrmRemoteEndpointRuntimeEntry 8  }
   
   
   wsrmRemoteEndpointRuntimeFailedMessagesTotal OBJECT-TYPE
      SYNTAX      Counter64
      MAX-ACCESS  read-only
      STATUS      current
      DESCRIPTION "Returns the total number of messages that have failed to be forwarded since the last reset. "
      ::= { wsrmRemoteEndpointRuntimeEntry 9  }
   
   
   wsrmRemoteEndpointRuntimeMessagesReceivedCount OBJECT-TYPE
      SYNTAX      Counter64
      MAX-ACCESS  read-only
      STATUS      current
      DESCRIPTION "The number of messages received since the last reset. "
      ::= { wsrmRemoteEndpointRuntimeEntry 10  }
   
   
   wsrmRemoteEndpointRuntimeURL OBJECT-TYPE
      SYNTAX      OCTET STRING
      MAX-ACCESS  read-only
      STATUS      current
      DESCRIPTION "The URL of the remote endpoint. "
      ::= { wsrmRemoteEndpointRuntimeEntry 11  }
   
   
   wsrmRemoteEndpointRuntimePausedForIncoming OBJECT-TYPE
      SYNTAX      OCTET STRING
      MAX-ACCESS  read-only
      STATUS      current
      DESCRIPTION "Indicates if a remote endpoint is currently not accepting new messages. "
      ::= { wsrmRemoteEndpointRuntimeEntry 12  }
   
   
   wsrmRemoteEndpointRuntimeName OBJECT-TYPE
      SYNTAX      OCTET STRING
      MAX-ACCESS  read-only
      STATUS      current
      DESCRIPTION "The name of this configuration. WebLogic Server uses an MBean to implement and persist the configuration. "
      ::= { wsrmRemoteEndpointRuntimeEntry 13  }
   
   
   wsrmRemoteEndpointRuntimeBytesHighCount OBJECT-TYPE
      SYNTAX      Counter64
      MAX-ACCESS  read-only
      STATUS      current
      DESCRIPTION "Returns the peak number of bytes since the last reset. "
      ::= { wsrmRemoteEndpointRuntimeEntry 14  }
   
   
   wsrmRemoteEndpointRuntimeUptimeHigh OBJECT-TYPE
      SYNTAX      Counter64
      MAX-ACCESS  read-only
      STATUS      current
      DESCRIPTION "Specifies the longest time, in seconds, that the remote endpoint has been available since the last reset. "
      ::= { wsrmRemoteEndpointRuntimeEntry 15  }
   
   
   wsrmRemoteEndpointRuntimeBytesCurrentCount OBJECT-TYPE
      SYNTAX      Counter64
      MAX-ACCESS  read-only
      STATUS      current
      DESCRIPTION "Returns the current number of bytes. This number does not include the pending bytes. "
      ::= { wsrmRemoteEndpointRuntimeEntry 16  }
   
   
   wsrmRemoteEndpointRuntimeMessagesPendingCount OBJECT-TYPE
      SYNTAX      Counter64
      MAX-ACCESS  read-only
      STATUS      current
      DESCRIPTION "Returns the number of pending messages. Pending messages are over and above the current number of messages. A pending message is one that has either been sent in a transaction and not committed, or been forwarded but has not been acknowledged. "
      ::= { wsrmRemoteEndpointRuntimeEntry 17  }
   
   
   wsrmRemoteEndpointRuntimeConversationsCurrentCount OBJECT-TYPE
      SYNTAX      Counter64
      MAX-ACCESS  read-only
      STATUS      current
      DESCRIPTION "Returns the current number of conversations "
      ::= { wsrmRemoteEndpointRuntimeEntry 18  }
   
   
   wsrmRemoteEndpointRuntimeConversationsHighCount OBJECT-TYPE
      SYNTAX      Counter64
      MAX-ACCESS  read-only
      STATUS      current
      DESCRIPTION "Returns the peak number of conversations since the last reset. "
      ::= { wsrmRemoteEndpointRuntimeEntry 19  }
   
   
   wsrmRemoteEndpointRuntimeConversationsTotalCount OBJECT-TYPE
      SYNTAX      Counter64
      MAX-ACCESS  read-only
      STATUS      current
      DESCRIPTION "Returns the total number of conversations since the last reset. "
      ::= { wsrmRemoteEndpointRuntimeEntry 20  }
   
   
   wsrmRemoteEndpointRuntimeDowntimeHigh OBJECT-TYPE
      SYNTAX      Counter64
      MAX-ACCESS  read-only
      STATUS      current
      DESCRIPTION "Specifies the longest time, in seconds, that the remote endpoint has not been available since the last reset. "
      ::= { wsrmRemoteEndpointRuntimeEntry 21  }
   
   
   wsrmRemoteEndpointRuntimeBytesThresholdTime OBJECT-TYPE
      SYNTAX      Counter64
      MAX-ACCESS  read-only
      STATUS      current
      DESCRIPTION "Returns the amount of time in the threshold condition since the last reset. "
      ::= { wsrmRemoteEndpointRuntimeEntry 22  }
   
   
   wsrmRemoteEndpointRuntimeBytesPendingCount OBJECT-TYPE
      SYNTAX      Counter64
      MAX-ACCESS  read-only
      STATUS      current
      DESCRIPTION "Returns the number of pending bytes. Pending bytes are over and above the current number of bytes. "
      ::= { wsrmRemoteEndpointRuntimeEntry 23  }
   
   
   wsrmRemoteEndpointRuntimePausedForForwarding OBJECT-TYPE
      SYNTAX      OCTET STRING
      MAX-ACCESS  read-only
      STATUS      current
      DESCRIPTION "Indicates if the remote endpoint is currently not forwarding messages. "
      ::= { wsrmRemoteEndpointRuntimeEntry 24  }
   
   
   wsrmRemoteEndpointRuntimeMessagesThresholdTime OBJECT-TYPE
      SYNTAX      Counter64
      MAX-ACCESS  read-only
      STATUS      current
      DESCRIPTION "Returns the amount of time in the threshold condition since the last reset. "
      ::= { wsrmRemoteEndpointRuntimeEntry 25  }
   
   
   wsrmRemoteEndpointRuntimeMessagesHighCount OBJECT-TYPE
      SYNTAX      Counter64
      MAX-ACCESS  read-only
      STATUS      current
      DESCRIPTION "Returns the peak number of messages since the last reset. "
      ::= { wsrmRemoteEndpointRuntimeEntry 26  }
   
   
   wsrmRemoteEndpointRuntimeOperationState OBJECT-TYPE
      SYNTAX      OCTET STRING
      MAX-ACCESS  read-only
      STATUS      current
      DESCRIPTION "Specifies the state of the most recent ExireAll operation. "
      ::= { wsrmRemoteEndpointRuntimeEntry 27  }
   
   
   wsrmRemoteEndpointRuntimeLastTimeFailedToConnect OBJECT-TYPE
      SYNTAX      OCTET STRING
      MAX-ACCESS  read-only
      STATUS      current
      DESCRIPTION "Specifies the last time that the remote endpoint failed to be connected. "
      ::= { wsrmRemoteEndpointRuntimeEntry 28  }
   
   
   wsrmRemoteEndpointRuntimeLastTimeConnected OBJECT-TYPE
      SYNTAX      OCTET STRING
      MAX-ACCESS  read-only
      STATUS      current
      DESCRIPTION "Specifies the last time that the remote endpoint was connected. "
      ::= { wsrmRemoteEndpointRuntimeEntry 29  }
   
   
   wtcRuntimeTable OBJECT-TYPE
      SYNTAX      SEQUENCE OF WtcRuntimeEntry
      MAX-ACCESS  not-accessible
      STATUS      current
      DESCRIPTION "This class is used to 1. query, stop, and start WTC connections. 2. query, suspend, and resume WTC imported and exported services. 3. retrieve statistics MBean relates to this WTC server. 4. query status of WTC server. "
      ::= { wls 1465  }
      
   
   wtcRuntimeEntry OBJECT-TYPE
      SYNTAX      WtcRuntimeEntry
      MAX-ACCESS  not-accessible
      STATUS      current
      DESCRIPTION "Generated SNMP Table Entry."
      INDEX { wtcRuntimeIndex}
      ::= { wtcRuntimeTable 1 }
      
   WtcRuntimeEntry ::=
      SEQUENCE
      {
         wtcRuntimeIndex      OCTET STRING,
         wtcRuntimeObjectName OCTET STRING,
         wtcRuntimeType       OCTET STRING,
         wtcRuntimeName       OCTET STRING,
         wtcRuntimeWTCServerStartTime Counter64,
         wtcRuntimeWTCServerStatus OCTET STRING
      }
      
   
   wtcRuntimeIndex OBJECT-TYPE
      SYNTAX      OCTET STRING
      MAX-ACCESS  not-accessible
      STATUS      current
      DESCRIPTION "Index column"
      ::= { wtcRuntimeEntry 1  }
   
   
   wtcRuntimeObjectName OBJECT-TYPE
      SYNTAX      OCTET STRING
      MAX-ACCESS  read-only
      STATUS      current
      DESCRIPTION "ObjectName column"
      ::= { wtcRuntimeEntry 2  }
   
   
   wtcRuntimeType OBJECT-TYPE
      SYNTAX      OCTET STRING
      MAX-ACCESS  read-only
      STATUS      current
      DESCRIPTION "Returns the type of the MBean. "
      ::= { wtcRuntimeEntry 3  }
   
   
   wtcRuntimeName OBJECT-TYPE
      SYNTAX      OCTET STRING
      MAX-ACCESS  read-only
      STATUS      current
      DESCRIPTION "The name of this configuration. WebLogic Server uses an MBean to implement and persist the configuration. "
      ::= { wtcRuntimeEntry 4  }
   
   
   wtcRuntimeWTCServerStartTime OBJECT-TYPE
      SYNTAX      Counter64
      MAX-ACCESS  read-only
      STATUS      current
      DESCRIPTION "Returns the timestamp when WTC server starts. "
      ::= { wtcRuntimeEntry 5  }
   
   
   wtcRuntimeWTCServerStatus OBJECT-TYPE
      SYNTAX      OCTET STRING
      MAX-ACCESS  read-only
      STATUS      current
      DESCRIPTION "Returns the status of WTC server itself. "
      ::= { wtcRuntimeEntry 6  }
   
   
   wseeHandlerRuntimeTable OBJECT-TYPE
      SYNTAX      SEQUENCE OF WseeHandlerRuntimeEntry
      MAX-ACCESS  not-accessible
      STATUS      current
      DESCRIPTION "Provides runtime information about a SOAP message handler that has been associated with a Web service.  SOAP message handlers are used to intercept both the inbound (request) and outbound (response) SOAP messages so that extra processing can be done on the messages. Programmers specify SOAP message handlers for a Web Service using the @SOAPMessageHandlers and @HandlerChain JWS annotations. "
      ::= { wls 1490  }
      
   
   wseeHandlerRuntimeEntry OBJECT-TYPE
      SYNTAX      WseeHandlerRuntimeEntry
      MAX-ACCESS  not-accessible
      STATUS      current
      DESCRIPTION "Generated SNMP Table Entry."
      INDEX { wseeHandlerRuntimeIndex}
      ::= { wseeHandlerRuntimeTable 1 }
      
   WseeHandlerRuntimeEntry ::=
      SEQUENCE
      {
         wseeHandlerRuntimeIndex OCTET STRING,
         wseeHandlerRuntimeObjectName OCTET STRING,
         wseeHandlerRuntimeType OCTET STRING,
         wseeHandlerRuntimeName OCTET STRING
      }
      
   
   wseeHandlerRuntimeIndex OBJECT-TYPE
      SYNTAX      OCTET STRING
      MAX-ACCESS  not-accessible
      STATUS      current
      DESCRIPTION "Index column"
      ::= { wseeHandlerRuntimeEntry 1  }
   
   
   wseeHandlerRuntimeObjectName OBJECT-TYPE
      SYNTAX      OCTET STRING
      MAX-ACCESS  read-only
      STATUS      current
      DESCRIPTION "ObjectName column"
      ::= { wseeHandlerRuntimeEntry 2  }
   
   
   wseeHandlerRuntimeType OBJECT-TYPE
      SYNTAX      OCTET STRING
      MAX-ACCESS  read-only
      STATUS      current
      DESCRIPTION "Returns the type of the MBean. "
      ::= { wseeHandlerRuntimeEntry 3  }
   
   
   wseeHandlerRuntimeName OBJECT-TYPE
      SYNTAX      OCTET STRING
      MAX-ACCESS  read-only
      STATUS      current
      DESCRIPTION "The name of this configuration. WebLogic Server uses an MBean to implement and persist the configuration. "
      ::= { wseeHandlerRuntimeEntry 4  }
   
   
   wseeOperationRuntimeTable OBJECT-TYPE
      SYNTAX      SEQUENCE OF WseeOperationRuntimeEntry
      MAX-ACCESS  not-accessible
      STATUS      current
      DESCRIPTION "Describes the state of a particular Web Service operation, such as deployment state and runtime statistics about the execution of the operation. This MBean can describe the operation on a web service client or service. Request statistics relate to outgoing requests on a client or incoming requests on a service. Response statistics relate to an incoming response on a client or an outgoing response on a service. Time values are reported in milliseconds "
      ::= { wls 1495  }
      
   
   wseeOperationRuntimeEntry OBJECT-TYPE
      SYNTAX      WseeOperationRuntimeEntry
      MAX-ACCESS  not-accessible
      STATUS      current
      DESCRIPTION "Generated SNMP Table Entry."
      INDEX { wseeOperationRuntimeIndex}
      ::= { wseeOperationRuntimeTable 1 }
      
   WseeOperationRuntimeEntry ::=
      SEQUENCE
      {
         wseeOperationRuntimeIndex OCTET STRING,
         wseeOperationRuntimeObjectName OCTET STRING,
         wseeOperationRuntimeType OCTET STRING,
         wseeOperationRuntimeResponseTimeHigh Counter64,
         wseeOperationRuntimeDispatchTimeLow Counter64,
         wseeOperationRuntimeDispatchTimeTotal Counter64,
         wseeOperationRuntimeResponseTimeLow Counter64,
         wseeOperationRuntimeResponseCount Integer32,
         wseeOperationRuntimeDispatchTimeAverage Counter64,
         wseeOperationRuntimeResponseErrorCount Integer32,
         wseeOperationRuntimeExecutionTimeLow Counter64,
         wseeOperationRuntimeOperationName OCTET STRING,
         wseeOperationRuntimeResponseTimeAverage Counter64,
         wseeOperationRuntimeExecutionTimeHigh Counter64,
         wseeOperationRuntimeExecutionTimeTotal Counter64,
         wseeOperationRuntimeDispatchTimeHigh Counter64,
         wseeOperationRuntimeExecutionTimeAverage Counter64,
         wseeOperationRuntimeInvocationCount Integer32,
         wseeOperationRuntimeResponseTimeTotal Counter64,
         wseeOperationRuntimeName OCTET STRING,
         wseeOperationRuntimePolicySubjectType OCTET STRING,
         wseeOperationRuntimeLastResponseTime Counter64,
         wseeOperationRuntimePolicySubjectName OCTET STRING,
         wseeOperationRuntimeErrorCount INTEGER,
         wseeOperationRuntimeLastResponseErrorTime Counter64,
         wseeOperationRuntimePolicyAttachmentSupport OCTET STRING,
         wseeOperationRuntimePolicySubjectResourcePattern OCTET STRING,
         wseeOperationRuntimeLastResponseError OCTET STRING,
         wseeOperationRuntimeLastError OCTET STRING,
         wseeOperationRuntimeLastInvocationTime Counter64,
         wseeOperationRuntimeLastErrorTime Counter64
      }
      
   
   wseeOperationRuntimeIndex OBJECT-TYPE
      SYNTAX      OCTET STRING
      MAX-ACCESS  not-accessible
      STATUS      current
      DESCRIPTION "Index column"
      ::= { wseeOperationRuntimeEntry 1  }
   
   
   wseeOperationRuntimeObjectName OBJECT-TYPE
      SYNTAX      OCTET STRING
      MAX-ACCESS  read-only
      STATUS      current
      DESCRIPTION "ObjectName column"
      ::= { wseeOperationRuntimeEntry 2  }
   
   
   wseeOperationRuntimeType OBJECT-TYPE
      SYNTAX      OCTET STRING
      MAX-ACCESS  read-only
      STATUS      current
      DESCRIPTION "Returns the type of the MBean. "
      ::= { wseeOperationRuntimeEntry 3  }
   
   
   wseeOperationRuntimeResponseTimeHigh OBJECT-TYPE
      SYNTAX      Counter64
      MAX-ACCESS  read-only
      STATUS      current
      DESCRIPTION "Longest response time from the responses generated from operation invocations. "
      ::= { wseeOperationRuntimeEntry 4  }
   
   
   wseeOperationRuntimeDispatchTimeLow OBJECT-TYPE
      SYNTAX      Counter64
      MAX-ACCESS  read-only
      STATUS      current
      DESCRIPTION "Shortest operation dispatch time for the current measurement period.  Dispatch time refers to the time for WebLogic Server to process the invocation.  The measurement period typically starts when WebLogic Server is first started. "
      ::= { wseeOperationRuntimeEntry 5  }
   
   
   wseeOperationRuntimeDispatchTimeTotal OBJECT-TYPE
      SYNTAX      Counter64
      MAX-ACCESS  read-only
      STATUS      current
      DESCRIPTION "Total time for all operation dispatches in the current measurement period.  Dispatch time refers to the time for WebLogic Server to process the invocation.  The measurement period typically starts when WebLogic Server is first started. "
      ::= { wseeOperationRuntimeEntry 6  }
   
   
   wseeOperationRuntimeResponseTimeLow OBJECT-TYPE
      SYNTAX      Counter64
      MAX-ACCESS  read-only
      STATUS      current
      DESCRIPTION "Lowest response time from the responses generated from operation invocations. "
      ::= { wseeOperationRuntimeEntry 7  }
   
   
   wseeOperationRuntimeResponseCount OBJECT-TYPE
      SYNTAX      Integer32
      MAX-ACCESS  read-only
      STATUS      current
      DESCRIPTION "Total number of oresponses generated from operation invocations. "
      ::= { wseeOperationRuntimeEntry 8  }
   
   
   wseeOperationRuntimeDispatchTimeAverage OBJECT-TYPE
      SYNTAX      Counter64
      MAX-ACCESS  read-only
      STATUS      current
      DESCRIPTION "Average operation dispatch time for the current measurement period.  Dispatch time refers to the time for WebLogic Server to process the invocation.  The measurement period typically starts when WebLogic Server is first started. "
      ::= { wseeOperationRuntimeEntry 9  }
   
   
   wseeOperationRuntimeResponseErrorCount OBJECT-TYPE
      SYNTAX      Integer32
      MAX-ACCESS  read-only
      STATUS      current
      DESCRIPTION "Total number of errors from responses generated from operation invocations. "
      ::= { wseeOperationRuntimeEntry 10  }
   
   
   wseeOperationRuntimeExecutionTimeLow OBJECT-TYPE
      SYNTAX      Counter64
      MAX-ACCESS  read-only
      STATUS      current
      DESCRIPTION "Shortest operation execution time. "
      ::= { wseeOperationRuntimeEntry 11  }
   
   
   wseeOperationRuntimeOperationName OBJECT-TYPE
      SYNTAX      OCTET STRING
      MAX-ACCESS  read-only
      STATUS      current
      DESCRIPTION "Name of the operation for which runtime information is being provided. "
      ::= { wseeOperationRuntimeEntry 12  }
   
   
   wseeOperationRuntimeResponseTimeAverage OBJECT-TYPE
      SYNTAX      Counter64
      MAX-ACCESS  read-only
      STATUS      current
      DESCRIPTION "Average response time from the responses generated from operation invocations.  "
      ::= { wseeOperationRuntimeEntry 13  }
   
   
   wseeOperationRuntimeExecutionTimeHigh OBJECT-TYPE
      SYNTAX      Counter64
      MAX-ACCESS  read-only
      STATUS      current
      DESCRIPTION "Longest operation execution time. "
      ::= { wseeOperationRuntimeEntry 14  }
   
   
   wseeOperationRuntimeExecutionTimeTotal OBJECT-TYPE
      SYNTAX      Counter64
      MAX-ACCESS  read-only
      STATUS      current
      DESCRIPTION "Total time for all operation executions. "
      ::= { wseeOperationRuntimeEntry 15  }
   
   
   wseeOperationRuntimeDispatchTimeHigh OBJECT-TYPE
      SYNTAX      Counter64
      MAX-ACCESS  read-only
      STATUS      current
      DESCRIPTION "Longest operation dispatch time for the current measurement period.  Dispatch time refers to the time for WebLogic Server to process the invocation.  The measurement period typically starts when WebLogic Server is first started. "
      ::= { wseeOperationRuntimeEntry 16  }
   
   
   wseeOperationRuntimeExecutionTimeAverage OBJECT-TYPE
      SYNTAX      Counter64
      MAX-ACCESS  read-only
      STATUS      current
      DESCRIPTION "Average operation execution time. "
      ::= { wseeOperationRuntimeEntry 17  }
   
   
   wseeOperationRuntimeInvocationCount OBJECT-TYPE
      SYNTAX      Integer32
      MAX-ACCESS  read-only
      STATUS      current
      DESCRIPTION "Total number of operation invocations in the current measurement period.  The measurement period typically starts when WebLogic Server is first started. "
      ::= { wseeOperationRuntimeEntry 18  }
   
   
   wseeOperationRuntimeResponseTimeTotal OBJECT-TYPE
      SYNTAX      Counter64
      MAX-ACCESS  read-only
      STATUS      current
      DESCRIPTION "Total time for all responses generated from operation invocations. "
      ::= { wseeOperationRuntimeEntry 19  }
   
   
   wseeOperationRuntimeName OBJECT-TYPE
      SYNTAX      OCTET STRING
      MAX-ACCESS  read-only
      STATUS      current
      DESCRIPTION "The name of this configuration. WebLogic Server uses an MBean to implement and persist the configuration. "
      ::= { wseeOperationRuntimeEntry 20  }
   
   
   wseeOperationRuntimePolicySubjectType OBJECT-TYPE
      SYNTAX      OCTET STRING
      MAX-ACCESS  read-only
      STATUS      current
      DESCRIPTION "Get subject type for this port MBean. "
      ::= { wseeOperationRuntimeEntry 21  }
   
   
   wseeOperationRuntimeLastResponseTime OBJECT-TYPE
      SYNTAX      Counter64
      MAX-ACCESS  read-only
      STATUS      current
      DESCRIPTION "Time on WebLogic Server of the last response to arrive for this client/service (or 0 if no responses have been received) expressed as the number of milliseconds since midnight, January 1, 1970 UTC. "
      ::= { wseeOperationRuntimeEntry 22  }
   
   
   wseeOperationRuntimePolicySubjectName OBJECT-TYPE
      SYNTAX      OCTET STRING
      MAX-ACCESS  read-only
      STATUS      current
      DESCRIPTION "Get subject name for this port MBean. "
      ::= { wseeOperationRuntimeEntry 23  }
   
   
   wseeOperationRuntimeErrorCount OBJECT-TYPE
      SYNTAX      INTEGER
      MAX-ACCESS  read-only
      STATUS      current
      DESCRIPTION "Number of errors sending or receiving a request. "
      ::= { wseeOperationRuntimeEntry 24  }
   
   
   wseeOperationRuntimeLastResponseErrorTime OBJECT-TYPE
      SYNTAX      Counter64
      MAX-ACCESS  read-only
      STATUS      current
      DESCRIPTION "Time on WebLogic Server of the last error sending or receiving a response (or 0 if no failures have occurred) expressed as the number of milliseconds since midnight, January 1, 1970 UTC. "
      ::= { wseeOperationRuntimeEntry 25  }
   
   
   wseeOperationRuntimePolicyAttachmentSupport OBJECT-TYPE
      SYNTAX      OCTET STRING
      MAX-ACCESS  read-only
      STATUS      current
      DESCRIPTION "Get attachment support for this port MBean. "
      ::= { wseeOperationRuntimeEntry 26  }
   
   
   wseeOperationRuntimePolicySubjectResourcePattern OBJECT-TYPE
      SYNTAX      OCTET STRING
      MAX-ACCESS  read-only
      STATUS      current
      DESCRIPTION "The policySubject parameter must uniquely identify what application, module, service, and port (port or operation for WLS Policy) is targeted. The syntax currently used by JRF (see [JRF ATTACHMENT POINT]) for J2EE Webservice Endpoints will be used: /{domain}/{instance}/{app}/WEBs|EJBs/{module }/WEBSERVICEs/{service}/PORTs/{port}/OPERATIONs/{operation} "
      ::= { wseeOperationRuntimeEntry 27  }
   
   
   wseeOperationRuntimeLastResponseError OBJECT-TYPE
      SYNTAX      OCTET STRING
      MAX-ACCESS  read-only
      STATUS      current
      DESCRIPTION "Last response error to arrive for this client/service (or null if no errors have occurred). "
      ::= { wseeOperationRuntimeEntry 28  }
   
   
   wseeOperationRuntimeLastError OBJECT-TYPE
      SYNTAX      OCTET STRING
      MAX-ACCESS  read-only
      STATUS      current
      DESCRIPTION "Last error that occurred processing a request. "
      ::= { wseeOperationRuntimeEntry 29  }
   
   
   wseeOperationRuntimeLastInvocationTime OBJECT-TYPE
      SYNTAX      Counter64
      MAX-ACCESS  read-only
      STATUS      current
      DESCRIPTION "Time of the last operation request to be sent or received (or 0 if no requests have been sent or received). "
      ::= { wseeOperationRuntimeEntry 30  }
   
   
   wseeOperationRuntimeLastErrorTime OBJECT-TYPE
      SYNTAX      Counter64
      MAX-ACCESS  read-only
      STATUS      current
      DESCRIPTION "Time on WebLogic Server of the last error for a request (sending or receiving) was detected expressed as the number of milliseconds since midnight, January 1, 1970 UTC. "
      ::= { wseeOperationRuntimeEntry 31  }
   
   
   wseePolicyRuntimeTable OBJECT-TYPE
      SYNTAX      SEQUENCE OF WseePolicyRuntimeEntry
      MAX-ACCESS  not-accessible
      STATUS      current
      DESCRIPTION "Specifies runtime information about the WS-Policy files that are available for the Web Service.  Web Services can have one or more WS-Policy files associated with the endpoint itself or its operations; the WS-Policy files specify configuration options for Web Service message-level security (encryption and digital signatures) and reliable SOAP messaging.  Programmers can use the @Policy JWS annotation to associate a WS-Policy file to a Web Service at development time.  Administrators can also associate additional WS-Policy files at runtime. "
      ::= { wls 1500  }
      
   
   wseePolicyRuntimeEntry OBJECT-TYPE
      SYNTAX      WseePolicyRuntimeEntry
      MAX-ACCESS  not-accessible
      STATUS      current
      DESCRIPTION "Generated SNMP Table Entry."
      INDEX { wseePolicyRuntimeIndex}
      ::= { wseePolicyRuntimeTable 1 }
      
   WseePolicyRuntimeEntry ::=
      SEQUENCE
      {
         wseePolicyRuntimeIndex OCTET STRING,
         wseePolicyRuntimeObjectName OCTET STRING,
         wseePolicyRuntimeType OCTET STRING,
         wseePolicyRuntimeName OCTET STRING,
         wseePolicyRuntimeAvailablePolicies OCTET STRING
      }
      
   
   wseePolicyRuntimeIndex OBJECT-TYPE
      SYNTAX      OCTET STRING
      MAX-ACCESS  not-accessible
      STATUS      current
      DESCRIPTION "Index column"
      ::= { wseePolicyRuntimeEntry 1  }
   
   
   wseePolicyRuntimeObjectName OBJECT-TYPE
      SYNTAX      OCTET STRING
      MAX-ACCESS  read-only
      STATUS      current
      DESCRIPTION "ObjectName column"
      ::= { wseePolicyRuntimeEntry 2  }
   
   
   wseePolicyRuntimeType OBJECT-TYPE
      SYNTAX      OCTET STRING
      MAX-ACCESS  read-only
      STATUS      current
      DESCRIPTION "Returns the type of the MBean. "
      ::= { wseePolicyRuntimeEntry 3  }
   
   
   wseePolicyRuntimeName OBJECT-TYPE
      SYNTAX      OCTET STRING
      MAX-ACCESS  read-only
      STATUS      current
      DESCRIPTION "The name of this configuration. WebLogic Server uses an MBean to implement and persist the configuration. "
      ::= { wseePolicyRuntimeEntry 4  }
   
   
   wseePolicyRuntimeAvailablePolicies OBJECT-TYPE
      SYNTAX      OCTET STRING
      MAX-ACCESS  read-only
      STATUS      current
      DESCRIPTION " "
      ::= { wseePolicyRuntimeEntry 5  }
   
   
   wseePortRuntimeTable OBJECT-TYPE
      SYNTAX      SEQUENCE OF WseePortRuntimeEntry
      MAX-ACCESS  not-accessible
      STATUS      current
      DESCRIPTION "Describes the state of a particular Web Service port.   "
      ::= { wls 1505  }
      
   
   wseePortRuntimeEntry OBJECT-TYPE
      SYNTAX      WseePortRuntimeEntry
      MAX-ACCESS  not-accessible
      STATUS      current
      DESCRIPTION "Generated SNMP Table Entry."
      INDEX { wseePortRuntimeIndex}
      ::= { wseePortRuntimeTable 1 }
      
   WseePortRuntimeEntry ::=
      SEQUENCE
      {
         wseePortRuntimeIndex OCTET STRING,
         wseePortRuntimeObjectName OCTET STRING,
         wseePortRuntimeType  OCTET STRING,
         wseePortRuntimePortName OCTET STRING,
         wseePortRuntimeTransportProtocolType OCTET STRING,
         wseePortRuntimeName  OCTET STRING,
         wseePortRuntimePolicySubjectType OCTET STRING,
         wseePortRuntimePolicyAttachmentSupport OCTET STRING,
         wseePortRuntimePolicySubjectResourcePattern OCTET STRING,
         wseePortRuntimeTotalFaults INTEGER,
         wseePortRuntimePolicyFaults INTEGER,
         wseePortRuntimePolicySubjectName OCTET STRING,
         wseePortRuntimeStartTime Counter64,
         wseePortRuntimeTotalSecurityFaults INTEGER,
         wseePortRuntimePolicySubjectAbsolutePortableExpression OCTET STRING
      }
      
   
   wseePortRuntimeIndex OBJECT-TYPE
      SYNTAX      OCTET STRING
      MAX-ACCESS  not-accessible
      STATUS      current
      DESCRIPTION "Index column"
      ::= { wseePortRuntimeEntry 1  }
   
   
   wseePortRuntimeObjectName OBJECT-TYPE
      SYNTAX      OCTET STRING
      MAX-ACCESS  read-only
      STATUS      current
      DESCRIPTION "ObjectName column"
      ::= { wseePortRuntimeEntry 2  }
   
   
   wseePortRuntimeType OBJECT-TYPE
      SYNTAX      OCTET STRING
      MAX-ACCESS  read-only
      STATUS      current
      DESCRIPTION "Returns the type of the MBean. "
      ::= { wseePortRuntimeEntry 3  }
   
   
   wseePortRuntimePortName OBJECT-TYPE
      SYNTAX      OCTET STRING
      MAX-ACCESS  read-only
      STATUS      current
      DESCRIPTION "Name of this port.  This attribute corresponds to the 'name' attribute of the 'port' element in the WSDL that describes the Web service.  Programmers specify the name of the port using the portName attribute of the &#64;WLXXXTransport annotation, where XXX refers to the type of transport (HTTP, HTTPS, or JMS).  Programmers can also use the WLXXXTransport child element of the jwsc Ant task to specify this attribute. "
      ::= { wseePortRuntimeEntry 4  }
   
   
   wseePortRuntimeTransportProtocolType OBJECT-TYPE
      SYNTAX      OCTET STRING
      MAX-ACCESS  read-only
      STATUS      current
      DESCRIPTION "Transport protocol used to invoke this Web service, such as HTTP, HTTPS, or JMS.  This attribute determines the transport that is published in the endpoint address section of the WSDL of the Web Service. Programmers specify the transport by the type of &#64;WLXXXTransport JWS annotation they specify, where XXX refers to the type of transport (HTTP, HTTPS, or JMS).  Programmers can also use the WLXXXTransport child element of the jwsc Ant task to specify this attribute. "
      ::= { wseePortRuntimeEntry 5  }
   
   
   wseePortRuntimeName OBJECT-TYPE
      SYNTAX      OCTET STRING
      MAX-ACCESS  read-only
      STATUS      current
      DESCRIPTION "The name of this configuration. WebLogic Server uses an MBean to implement and persist the configuration. "
      ::= { wseePortRuntimeEntry 6  }
   
   
   wseePortRuntimePolicySubjectType OBJECT-TYPE
      SYNTAX      OCTET STRING
      MAX-ACCESS  read-only
      STATUS      current
      DESCRIPTION "Get subject type for this port MBean. "
      ::= { wseePortRuntimeEntry 7  }
   
   
   wseePortRuntimePolicyAttachmentSupport OBJECT-TYPE
      SYNTAX      OCTET STRING
      MAX-ACCESS  read-only
      STATUS      current
      DESCRIPTION "Get attachment support for this port MBean. "
      ::= { wseePortRuntimeEntry 8  }
   
   
   wseePortRuntimePolicySubjectResourcePattern OBJECT-TYPE
      SYNTAX      OCTET STRING
      MAX-ACCESS  read-only
      STATUS      current
      DESCRIPTION "The policySubject parameter must uniquely identify what application, module, service or reference-name, and port (port or operation for WLS Policy) is targeted. The syntax currently used by JRF (see [JRF ATTACHMENT POINT]) for J2EE Webservice Endpoints will be used: /{domain}/{instance}/{app}/WEBs|EJBs/{module}/WEBSERVICEs/{service}|{reference-name}/PORTs/{port} "
      ::= { wseePortRuntimeEntry 9  }
   
   
   wseePortRuntimeTotalFaults OBJECT-TYPE
      SYNTAX      INTEGER
      MAX-ACCESS  read-only
      STATUS      current
      DESCRIPTION "Total number of security faults and violations. "
      ::= { wseePortRuntimeEntry 10  }
   
   
   wseePortRuntimePolicyFaults OBJECT-TYPE
      SYNTAX      INTEGER
      MAX-ACCESS  read-only
      STATUS      current
      DESCRIPTION "Total number of policy faults. "
      ::= { wseePortRuntimeEntry 11  }
   
   
   wseePortRuntimePolicySubjectName OBJECT-TYPE
      SYNTAX      OCTET STRING
      MAX-ACCESS  read-only
      STATUS      current
      DESCRIPTION "Get subject name for this port MBean. "
      ::= { wseePortRuntimeEntry 12  }
   
   
   wseePortRuntimeStartTime OBJECT-TYPE
      SYNTAX      Counter64
      MAX-ACCESS  read-only
      STATUS      current
      DESCRIPTION "Date and time that the Web service endpoint started. "
      ::= { wseePortRuntimeEntry 13  }
   
   
   wseePortRuntimeTotalSecurityFaults OBJECT-TYPE
      SYNTAX      INTEGER
      MAX-ACCESS  read-only
      STATUS      current
      DESCRIPTION "Total number of security faults and violations. "
      ::= { wseePortRuntimeEntry 14  }
   
   
   wseePortRuntimePolicySubjectAbsolutePortableExpression OBJECT-TYPE
      SYNTAX      OCTET STRING
      MAX-ACCESS  read-only
      STATUS      current
      DESCRIPTION "The policySubject AbsolutePortableExpression This is the WSM ResourcePattern AbsolutePortableExpression string "
      ::= { wseePortRuntimeEntry 15  }
   
   
   wseeRuntimeTable OBJECT-TYPE
      SYNTAX      SEQUENCE OF WseeRuntimeEntry
      MAX-ACCESS  not-accessible
      STATUS      current
      DESCRIPTION "Encapsulates runtime information about a particular Web Service."
      ::= { wls 1510  }
      
   
   wseeRuntimeEntry OBJECT-TYPE
      SYNTAX      WseeRuntimeEntry
      MAX-ACCESS  not-accessible
      STATUS      current
      DESCRIPTION "Generated SNMP Table Entry."
      INDEX { wseeRuntimeIndex}
      ::= { wseeRuntimeTable 1 }
      
   WseeRuntimeEntry ::=
      SEQUENCE
      {
         wseeRuntimeIndex     OCTET STRING,
         wseeRuntimeObjectName OCTET STRING,
         wseeRuntimeType      OCTET STRING,
         wseeRuntimeWebserviceDescriptionName OCTET STRING,
         wseeRuntimeImplementationType OCTET STRING,
         wseeRuntimeURI       OCTET STRING,
         wseeRuntimeName      OCTET STRING,
         wseeRuntimeServiceName OCTET STRING
      }
      
   
   wseeRuntimeIndex OBJECT-TYPE
      SYNTAX      OCTET STRING
      MAX-ACCESS  not-accessible
      STATUS      current
      DESCRIPTION "Index column"
      ::= { wseeRuntimeEntry 1  }
   
   
   wseeRuntimeObjectName OBJECT-TYPE
      SYNTAX      OCTET STRING
      MAX-ACCESS  read-only
      STATUS      current
      DESCRIPTION "ObjectName column"
      ::= { wseeRuntimeEntry 2  }
   
   
   wseeRuntimeType OBJECT-TYPE
      SYNTAX      OCTET STRING
      MAX-ACCESS  read-only
      STATUS      current
      DESCRIPTION "Returns the type of the MBean."
      ::= { wseeRuntimeEntry 3  }
   
   
   wseeRuntimeWebserviceDescriptionName OBJECT-TYPE
      SYNTAX      OCTET STRING
      MAX-ACCESS  read-only
      STATUS      current
      DESCRIPTION "webservice description name for this webservice"
      ::= { wseeRuntimeEntry 4  }
   
   
   wseeRuntimeImplementationType OBJECT-TYPE
      SYNTAX      OCTET STRING
      MAX-ACCESS  read-only
      STATUS      current
      DESCRIPTION "Specifies the implementation type of this service.  The allowed values are: JAX-WS 2.0 JAX-RPC 1.1"
      ::= { wseeRuntimeEntry 5  }
   
   
   wseeRuntimeURI OBJECT-TYPE
      SYNTAX      OCTET STRING
      MAX-ACCESS  read-only
      STATUS      current
      DESCRIPTION "Specifies the URI of this Web Service.  This attribute corresponds to the final part of the endpoint address in the WSDL that describes the Web Services.  It is specified at development time using the contextPath and serviceURI attributes of the"
      ::= { wseeRuntimeEntry 6  }
   
   
   wseeRuntimeName OBJECT-TYPE
      SYNTAX      OCTET STRING
      MAX-ACCESS  read-only
      STATUS      current
      DESCRIPTION "The name of this configuration. WebLogic Server uses an MBean to implement and persist the configuration."
      ::= { wseeRuntimeEntry 7  }
   
   
   wseeRuntimeServiceName OBJECT-TYPE
      SYNTAX      OCTET STRING
      MAX-ACCESS  read-only
      STATUS      current
      DESCRIPTION "Specifies the name of this service.  This attribute corresponds to the 'name' attribute of the 'service' element in the WSDL that describes the Web Service.  It is specified at development time using the serviceName attribute of the @WebService JWS annotation."
      ::= { wseeRuntimeEntry 8  }
   
   
   channelRuntimeTable OBJECT-TYPE
      SYNTAX      SEQUENCE OF ChannelRuntimeEntry
      MAX-ACCESS  not-accessible
      STATUS      current
      DESCRIPTION " "
      ::= { wls 1520  }
      
   
   channelRuntimeEntry OBJECT-TYPE
      SYNTAX      ChannelRuntimeEntry
      MAX-ACCESS  not-accessible
      STATUS      current
      DESCRIPTION "Generated SNMP Table Entry."
      INDEX { channelRuntimeIndex}
      ::= { channelRuntimeTable 1 }
      
   ChannelRuntimeEntry ::=
      SEQUENCE
      {
         channelRuntimeIndex  OCTET STRING,
         channelRuntimeObjectName OCTET STRING,
         channelRuntimePublishedMessageCount Counter64,
         channelRuntimeSubscriberCount Integer32,
         channelRuntimeType   OCTET STRING,
         channelRuntimeName   OCTET STRING
      }
      
   
   channelRuntimeIndex OBJECT-TYPE
      SYNTAX      OCTET STRING
      MAX-ACCESS  not-accessible
      STATUS      current
      DESCRIPTION "Index column"
      ::= { channelRuntimeEntry 1  }
   
   
   channelRuntimeObjectName OBJECT-TYPE
      SYNTAX      OCTET STRING
      MAX-ACCESS  read-only
      STATUS      current
      DESCRIPTION "ObjectName column"
      ::= { channelRuntimeEntry 2  }
   
   
   channelRuntimePublishedMessageCount OBJECT-TYPE
      SYNTAX      Counter64
      MAX-ACCESS  read-only
      STATUS      current
      DESCRIPTION "Get the number of published messages to this Channel "
      ::= { channelRuntimeEntry 3  }
   
   
   channelRuntimeSubscriberCount OBJECT-TYPE
      SYNTAX      Integer32
      MAX-ACCESS  read-only
      STATUS      current
      DESCRIPTION "Get the number of subscribers for this channel currently "
      ::= { channelRuntimeEntry 4  }
   
   
   channelRuntimeType OBJECT-TYPE
      SYNTAX      OCTET STRING
      MAX-ACCESS  read-only
      STATUS      current
      DESCRIPTION "Returns the type of the MBean. "
      ::= { channelRuntimeEntry 5  }
   
   
   channelRuntimeName OBJECT-TYPE
      SYNTAX      OCTET STRING
      MAX-ACCESS  read-only
      STATUS      current
      DESCRIPTION "Get the qualified name for this channel "
      ::= { channelRuntimeEntry 6  }
   
   
   manAsyncReplicationRuntimeTable OBJECT-TYPE
      SYNTAX      SEQUENCE OF ManAsyncReplicationRuntimeEntry
      MAX-ACCESS  not-accessible
      STATUS      current
      DESCRIPTION "RuntimeMBean for MAN Asynchronous Replication "
      ::= { wls 1525  }
      
   
   manAsyncReplicationRuntimeEntry OBJECT-TYPE
      SYNTAX      ManAsyncReplicationRuntimeEntry
      MAX-ACCESS  not-accessible
      STATUS      current
      DESCRIPTION "Generated SNMP Table Entry."
      INDEX { manAsyncReplicationRuntimeIndex}
      ::= { manAsyncReplicationRuntimeTable 1 }
      
   ManAsyncReplicationRuntimeEntry ::=
      SEQUENCE
      {
         manAsyncReplicationRuntimeIndex OCTET STRING,
         manAsyncReplicationRuntimeObjectName OCTET STRING,
         manAsyncReplicationRuntimeSecondaryServerName OCTET STRING,
         manAsyncReplicationRuntimeType OCTET STRING,
         manAsyncReplicationRuntimePrimaryCount Counter64,
         manAsyncReplicationRuntimeName OCTET STRING,
         manAsyncReplicationRuntimeRemoteClusterReachable OCTET STRING,
         manAsyncReplicationRuntimeSecondaryServerDetails OCTET STRING,
         manAsyncReplicationRuntimeSecondaryCount Counter64,
         manAsyncReplicationRuntimeDetailedSecondariesDistribution OCTET STRING,
         manAsyncReplicationRuntimeActiveServersInRemoteCluster OCTET STRING,
         manAsyncReplicationRuntimeLastSessionsFlushTime Counter64,
         manAsyncReplicationRuntimeSessionsWaitingForFlushCount INTEGER
      }
      
   
   manAsyncReplicationRuntimeIndex OBJECT-TYPE
      SYNTAX      OCTET STRING
      MAX-ACCESS  not-accessible
      STATUS      current
      DESCRIPTION "Index column"
      ::= { manAsyncReplicationRuntimeEntry 1  }
   
   
   manAsyncReplicationRuntimeObjectName OBJECT-TYPE
      SYNTAX      OCTET STRING
      MAX-ACCESS  read-only
      STATUS      current
      DESCRIPTION "ObjectName column"
      ::= { manAsyncReplicationRuntimeEntry 2  }
   
   
   manAsyncReplicationRuntimeSecondaryServerName OBJECT-TYPE
      SYNTAX      OCTET STRING
      MAX-ACCESS  read-only
      STATUS      current
      DESCRIPTION " Answer the name of the secondary server  "
      ::= { manAsyncReplicationRuntimeEntry 3  }
   
   
   manAsyncReplicationRuntimeType OBJECT-TYPE
      SYNTAX      OCTET STRING
      MAX-ACCESS  read-only
      STATUS      current
      DESCRIPTION "Returns the type of the MBean. "
      ::= { manAsyncReplicationRuntimeEntry 4  }
   
   
   manAsyncReplicationRuntimePrimaryCount OBJECT-TYPE
      SYNTAX      Counter64
      MAX-ACCESS  read-only
      STATUS      current
      DESCRIPTION "Provides the number of object that the local server hosts as primaries.  Answer the number of object that the local server hosts as primaries. "
      ::= { manAsyncReplicationRuntimeEntry 5  }
   
   
   manAsyncReplicationRuntimeName OBJECT-TYPE
      SYNTAX      OCTET STRING
      MAX-ACCESS  read-only
      STATUS      current
      DESCRIPTION "The name of this configuration. WebLogic Server uses an MBean to implement and persist the configuration. "
      ::= { manAsyncReplicationRuntimeEntry 6  }
   
   
   manAsyncReplicationRuntimeRemoteClusterReachable OBJECT-TYPE
      SYNTAX      OCTET STRING
      MAX-ACCESS  read-only
      STATUS      current
      DESCRIPTION "Answer if the remote cluster is reachable or not. "
      ::= { manAsyncReplicationRuntimeEntry 7  }
   
   
   manAsyncReplicationRuntimeSecondaryServerDetails OBJECT-TYPE
      SYNTAX      OCTET STRING
      MAX-ACCESS  read-only
      STATUS      current
      DESCRIPTION " "
      ::= { manAsyncReplicationRuntimeEntry 8  }
   
   
   manAsyncReplicationRuntimeSecondaryCount OBJECT-TYPE
      SYNTAX      Counter64
      MAX-ACCESS  read-only
      STATUS      current
      DESCRIPTION "Answer the number of object that the local server hosts as secondaries. "
      ::= { manAsyncReplicationRuntimeEntry 9  }
   
   
   manAsyncReplicationRuntimeDetailedSecondariesDistribution OBJECT-TYPE
      SYNTAX      OCTET STRING
      MAX-ACCESS  read-only
      STATUS      current
      DESCRIPTION "Provides the names of the remote servers (such as myserver) for which the local server is hosting secondary objects. The name is appended with a number to indicate the number of secondaries hosted on behalf of that server. "
      ::= { manAsyncReplicationRuntimeEntry 10  }
   
   
   manAsyncReplicationRuntimeActiveServersInRemoteCluster OBJECT-TYPE
      SYNTAX      OCTET STRING
      MAX-ACCESS  read-only
      STATUS      current
      DESCRIPTION " "
      ::= { manAsyncReplicationRuntimeEntry 11  }
   
   
   manAsyncReplicationRuntimeLastSessionsFlushTime OBJECT-TYPE
      SYNTAX      Counter64
      MAX-ACCESS  read-only
      STATUS      current
      DESCRIPTION "The last time the sessions were flushed, in milliseconds since midnight, January 1, 1970 UTC "
      ::= { manAsyncReplicationRuntimeEntry 12  }
   
   
   manAsyncReplicationRuntimeSessionsWaitingForFlushCount OBJECT-TYPE
      SYNTAX      INTEGER
      MAX-ACCESS  read-only
      STATUS      current
      DESCRIPTION "Number of sessions which are waiting to be flushed. "
      ::= { manAsyncReplicationRuntimeEntry 13  }
   
   
   webPubSubRuntimeTable OBJECT-TYPE
      SYNTAX      SEQUENCE OF WebPubSubRuntimeEntry
      MAX-ACCESS  not-accessible
      STATUS      current
      DESCRIPTION " "
      ::= { wls 1545  }
      
   
   webPubSubRuntimeEntry OBJECT-TYPE
      SYNTAX      WebPubSubRuntimeEntry
      MAX-ACCESS  not-accessible
      STATUS      current
      DESCRIPTION "Generated SNMP Table Entry."
      INDEX { webPubSubRuntimeIndex}
      ::= { webPubSubRuntimeTable 1 }
      
   WebPubSubRuntimeEntry ::=
      SEQUENCE
      {
         webPubSubRuntimeIndex OCTET STRING,
         webPubSubRuntimeObjectName OCTET STRING,
         webPubSubRuntimeType OCTET STRING,
         webPubSubRuntimeName OCTET STRING
      }
      
   
   webPubSubRuntimeIndex OBJECT-TYPE
      SYNTAX      OCTET STRING
      MAX-ACCESS  not-accessible
      STATUS      current
      DESCRIPTION "Index column"
      ::= { webPubSubRuntimeEntry 1  }
   
   
   webPubSubRuntimeObjectName OBJECT-TYPE
      SYNTAX      OCTET STRING
      MAX-ACCESS  read-only
      STATUS      current
      DESCRIPTION "ObjectName column"
      ::= { webPubSubRuntimeEntry 2  }
   
   
   webPubSubRuntimeType OBJECT-TYPE
      SYNTAX      OCTET STRING
      MAX-ACCESS  read-only
      STATUS      current
      DESCRIPTION "Returns the type of the MBean. "
      ::= { webPubSubRuntimeEntry 3  }
   
   
   webPubSubRuntimeName OBJECT-TYPE
      SYNTAX      OCTET STRING
      MAX-ACCESS  read-only
      STATUS      current
      DESCRIPTION "Get the context-root of the webapp associated with the event router "
      ::= { webPubSubRuntimeEntry 4  }
   
   
   cacheAsyncListenersTable OBJECT-TYPE
      SYNTAX      SEQUENCE OF CacheAsyncListenersEntry
      MAX-ACCESS  not-accessible
      STATUS      current
      DESCRIPTION " "
      ::= { wls 1550  }
      
   
   cacheAsyncListenersEntry OBJECT-TYPE
      SYNTAX      CacheAsyncListenersEntry
      MAX-ACCESS  not-accessible
      STATUS      current
      DESCRIPTION "Generated SNMP Table Entry."
      INDEX { cacheAsyncListenersIndex}
      ::= { cacheAsyncListenersTable 1 }
      
   CacheAsyncListenersEntry ::=
      SEQUENCE
      {
         cacheAsyncListenersIndex OCTET STRING,
         cacheAsyncListenersObjectName OCTET STRING,
         cacheAsyncListenersWorkManager OCTET STRING,
         cacheAsyncListenersEnabled OCTET STRING,
         cacheAsyncListenersType OCTET STRING,
         cacheAsyncListenersName OCTET STRING,
         cacheAsyncListenersTags OCTET STRING
      }
      
   
   cacheAsyncListenersIndex OBJECT-TYPE
      SYNTAX      OCTET STRING
      MAX-ACCESS  not-accessible
      STATUS      current
      DESCRIPTION "Index column"
      ::= { cacheAsyncListenersEntry 1  }
   
   
   cacheAsyncListenersObjectName OBJECT-TYPE
      SYNTAX      OCTET STRING
      MAX-ACCESS  read-only
      STATUS      current
      DESCRIPTION "ObjectName column"
      ::= { cacheAsyncListenersEntry 2  }
   
   
   cacheAsyncListenersWorkManager OBJECT-TYPE
      SYNTAX      OCTET STRING
      MAX-ACCESS  read-only
      STATUS      current
      DESCRIPTION "The work manager to be used for firing event listeners asynchronously "
      ::= { cacheAsyncListenersEntry 3  }
   
   
   cacheAsyncListenersEnabled OBJECT-TYPE
      SYNTAX      OCTET STRING
      MAX-ACCESS  read-only
      STATUS      current
      DESCRIPTION "Specify if listeners must be fired asynchronously "
      ::= { cacheAsyncListenersEntry 4  }
   
   
   cacheAsyncListenersType OBJECT-TYPE
      SYNTAX      OCTET STRING
      MAX-ACCESS  read-only
      STATUS      current
      DESCRIPTION "Returns the type of the MBean. "
      ::= { cacheAsyncListenersEntry 5  }
   
   
   cacheAsyncListenersName OBJECT-TYPE
      SYNTAX      OCTET STRING
      MAX-ACCESS  read-only
      STATUS      current
      DESCRIPTION "The user-specified name of this MBean instance.  This name is included as one of the key properties in the MBean's javax.management.ObjectName:  Name=user-specified-name "
      ::= { cacheAsyncListenersEntry 6  }
   
   
   cacheAsyncListenersTags OBJECT-TYPE
      SYNTAX      OCTET STRING
      MAX-ACCESS  read-only
      STATUS      current
      DESCRIPTION "Return all tags on this Configuration MBean "
      ::= { cacheAsyncListenersEntry 7  }
   
   
   cacheExpirationTable OBJECT-TYPE
      SYNTAX      SEQUENCE OF CacheExpirationEntry
      MAX-ACCESS  not-accessible
      STATUS      current
      DESCRIPTION " "
      ::= { wls 1555  }
      
   
   cacheExpirationEntry OBJECT-TYPE
      SYNTAX      CacheExpirationEntry
      MAX-ACCESS  not-accessible
      STATUS      current
      DESCRIPTION "Generated SNMP Table Entry."
      INDEX { cacheExpirationIndex}
      ::= { cacheExpirationTable 1 }
      
   CacheExpirationEntry ::=
      SEQUENCE
      {
         cacheExpirationIndex OCTET STRING,
         cacheExpirationObjectName OCTET STRING,
         cacheExpirationType  OCTET STRING,
         cacheExpirationTTL   Counter64,
         cacheExpirationIdleTime Counter64,
         cacheExpirationName  OCTET STRING,
         cacheExpirationTags  OCTET STRING
      }
      
   
   cacheExpirationIndex OBJECT-TYPE
      SYNTAX      OCTET STRING
      MAX-ACCESS  not-accessible
      STATUS      current
      DESCRIPTION "Index column"
      ::= { cacheExpirationEntry 1  }
   
   
   cacheExpirationObjectName OBJECT-TYPE
      SYNTAX      OCTET STRING
      MAX-ACCESS  read-only
      STATUS      current
      DESCRIPTION "ObjectName column"
      ::= { cacheExpirationEntry 2  }
   
   
   cacheExpirationType OBJECT-TYPE
      SYNTAX      OCTET STRING
      MAX-ACCESS  read-only
      STATUS      current
      DESCRIPTION "Returns the type of the MBean. "
      ::= { cacheExpirationEntry 3  }
   
   
   cacheExpirationTTL OBJECT-TYPE
      SYNTAX      Counter64
      MAX-ACCESS  read-only
      STATUS      current
      DESCRIPTION "The time after creation an entry is removed from the cache. TTL is measured in milliseconds "
      ::= { cacheExpirationEntry 4  }
   
   
   cacheExpirationIdleTime OBJECT-TYPE
      SYNTAX      Counter64
      MAX-ACCESS  read-only
      STATUS      current
      DESCRIPTION "The time after last access an entry becomes a target for eviction. Idle time is measured in milliseconds. "
      ::= { cacheExpirationEntry 5  }
   
   
   cacheExpirationName OBJECT-TYPE
      SYNTAX      OCTET STRING
      MAX-ACCESS  read-only
      STATUS      current
      DESCRIPTION "The user-specified name of this MBean instance.  This name is included as one of the key properties in the MBean's javax.management.ObjectName:  Name=user-specified-name "
      ::= { cacheExpirationEntry 6  }
   
   
   cacheExpirationTags OBJECT-TYPE
      SYNTAX      OCTET STRING
      MAX-ACCESS  read-only
      STATUS      current
      DESCRIPTION "Return all tags on this Configuration MBean "
      ::= { cacheExpirationEntry 7  }
   
   
   cacheLoaderTable OBJECT-TYPE
      SYNTAX      SEQUENCE OF CacheLoaderEntry
      MAX-ACCESS  not-accessible
      STATUS      current
      DESCRIPTION " "
      ::= { wls 1560  }
      
   
   cacheLoaderEntry OBJECT-TYPE
      SYNTAX      CacheLoaderEntry
      MAX-ACCESS  not-accessible
      STATUS      current
      DESCRIPTION "Generated SNMP Table Entry."
      INDEX { cacheLoaderIndex}
      ::= { cacheLoaderTable 1 }
      
   CacheLoaderEntry ::=
      SEQUENCE
      {
         cacheLoaderIndex     OCTET STRING,
         cacheLoaderObjectName OCTET STRING,
         cacheLoaderCustomLoader OCTET STRING,
         cacheLoaderType      OCTET STRING,
         cacheLoaderName      OCTET STRING,
         cacheLoaderTags      OCTET STRING
      }
      
   
   cacheLoaderIndex OBJECT-TYPE
      SYNTAX      OCTET STRING
      MAX-ACCESS  not-accessible
      STATUS      current
      DESCRIPTION "Index column"
      ::= { cacheLoaderEntry 1  }
   
   
   cacheLoaderObjectName OBJECT-TYPE
      SYNTAX      OCTET STRING
      MAX-ACCESS  read-only
      STATUS      current
      DESCRIPTION "ObjectName column"
      ::= { cacheLoaderEntry 2  }
   
   
   cacheLoaderCustomLoader OBJECT-TYPE
      SYNTAX      OCTET STRING
      MAX-ACCESS  read-only
      STATUS      current
      DESCRIPTION "The custom loader to be used for self loading caches "
      ::= { cacheLoaderEntry 3  }
   
   
   cacheLoaderType OBJECT-TYPE
      SYNTAX      OCTET STRING
      MAX-ACCESS  read-only
      STATUS      current
      DESCRIPTION "Returns the type of the MBean. "
      ::= { cacheLoaderEntry 4  }
   
   
   cacheLoaderName OBJECT-TYPE
      SYNTAX      OCTET STRING
      MAX-ACCESS  read-only
      STATUS      current
      DESCRIPTION "The user-specified name of this MBean instance.  This name is included as one of the key properties in the MBean's javax.management.ObjectName:  Name=user-specified-name "
      ::= { cacheLoaderEntry 5  }
   
   
   cacheLoaderTags OBJECT-TYPE
      SYNTAX      OCTET STRING
      MAX-ACCESS  read-only
      STATUS      current
      DESCRIPTION "Return all tags on this Configuration MBean "
      ::= { cacheLoaderEntry 6  }
   
   
   cacheTable OBJECT-TYPE
      SYNTAX      SEQUENCE OF CacheEntry
      MAX-ACCESS  not-accessible
      STATUS      current
      DESCRIPTION " "
      ::= { wls 1565  }
      
   
   cacheEntry OBJECT-TYPE
      SYNTAX      CacheEntry
      MAX-ACCESS  not-accessible
      STATUS      current
      DESCRIPTION "Generated SNMP Table Entry."
      INDEX { cacheIndex}
      ::= { cacheTable 1 }
      
   CacheEntry ::=
      SEQUENCE
      {
         cacheIndex           OCTET STRING,
         cacheObjectName      OCTET STRING,
         cacheWorkManager     OCTET STRING,
         cacheType            OCTET STRING,
         cacheName            OCTET STRING,
         cacheEvictionPolicy  OCTET STRING,
         cacheMaxCacheUnits   Integer32,
         cacheJNDIName        OCTET STRING,
         cacheDeploymentOrder Integer32,
         cacheTags            OCTET STRING
      }
      
   
   cacheIndex OBJECT-TYPE
      SYNTAX      OCTET STRING
      MAX-ACCESS  not-accessible
      STATUS      current
      DESCRIPTION "Index column"
      ::= { cacheEntry 1  }
   
   
   cacheObjectName OBJECT-TYPE
      SYNTAX      OCTET STRING
      MAX-ACCESS  read-only
      STATUS      current
      DESCRIPTION "ObjectName column"
      ::= { cacheEntry 2  }
   
   
   cacheWorkManager OBJECT-TYPE
      SYNTAX      OCTET STRING
      MAX-ACCESS  read-only
      STATUS      current
      DESCRIPTION "Set the default work manager to use for all asynchronous caching tasks. If none of the specific work managers are specified, this work manager is used. This work manager may be overriden by other work managers configured for specific tasks like store backup, listeners etc "
      ::= { cacheEntry 3  }
   
   
   cacheType OBJECT-TYPE
      SYNTAX      OCTET STRING
      MAX-ACCESS  read-only
      STATUS      current
      DESCRIPTION "Returns the type of the MBean. "
      ::= { cacheEntry 4  }
   
   
   cacheName OBJECT-TYPE
      SYNTAX      OCTET STRING
      MAX-ACCESS  read-only
      STATUS      current
      DESCRIPTION "The user-specified name of this MBean instance.  This name is included as one of the key properties in the MBean's javax.management.ObjectName:  Name=user-specified-name "
      ::= { cacheEntry 5  }
   
   
   cacheEvictionPolicy OBJECT-TYPE
      SYNTAX      OCTET STRING
      MAX-ACCESS  read-only
      STATUS      current
      DESCRIPTION "The eviction policy to choose when the number of entries in cache hits the maximum "
      ::= { cacheEntry 6  }
   
   
   cacheMaxCacheUnits OBJECT-TYPE
      SYNTAX      Integer32
      MAX-ACCESS  read-only
      STATUS      current
      DESCRIPTION "Maximum number of cache elements in memory after which eviction/paging occurs. This value is defined as an Integer. "
      ::= { cacheEntry 7  }
   
   
   cacheJNDIName OBJECT-TYPE
      SYNTAX      OCTET STRING
      MAX-ACCESS  read-only
      STATUS      current
      DESCRIPTION " "
      ::= { cacheEntry 8  }
   
   
   cacheDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { cacheEntry 9  }
   
   
   cacheTags OBJECT-TYPE
      SYNTAX      OCTET STRING
      MAX-ACCESS  read-only
      STATUS      current
      DESCRIPTION "Return all tags on this Configuration MBean "
      ::= { cacheEntry 10  }
   
   
   cacheStoreTable OBJECT-TYPE
      SYNTAX      SEQUENCE OF CacheStoreEntry
      MAX-ACCESS  not-accessible
      STATUS      current
      DESCRIPTION " "
      ::= { wls 1570  }
      
   
   cacheStoreEntry OBJECT-TYPE
      SYNTAX      CacheStoreEntry
      MAX-ACCESS  not-accessible
      STATUS      current
      DESCRIPTION "Generated SNMP Table Entry."
      INDEX { cacheStoreIndex}
      ::= { cacheStoreTable 1 }
      
   CacheStoreEntry ::=
      SEQUENCE
      {
         cacheStoreIndex      OCTET STRING,
         cacheStoreObjectName OCTET STRING,
         cacheStoreWorkManager OCTET STRING,
         cacheStoreStoreBatchSize Integer32,
         cacheStoreBufferMaxSize Integer32,
         cacheStoreType       OCTET STRING,
         cacheStoreBufferWriteAttempts Integer32,
         cacheStoreCustomStore OCTET STRING,
         cacheStoreName       OCTET STRING,
         cacheStoreBufferWriteTimeout Counter64,
         cacheStoreWritePolicy OCTET STRING,
         cacheStoreTags       OCTET STRING
      }
      
   
   cacheStoreIndex OBJECT-TYPE
      SYNTAX      OCTET STRING
      MAX-ACCESS  not-accessible
      STATUS      current
      DESCRIPTION "Index column"
      ::= { cacheStoreEntry 1  }
   
   
   cacheStoreObjectName OBJECT-TYPE
      SYNTAX      OCTET STRING
      MAX-ACCESS  read-only
      STATUS      current
      DESCRIPTION "ObjectName column"
      ::= { cacheStoreEntry 2  }
   
   
   cacheStoreWorkManager OBJECT-TYPE
      SYNTAX      OCTET STRING
      MAX-ACCESS  read-only
      STATUS      current
      DESCRIPTION "Sets the work manager that schedules the thread that writes to the backing store asynchronously "
      ::= { cacheStoreEntry 3  }
   
   
   cacheStoreStoreBatchSize OBJECT-TYPE
      SYNTAX      Integer32
      MAX-ACCESS  read-only
      STATUS      current
      DESCRIPTION "Sets the number of user updates that are picked up from the store buffer to write back to the backing store "
      ::= { cacheStoreEntry 4  }
   
   
   cacheStoreBufferMaxSize OBJECT-TYPE
      SYNTAX      Integer32
      MAX-ACCESS  read-only
      STATUS      current
      DESCRIPTION "Sets the upper limit for the store buffer that's used to write out updates to the store. A value of 0 indicates no limit "
      ::= { cacheStoreEntry 5  }
   
   
   cacheStoreType OBJECT-TYPE
      SYNTAX      OCTET STRING
      MAX-ACCESS  read-only
      STATUS      current
      DESCRIPTION "Returns the type of the MBean. "
      ::= { cacheStoreEntry 6  }
   
   
   cacheStoreBufferWriteAttempts OBJECT-TYPE
      SYNTAX      Integer32
      MAX-ACCESS  read-only
      STATUS      current
      DESCRIPTION "Sets the number of attempts that the user thread will make to write to the store buffer. "
      ::= { cacheStoreEntry 7  }
   
   
   cacheStoreCustomStore OBJECT-TYPE
      SYNTAX      OCTET STRING
      MAX-ACCESS  read-only
      STATUS      current
      DESCRIPTION "The cache store to be used for store backed caches "
      ::= { cacheStoreEntry 8  }
   
   
   cacheStoreName OBJECT-TYPE
      SYNTAX      OCTET STRING
      MAX-ACCESS  read-only
      STATUS      current
      DESCRIPTION "The user-specified name of this MBean instance.  This name is included as one of the key properties in the MBean's javax.management.ObjectName:  Name=user-specified-name "
      ::= { cacheStoreEntry 9  }
   
   
   cacheStoreBufferWriteTimeout OBJECT-TYPE
      SYNTAX      Counter64
      MAX-ACCESS  read-only
      STATUS      current
      DESCRIPTION "Sets the time in milliseconds that the user thread will wait before aborting an attempt to write to the buffer. The attempt to write to the store buffer fails only in case the buffer is full. After the timeout, futher attempts may be made to write to the buffer based on the value of StoreBufferWriteAttempts "
      ::= { cacheStoreEntry 10  }
   
   
   cacheStoreWritePolicy OBJECT-TYPE
      SYNTAX      OCTET STRING
      MAX-ACCESS  read-only
      STATUS      current
      DESCRIPTION " "
      ::= { cacheStoreEntry 11  }
   
   
   cacheStoreTags OBJECT-TYPE
      SYNTAX      OCTET STRING
      MAX-ACCESS  read-only
      STATUS      current
      DESCRIPTION "Return all tags on this Configuration MBean "
      ::= { cacheStoreEntry 12  }
   
   
   cacheTransactionTable OBJECT-TYPE
      SYNTAX      SEQUENCE OF CacheTransactionEntry
      MAX-ACCESS  not-accessible
      STATUS      current
      DESCRIPTION " "
      ::= { wls 1575  }
      
   
   cacheTransactionEntry OBJECT-TYPE
      SYNTAX      CacheTransactionEntry
      MAX-ACCESS  not-accessible
      STATUS      current
      DESCRIPTION "Generated SNMP Table Entry."
      INDEX { cacheTransactionIndex}
      ::= { cacheTransactionTable 1 }
      
   CacheTransactionEntry ::=
      SEQUENCE
      {
         cacheTransactionIndex OCTET STRING,
         cacheTransactionObjectName OCTET STRING,
         cacheTransactionType OCTET STRING,
         cacheTransactionName OCTET STRING,
         cacheTransactionIsolationLevel OCTET STRING,
         cacheTransactionConcurrency OCTET STRING,
         cacheTransactionTags OCTET STRING
      }
      
   
   cacheTransactionIndex OBJECT-TYPE
      SYNTAX      OCTET STRING
      MAX-ACCESS  not-accessible
      STATUS      current
      DESCRIPTION "Index column"
      ::= { cacheTransactionEntry 1  }
   
   
   cacheTransactionObjectName OBJECT-TYPE
      SYNTAX      OCTET STRING
      MAX-ACCESS  read-only
      STATUS      current
      DESCRIPTION "ObjectName column"
      ::= { cacheTransactionEntry 2  }
   
   
   cacheTransactionType OBJECT-TYPE
      SYNTAX      OCTET STRING
      MAX-ACCESS  read-only
      STATUS      current
      DESCRIPTION "Returns the type of the MBean. "
      ::= { cacheTransactionEntry 3  }
   
   
   cacheTransactionName OBJECT-TYPE
      SYNTAX      OCTET STRING
      MAX-ACCESS  read-only
      STATUS      current
      DESCRIPTION "The user-specified name of this MBean instance.  This name is included as one of the key properties in the MBean's javax.management.ObjectName:  Name=user-specified-name "
      ::= { cacheTransactionEntry 4  }
   
   
   cacheTransactionIsolationLevel OBJECT-TYPE
      SYNTAX      OCTET STRING
      MAX-ACCESS  read-only
      STATUS      current
      DESCRIPTION " "
      ::= { cacheTransactionEntry 5  }
   
   
   cacheTransactionConcurrency OBJECT-TYPE
      SYNTAX      OCTET STRING
      MAX-ACCESS  read-only
      STATUS      current
      DESCRIPTION "Setting this property to something other than none will make this cache transactional "
      ::= { cacheTransactionEntry 6  }
   
   
   cacheTransactionTags OBJECT-TYPE
      SYNTAX      OCTET STRING
      MAX-ACCESS  read-only
      STATUS      current
      DESCRIPTION "Return all tags on this Configuration MBean "
      ::= { cacheTransactionEntry 7  }
   
   
   consoleRuntimeTable OBJECT-TYPE
      SYNTAX      SEQUENCE OF ConsoleRuntimeEntry
      MAX-ACCESS  not-accessible
      STATUS      current
      DESCRIPTION "Runtime services for the console. "
      ::= { wls 1580  }
      
   
   consoleRuntimeEntry OBJECT-TYPE
      SYNTAX      ConsoleRuntimeEntry
      MAX-ACCESS  not-accessible
      STATUS      current
      DESCRIPTION "Generated SNMP Table Entry."
      INDEX { consoleRuntimeIndex}
      ::= { consoleRuntimeTable 1 }
      
   ConsoleRuntimeEntry ::=
      SEQUENCE
      {
         consoleRuntimeIndex  OCTET STRING,
         consoleRuntimeObjectName OCTET STRING,
         consoleRuntimeEnabled OCTET STRING,
         consoleRuntimeType   OCTET STRING,
         consoleRuntimeHomePageURL OCTET STRING,
         consoleRuntimeName   OCTET STRING
      }
      
   
   consoleRuntimeIndex OBJECT-TYPE
      SYNTAX      OCTET STRING
      MAX-ACCESS  not-accessible
      STATUS      current
      DESCRIPTION "Index column"
      ::= { consoleRuntimeEntry 1  }
   
   
   consoleRuntimeObjectName OBJECT-TYPE
      SYNTAX      OCTET STRING
      MAX-ACCESS  read-only
      STATUS      current
      DESCRIPTION "ObjectName column"
      ::= { consoleRuntimeEntry 2  }
   
   
   consoleRuntimeEnabled OBJECT-TYPE
      SYNTAX      OCTET STRING
      MAX-ACCESS  read-only
      STATUS      current
      DESCRIPTION "Is the console enabled? "
      ::= { consoleRuntimeEntry 3  }
   
   
   consoleRuntimeType OBJECT-TYPE
      SYNTAX      OCTET STRING
      MAX-ACCESS  read-only
      STATUS      current
      DESCRIPTION "Returns the type of the MBean. "
      ::= { consoleRuntimeEntry 4  }
   
   
   consoleRuntimeHomePageURL OBJECT-TYPE
      SYNTAX      OCTET STRING
      MAX-ACCESS  read-only
      STATUS      current
      DESCRIPTION "Gets the URL for the console's home page "
      ::= { consoleRuntimeEntry 5  }
   
   
   consoleRuntimeName OBJECT-TYPE
      SYNTAX      OCTET STRING
      MAX-ACCESS  read-only
      STATUS      current
      DESCRIPTION "The name of this configuration. WebLogic Server uses an MBean to implement and persist the configuration. "
      ::= { consoleRuntimeEntry 6  }
   
   
   owsmSecurityPolicyRuntimeTable OBJECT-TYPE
      SYNTAX      SEQUENCE OF OwsmSecurityPolicyRuntimeEntry
      MAX-ACCESS  not-accessible
      STATUS      current
      DESCRIPTION "Specifies runtime information about the WS-Policy files that are available for the Web Service.  Web Services can have one or more WS-Policy files associated with the endpoint itself or its operations; the WS-Policy files specify configuration options for Web Service message-level security (encryption and digital signatures) and reliable SOAP messaging.  Programmers can use the @Policy JWS annotation to associate a WS-Policy file to a Web Service at development time.  Administrators can also associate additional WS-Policy files at runtime. "
      ::= { wls 1585  }
      
   
   owsmSecurityPolicyRuntimeEntry OBJECT-TYPE
      SYNTAX      OwsmSecurityPolicyRuntimeEntry
      MAX-ACCESS  not-accessible
      STATUS      current
      DESCRIPTION "Generated SNMP Table Entry."
      INDEX { owsmSecurityPolicyRuntimeIndex}
      ::= { owsmSecurityPolicyRuntimeTable 1 }
      
   OwsmSecurityPolicyRuntimeEntry ::=
      SEQUENCE
      {
         owsmSecurityPolicyRuntimeIndex OCTET STRING,
         owsmSecurityPolicyRuntimeObjectName OCTET STRING,
         owsmSecurityPolicyRuntimeAvailablePolicies OCTET STRING,
         owsmSecurityPolicyRuntimeType OCTET STRING,
         owsmSecurityPolicyRuntimeName OCTET STRING
      }
      
   
   owsmSecurityPolicyRuntimeIndex OBJECT-TYPE
      SYNTAX      OCTET STRING
      MAX-ACCESS  not-accessible
      STATUS      current
      DESCRIPTION "Index column"
      ::= { owsmSecurityPolicyRuntimeEntry 1  }
   
   
   owsmSecurityPolicyRuntimeObjectName OBJECT-TYPE
      SYNTAX      OCTET STRING
      MAX-ACCESS  read-only
      STATUS      current
      DESCRIPTION "ObjectName column"
      ::= { owsmSecurityPolicyRuntimeEntry 2  }
   
   
   owsmSecurityPolicyRuntimeAvailablePolicies OBJECT-TYPE
      SYNTAX      OCTET STRING
      MAX-ACCESS  read-only
      STATUS      current
      DESCRIPTION " "
      ::= { owsmSecurityPolicyRuntimeEntry 3  }
   
   
   owsmSecurityPolicyRuntimeType OBJECT-TYPE
      SYNTAX      OCTET STRING
      MAX-ACCESS  read-only
      STATUS      current
      DESCRIPTION "Returns the type of the MBean. "
      ::= { owsmSecurityPolicyRuntimeEntry 4  }
   
   
   owsmSecurityPolicyRuntimeName OBJECT-TYPE
      SYNTAX      OCTET STRING
      MAX-ACCESS  read-only
      STATUS      current
      DESCRIPTION "The name of this configuration. WebLogic Server uses an MBean to implement and persist the configuration. "
      ::= { owsmSecurityPolicyRuntimeEntry 5  }
   
   
   springApplicationContextRuntimeTable OBJECT-TYPE
      SYNTAX      SEQUENCE OF SpringApplicationContextRuntimeEntry
      MAX-ACCESS  not-accessible
      STATUS      current
      DESCRIPTION "This MBean represents instances of class org.springframework.context.support.AbstractApplicationContext and org.springframework.beans.factory.support.AbstractBeanFactory There is a SpringApplicationContextRuntimeMBean for each application context in a deployment. "
      ::= { wls 1590  }
      
   
   springApplicationContextRuntimeEntry OBJECT-TYPE
      SYNTAX      SpringApplicationContextRuntimeEntry
      MAX-ACCESS  not-accessible
      STATUS      current
      DESCRIPTION "Generated SNMP Table Entry."
      INDEX { springApplicationContextRuntimeIndex}
      ::= { springApplicationContextRuntimeTable 1 }
      
   SpringApplicationContextRuntimeEntry ::=
      SEQUENCE
      {
         springApplicationContextRuntimeIndex OCTET STRING,
         springApplicationContextRuntimeObjectName OCTET STRING,
         springApplicationContextRuntimeGetBeansOfTypeCount Counter64,
         springApplicationContextRuntimeGetBeanNamesForTypeCount Counter64,
         springApplicationContextRuntimeType OCTET STRING,
         springApplicationContextRuntimeGetBeanCount Counter64,
         springApplicationContextRuntimeAverageSingletonBeanCreationTime OCTET STRING,
         springApplicationContextRuntimeAverageGetBeanNamesForTypeTime OCTET STRING,
         springApplicationContextRuntimeParentContext OCTET STRING,
         springApplicationContextRuntimeDisplayName OCTET STRING,
         springApplicationContextRuntimeStartupDate Counter64,
         springApplicationContextRuntimeName OCTET STRING,
         springApplicationContextRuntimeAveragePrototypeBeanCreationTime OCTET STRING,
         springApplicationContextRuntimePrototypeBeansCreatedCount Counter64,
         springApplicationContextRuntimeAverageGetBeansOfTypeTime OCTET STRING,
         springApplicationContextRuntimeSingletonBeansCreatedCount Counter64,
         springApplicationContextRuntimeRefreshCount Counter64,
         springApplicationContextRuntimeAverageGetBeanTime OCTET STRING,
         springApplicationContextRuntimeCustomScopeNames OCTET STRING,
         springApplicationContextRuntimeAverageRefreshTime OCTET STRING
      }
      
   
   springApplicationContextRuntimeIndex OBJECT-TYPE
      SYNTAX      OCTET STRING
      MAX-ACCESS  not-accessible
      STATUS      current
      DESCRIPTION "Index column"
      ::= { springApplicationContextRuntimeEntry 1  }
   
   
   springApplicationContextRuntimeObjectName OBJECT-TYPE
      SYNTAX      OCTET STRING
      MAX-ACCESS  read-only
      STATUS      current
      DESCRIPTION "ObjectName column"
      ::= { springApplicationContextRuntimeEntry 2  }
   
   
   springApplicationContextRuntimeGetBeansOfTypeCount OBJECT-TYPE
      SYNTAX      Counter64
      MAX-ACCESS  read-only
      STATUS      current
      DESCRIPTION "The number of times getBeansOfType() was called "
      ::= { springApplicationContextRuntimeEntry 3  }
   
   
   springApplicationContextRuntimeGetBeanNamesForTypeCount OBJECT-TYPE
      SYNTAX      Counter64
      MAX-ACCESS  read-only
      STATUS      current
      DESCRIPTION "The number of times getBeanNamesForType() was called "
      ::= { springApplicationContextRuntimeEntry 4  }
   
   
   springApplicationContextRuntimeType OBJECT-TYPE
      SYNTAX      OCTET STRING
      MAX-ACCESS  read-only
      STATUS      current
      DESCRIPTION "Returns the type of the MBean. "
      ::= { springApplicationContextRuntimeEntry 5  }
   
   
   springApplicationContextRuntimeGetBeanCount OBJECT-TYPE
      SYNTAX      Counter64
      MAX-ACCESS  read-only
      STATUS      current
      DESCRIPTION "The number of times getBean() was called "
      ::= { springApplicationContextRuntimeEntry 6  }
   
   
   springApplicationContextRuntimeAverageSingletonBeanCreationTime OBJECT-TYPE
      SYNTAX      OCTET STRING
      MAX-ACCESS  read-only
      STATUS      current
      DESCRIPTION "This returns the average elapsed time in milliseconds required to create singleton beans "
      ::= { springApplicationContextRuntimeEntry 7  }
   
   
   springApplicationContextRuntimeAverageGetBeanNamesForTypeTime OBJECT-TYPE
      SYNTAX      OCTET STRING
      MAX-ACCESS  read-only
      STATUS      current
      DESCRIPTION "This returns the average elapsed time in milliseconds required for getBeanNamesForType() "
      ::= { springApplicationContextRuntimeEntry 8  }
   
   
   springApplicationContextRuntimeParentContext OBJECT-TYPE
      SYNTAX      OCTET STRING
      MAX-ACCESS  read-only
      STATUS      current
      DESCRIPTION "The name of the parent context "
      ::= { springApplicationContextRuntimeEntry 9  }
   
   
   springApplicationContextRuntimeDisplayName OBJECT-TYPE
      SYNTAX      OCTET STRING
      MAX-ACCESS  read-only
      STATUS      current
      DESCRIPTION "Display name of the application context "
      ::= { springApplicationContextRuntimeEntry 10  }
   
   
   springApplicationContextRuntimeStartupDate OBJECT-TYPE
      SYNTAX      Counter64
      MAX-ACCESS  read-only
      STATUS      current
      DESCRIPTION "Return the timestamp in milliseconds when this context was first loaded "
      ::= { springApplicationContextRuntimeEntry 11  }
   
   
   springApplicationContextRuntimeName OBJECT-TYPE
      SYNTAX      OCTET STRING
      MAX-ACCESS  read-only
      STATUS      current
      DESCRIPTION "The name of this configuration. WebLogic Server uses an MBean to implement and persist the configuration. "
      ::= { springApplicationContextRuntimeEntry 12  }
   
   
   springApplicationContextRuntimeAveragePrototypeBeanCreationTime OBJECT-TYPE
      SYNTAX      OCTET STRING
      MAX-ACCESS  read-only
      STATUS      current
      DESCRIPTION "This returns the average elapsed time in milliseconds required to create prototype beans "
      ::= { springApplicationContextRuntimeEntry 13  }
   
   
   springApplicationContextRuntimePrototypeBeansCreatedCount OBJECT-TYPE
      SYNTAX      Counter64
      MAX-ACCESS  read-only
      STATUS      current
      DESCRIPTION "The number of Prototype beans created. "
      ::= { springApplicationContextRuntimeEntry 14  }
   
   
   springApplicationContextRuntimeAverageGetBeansOfTypeTime OBJECT-TYPE
      SYNTAX      OCTET STRING
      MAX-ACCESS  read-only
      STATUS      current
      DESCRIPTION "This returns the average elapsed time in milliseconds required for getBeansOfType() "
      ::= { springApplicationContextRuntimeEntry 15  }
   
   
   springApplicationContextRuntimeSingletonBeansCreatedCount OBJECT-TYPE
      SYNTAX      Counter64
      MAX-ACCESS  read-only
      STATUS      current
      DESCRIPTION "The number of singleton beans created. "
      ::= { springApplicationContextRuntimeEntry 16  }
   
   
   springApplicationContextRuntimeRefreshCount OBJECT-TYPE
      SYNTAX      Counter64
      MAX-ACCESS  read-only
      STATUS      current
      DESCRIPTION "The number of refreshes performed "
      ::= { springApplicationContextRuntimeEntry 17  }
   
   
   springApplicationContextRuntimeAverageGetBeanTime OBJECT-TYPE
      SYNTAX      OCTET STRING
      MAX-ACCESS  read-only
      STATUS      current
      DESCRIPTION "This returns the average elapsed time in milliseconds required for getBean() "
      ::= { springApplicationContextRuntimeEntry 18  }
   
   
   springApplicationContextRuntimeCustomScopeNames OBJECT-TYPE
      SYNTAX      OCTET STRING
      MAX-ACCESS  read-only
      STATUS      current
      DESCRIPTION "The names of customer scopes that were registered. "
      ::= { springApplicationContextRuntimeEntry 19  }
   
   
   springApplicationContextRuntimeAverageRefreshTime OBJECT-TYPE
      SYNTAX      OCTET STRING
      MAX-ACCESS  read-only
      STATUS      current
      DESCRIPTION "This returns the average elapsed time in milliseconds required to perform a refresh "
      ::= { springApplicationContextRuntimeEntry 20  }
   
   
   springBeanDefinitionRuntimeTable OBJECT-TYPE
      SYNTAX      SEQUENCE OF SpringBeanDefinitionRuntimeEntry
      MAX-ACCESS  not-accessible
      STATUS      current
      DESCRIPTION " "
      ::= { wls 1595  }
      
   
   springBeanDefinitionRuntimeEntry OBJECT-TYPE
      SYNTAX      SpringBeanDefinitionRuntimeEntry
      MAX-ACCESS  not-accessible
      STATUS      current
      DESCRIPTION "Generated SNMP Table Entry."
      INDEX { springBeanDefinitionRuntimeIndex}
      ::= { springBeanDefinitionRuntimeTable 1 }
      
   SpringBeanDefinitionRuntimeEntry ::=
      SEQUENCE
      {
         springBeanDefinitionRuntimeIndex OCTET STRING,
         springBeanDefinitionRuntimeObjectName OCTET STRING,
         springBeanDefinitionRuntimeAliases OCTET STRING,
         springBeanDefinitionRuntimeParentId OCTET STRING,
         springBeanDefinitionRuntimeType OCTET STRING,
         springBeanDefinitionRuntimeBeanId OCTET STRING,
         springBeanDefinitionRuntimeApplicationContextDisplayName OCTET STRING,
         springBeanDefinitionRuntimeLazyInit OCTET STRING,
         springBeanDefinitionRuntimeResourceDescription OCTET STRING,
         springBeanDefinitionRuntimeAutowireCandidate OCTET STRING,
         springBeanDefinitionRuntimeDependencies OCTET STRING,
         springBeanDefinitionRuntimeBeanClassname OCTET STRING,
         springBeanDefinitionRuntimeSingleton OCTET STRING,
         springBeanDefinitionRuntimeName OCTET STRING,
         springBeanDefinitionRuntimeRole Integer32,
         springBeanDefinitionRuntimeAbstract OCTET STRING,
         springBeanDefinitionRuntimeScope OCTET STRING
      }
      
   
   springBeanDefinitionRuntimeIndex OBJECT-TYPE
      SYNTAX      OCTET STRING
      MAX-ACCESS  not-accessible
      STATUS      current
      DESCRIPTION "Index column"
      ::= { springBeanDefinitionRuntimeEntry 1  }
   
   
   springBeanDefinitionRuntimeObjectName OBJECT-TYPE
      SYNTAX      OCTET STRING
      MAX-ACCESS  read-only
      STATUS      current
      DESCRIPTION "ObjectName column"
      ::= { springBeanDefinitionRuntimeEntry 2  }
   
   
   springBeanDefinitionRuntimeAliases OBJECT-TYPE
      SYNTAX      OCTET STRING
      MAX-ACCESS  read-only
      STATUS      current
      DESCRIPTION "Get the aliases for this bean definition. Aliases are other names this bean definition is known by. "
      ::= { springBeanDefinitionRuntimeEntry 3  }
   
   
   springBeanDefinitionRuntimeParentId OBJECT-TYPE
      SYNTAX      OCTET STRING
      MAX-ACCESS  read-only
      STATUS      current
      DESCRIPTION "Name (Id) of parent bean definition. "
      ::= { springBeanDefinitionRuntimeEntry 4  }
   
   
   springBeanDefinitionRuntimeType OBJECT-TYPE
      SYNTAX      OCTET STRING
      MAX-ACCESS  read-only
      STATUS      current
      DESCRIPTION "Returns the type of the MBean. "
      ::= { springBeanDefinitionRuntimeEntry 5  }
   
   
   springBeanDefinitionRuntimeBeanId OBJECT-TYPE
      SYNTAX      OCTET STRING
      MAX-ACCESS  read-only
      STATUS      current
      DESCRIPTION "Name of the Spring bean. "
      ::= { springBeanDefinitionRuntimeEntry 6  }
   
   
   springBeanDefinitionRuntimeApplicationContextDisplayName OBJECT-TYPE
      SYNTAX      OCTET STRING
      MAX-ACCESS  read-only
      STATUS      current
      DESCRIPTION "Display name of the application context that this Spring bean is defined in. The application context is the Spring Inversion of Control (IoC) container. "
      ::= { springBeanDefinitionRuntimeEntry 7  }
   
   
   springBeanDefinitionRuntimeLazyInit OBJECT-TYPE
      SYNTAX      OCTET STRING
      MAX-ACCESS  read-only
      STATUS      current
      DESCRIPTION "Whether this bean should be lazily initialized. A lazy initialized bean is not created until it is needed. "
      ::= { springBeanDefinitionRuntimeEntry 8  }
   
   
   springBeanDefinitionRuntimeResourceDescription OBJECT-TYPE
      SYNTAX      OCTET STRING
      MAX-ACCESS  read-only
      STATUS      current
      DESCRIPTION "The name of the resource that this bean definition comes from. May be empty if the bean is implicitly registered. "
      ::= { springBeanDefinitionRuntimeEntry 9  }
   
   
   springBeanDefinitionRuntimeAutowireCandidate OBJECT-TYPE
      SYNTAX      OCTET STRING
      MAX-ACCESS  read-only
      STATUS      current
      DESCRIPTION "Whether this bean is a candidate to be autowired to other beans. "
      ::= { springBeanDefinitionRuntimeEntry 10  }
   
   
   springBeanDefinitionRuntimeDependencies OBJECT-TYPE
      SYNTAX      OCTET STRING
      MAX-ACCESS  read-only
      STATUS      current
      DESCRIPTION "Get the names (ids) of other bean definitions that this bean definition depends on. "
      ::= { springBeanDefinitionRuntimeEntry 11  }
   
   
   springBeanDefinitionRuntimeBeanClassname OBJECT-TYPE
      SYNTAX      OCTET STRING
      MAX-ACCESS  read-only
      STATUS      current
      DESCRIPTION "Class name of this Spring bean, as defined in the application context of the Spring application. "
      ::= { springBeanDefinitionRuntimeEntry 12  }
   
   
   springBeanDefinitionRuntimeSingleton OBJECT-TYPE
      SYNTAX      OCTET STRING
      MAX-ACCESS  read-only
      STATUS      current
      DESCRIPTION "Whether this is a singleton Spring bean. There is just one instance of a singleton bean per bean definition per application context. "
      ::= { springBeanDefinitionRuntimeEntry 13  }
   
   
   springBeanDefinitionRuntimeName OBJECT-TYPE
      SYNTAX      OCTET STRING
      MAX-ACCESS  read-only
      STATUS      current
      DESCRIPTION "The name of this configuration. WebLogic Server uses an MBean to implement and persist the configuration. "
      ::= { springBeanDefinitionRuntimeEntry 14  }
   
   
   springBeanDefinitionRuntimeRole OBJECT-TYPE
      SYNTAX      Integer32
      MAX-ACCESS  read-only
      STATUS      current
      DESCRIPTION "Role hint of this bean definition. The role is one of ROLE_APPLICATION, ROLE_SUPPORT, or ROLE_INFRASTRUCTURE. "
      ::= { springBeanDefinitionRuntimeEntry 15  }
   
   
   springBeanDefinitionRuntimeAbstract OBJECT-TYPE
      SYNTAX      OCTET STRING
      MAX-ACCESS  read-only
      STATUS      current
      DESCRIPTION "Whether this Spring bean is 'abstract'. An abstract bean definition can be used as a base for other definitions but cannot be instantiated. "
      ::= { springBeanDefinitionRuntimeEntry 16  }
   
   
   springBeanDefinitionRuntimeScope OBJECT-TYPE
      SYNTAX      OCTET STRING
      MAX-ACCESS  read-only
      STATUS      current
      DESCRIPTION "Scope of this bean. The scope is 'singleton', 'prototype', or other web specific or user defined values. "
      ::= { springBeanDefinitionRuntimeEntry 17  }
   
   
   springTransactionTemplateRuntimeTable OBJECT-TYPE
      SYNTAX      SEQUENCE OF SpringTransactionTemplateRuntimeEntry
      MAX-ACCESS  not-accessible
      STATUS      current
      DESCRIPTION "This MBean represents statistics gathered for org.springframework.transaction.support.TransactionTemplate "
      ::= { wls 1600  }
      
   
   springTransactionTemplateRuntimeEntry OBJECT-TYPE
      SYNTAX      SpringTransactionTemplateRuntimeEntry
      MAX-ACCESS  not-accessible
      STATUS      current
      DESCRIPTION "Generated SNMP Table Entry."
      INDEX { springTransactionTemplateRuntimeIndex}
      ::= { springTransactionTemplateRuntimeTable 1 }
      
   SpringTransactionTemplateRuntimeEntry ::=
      SEQUENCE
      {
         springTransactionTemplateRuntimeIndex OCTET STRING,
         springTransactionTemplateRuntimeObjectName OCTET STRING,
         springTransactionTemplateRuntimeExecuteCount Counter64,
         springTransactionTemplateRuntimeAverageExecuteTime OCTET STRING,
         springTransactionTemplateRuntimeType OCTET STRING,
         springTransactionTemplateRuntimeBeanId OCTET STRING,
         springTransactionTemplateRuntimeApplicationContextDisplayName OCTET STRING,
         springTransactionTemplateRuntimeName OCTET STRING,
         springTransactionTemplateRuntimeExecuteFailedCount Counter64
      }
      
   
   springTransactionTemplateRuntimeIndex OBJECT-TYPE
      SYNTAX      OCTET STRING
      MAX-ACCESS  not-accessible
      STATUS      current
      DESCRIPTION "Index column"
      ::= { springTransactionTemplateRuntimeEntry 1  }
   
   
   springTransactionTemplateRuntimeObjectName OBJECT-TYPE
      SYNTAX      OCTET STRING
      MAX-ACCESS  read-only
      STATUS      current
      DESCRIPTION "ObjectName column"
      ::= { springTransactionTemplateRuntimeEntry 2  }
   
   
   springTransactionTemplateRuntimeExecuteCount OBJECT-TYPE
      SYNTAX      Counter64
      MAX-ACCESS  read-only
      STATUS      current
      DESCRIPTION "This returns the number of time execute was called "
      ::= { springTransactionTemplateRuntimeEntry 3  }
   
   
   springTransactionTemplateRuntimeAverageExecuteTime OBJECT-TYPE
      SYNTAX      OCTET STRING
      MAX-ACCESS  read-only
      STATUS      current
      DESCRIPTION "This returns the average elapsed time in milliseconds required to execute "
      ::= { springTransactionTemplateRuntimeEntry 4  }
   
   
   springTransactionTemplateRuntimeType OBJECT-TYPE
      SYNTAX      OCTET STRING
      MAX-ACCESS  read-only
      STATUS      current
      DESCRIPTION "Returns the type of the MBean. "
      ::= { springTransactionTemplateRuntimeEntry 5  }
   
   
   springTransactionTemplateRuntimeBeanId OBJECT-TYPE
      SYNTAX      OCTET STRING
      MAX-ACCESS  read-only
      STATUS      current
      DESCRIPTION "Name of the Spring bean. "
      ::= { springTransactionTemplateRuntimeEntry 6  }
   
   
   springTransactionTemplateRuntimeApplicationContextDisplayName OBJECT-TYPE
      SYNTAX      OCTET STRING
      MAX-ACCESS  read-only
      STATUS      current
      DESCRIPTION "The display name of the Application Context that this bean is from "
      ::= { springTransactionTemplateRuntimeEntry 7  }
   
   
   springTransactionTemplateRuntimeName OBJECT-TYPE
      SYNTAX      OCTET STRING
      MAX-ACCESS  read-only
      STATUS      current
      DESCRIPTION "The name of this configuration. WebLogic Server uses an MBean to implement and persist the configuration. "
      ::= { springTransactionTemplateRuntimeEntry 8  }
   
   
   springTransactionTemplateRuntimeExecuteFailedCount OBJECT-TYPE
      SYNTAX      Counter64
      MAX-ACCESS  read-only
      STATUS      current
      DESCRIPTION "The number of executes that failed "
      ::= { springTransactionTemplateRuntimeEntry 9  }
   
   
   springViewResolverRuntimeTable OBJECT-TYPE
      SYNTAX      SEQUENCE OF SpringViewResolverRuntimeEntry
      MAX-ACCESS  not-accessible
      STATUS      current
      DESCRIPTION "This MBean represents statistics for org.springframework.web.servlet.ViewResolver "
      ::= { wls 1605  }
      
   
   springViewResolverRuntimeEntry OBJECT-TYPE
      SYNTAX      SpringViewResolverRuntimeEntry
      MAX-ACCESS  not-accessible
      STATUS      current
      DESCRIPTION "Generated SNMP Table Entry."
      INDEX { springViewResolverRuntimeIndex}
      ::= { springViewResolverRuntimeTable 1 }
      
   SpringViewResolverRuntimeEntry ::=
      SEQUENCE
      {
         springViewResolverRuntimeIndex OCTET STRING,
         springViewResolverRuntimeObjectName OCTET STRING,
         springViewResolverRuntimeType OCTET STRING,
         springViewResolverRuntimeBeanId OCTET STRING,
         springViewResolverRuntimeApplicationContextDisplayName OCTET STRING,
         springViewResolverRuntimeResolveViewNameCount Counter64,
         springViewResolverRuntimeName OCTET STRING,
         springViewResolverRuntimeAverageResolveViewNameTime OCTET STRING,
         springViewResolverRuntimeResolveViewNameFailedCount Counter64
      }
      
   
   springViewResolverRuntimeIndex OBJECT-TYPE
      SYNTAX      OCTET STRING
      MAX-ACCESS  not-accessible
      STATUS      current
      DESCRIPTION "Index column"
      ::= { springViewResolverRuntimeEntry 1  }
   
   
   springViewResolverRuntimeObjectName OBJECT-TYPE
      SYNTAX      OCTET STRING
      MAX-ACCESS  read-only
      STATUS      current
      DESCRIPTION "ObjectName column"
      ::= { springViewResolverRuntimeEntry 2  }
   
   
   springViewResolverRuntimeType OBJECT-TYPE
      SYNTAX      OCTET STRING
      MAX-ACCESS  read-only
      STATUS      current
      DESCRIPTION "Returns the type of the MBean. "
      ::= { springViewResolverRuntimeEntry 3  }
   
   
   springViewResolverRuntimeBeanId OBJECT-TYPE
      SYNTAX      OCTET STRING
      MAX-ACCESS  read-only
      STATUS      current
      DESCRIPTION "Name of the Spring bean. "
      ::= { springViewResolverRuntimeEntry 4  }
   
   
   springViewResolverRuntimeApplicationContextDisplayName OBJECT-TYPE
      SYNTAX      OCTET STRING
      MAX-ACCESS  read-only
      STATUS      current
      DESCRIPTION "The display name of the Application Context that this bean is from "
      ::= { springViewResolverRuntimeEntry 5  }
   
   
   springViewResolverRuntimeResolveViewNameCount OBJECT-TYPE
      SYNTAX      Counter64
      MAX-ACCESS  read-only
      STATUS      current
      DESCRIPTION "The number of times resolveViewName was called "
      ::= { springViewResolverRuntimeEntry 6  }
   
   
   springViewResolverRuntimeName OBJECT-TYPE
      SYNTAX      OCTET STRING
      MAX-ACCESS  read-only
      STATUS      current
      DESCRIPTION "The name of this configuration. WebLogic Server uses an MBean to implement and persist the configuration. "
      ::= { springViewResolverRuntimeEntry 7  }
   
   
   springViewResolverRuntimeAverageResolveViewNameTime OBJECT-TYPE
      SYNTAX      OCTET STRING
      MAX-ACCESS  read-only
      STATUS      current
      DESCRIPTION "This returns the average elapsed time in milliseconds required to resolve a view name "
      ::= { springViewResolverRuntimeEntry 8  }
   
   
   springViewResolverRuntimeResolveViewNameFailedCount OBJECT-TYPE
      SYNTAX      Counter64
      MAX-ACCESS  read-only
      STATUS      current
      DESCRIPTION "The number of resolveViewName calls that failed "
      ::= { springViewResolverRuntimeEntry 9  }
   
   
   springViewRuntimeTable OBJECT-TYPE
      SYNTAX      SEQUENCE OF SpringViewRuntimeEntry
      MAX-ACCESS  not-accessible
      STATUS      current
      DESCRIPTION "This MBean represents statistics for org.springframework.web.servlet.view.AbstractView "
      ::= { wls 1610  }
      
   
   springViewRuntimeEntry OBJECT-TYPE
      SYNTAX      SpringViewRuntimeEntry
      MAX-ACCESS  not-accessible
      STATUS      current
      DESCRIPTION "Generated SNMP Table Entry."
      INDEX { springViewRuntimeIndex}
      ::= { springViewRuntimeTable 1 }
      
   SpringViewRuntimeEntry ::=
      SEQUENCE
      {
         springViewRuntimeIndex OCTET STRING,
         springViewRuntimeObjectName OCTET STRING,
         springViewRuntimeType OCTET STRING,
         springViewRuntimeBeanId OCTET STRING,
         springViewRuntimeApplicationContextDisplayName OCTET STRING,
         springViewRuntimeName OCTET STRING,
         springViewRuntimeRenderFailedCount Counter64,
         springViewRuntimeRenderCount Counter64,
         springViewRuntimeAverageRenderTime OCTET STRING
      }
      
   
   springViewRuntimeIndex OBJECT-TYPE
      SYNTAX      OCTET STRING
      MAX-ACCESS  not-accessible
      STATUS      current
      DESCRIPTION "Index column"
      ::= { springViewRuntimeEntry 1  }
   
   
   springViewRuntimeObjectName OBJECT-TYPE
      SYNTAX      OCTET STRING
      MAX-ACCESS  read-only
      STATUS      current
      DESCRIPTION "ObjectName column"
      ::= { springViewRuntimeEntry 2  }
   
   
   springViewRuntimeType OBJECT-TYPE
      SYNTAX      OCTET STRING
      MAX-ACCESS  read-only
      STATUS      current
      DESCRIPTION "Returns the type of the MBean. "
      ::= { springViewRuntimeEntry 3  }
   
   
   springViewRuntimeBeanId OBJECT-TYPE
      SYNTAX      OCTET STRING
      MAX-ACCESS  read-only
      STATUS      current
      DESCRIPTION "Name of the Spring bean. "
      ::= { springViewRuntimeEntry 4  }
   
   
   springViewRuntimeApplicationContextDisplayName OBJECT-TYPE
      SYNTAX      OCTET STRING
      MAX-ACCESS  read-only
      STATUS      current
      DESCRIPTION "The display name of the Application Context that this bean is from "
      ::= { springViewRuntimeEntry 5  }
   
   
   springViewRuntimeName OBJECT-TYPE
      SYNTAX      OCTET STRING
      MAX-ACCESS  read-only
      STATUS      current
      DESCRIPTION "The name of this configuration. WebLogic Server uses an MBean to implement and persist the configuration. "
      ::= { springViewRuntimeEntry 6  }
   
   
   springViewRuntimeRenderFailedCount OBJECT-TYPE
      SYNTAX      Counter64
      MAX-ACCESS  read-only
      STATUS      current
      DESCRIPTION "The number of render calls that failed "
      ::= { springViewRuntimeEntry 7  }
   
   
   springViewRuntimeRenderCount OBJECT-TYPE
      SYNTAX      Counter64
      MAX-ACCESS  read-only
      STATUS      current
      DESCRIPTION "The number of times render was called "
      ::= { springViewRuntimeEntry 8  }
   
   
   springViewRuntimeAverageRenderTime OBJECT-TYPE
      SYNTAX      OCTET STRING
      MAX-ACCESS  read-only
      STATUS      current
      DESCRIPTION "This returns the average elapsed time in milliseconds required to render "
      ::= { springViewRuntimeEntry 9  }
   
   
   coherenceClusterSystemResourceTable OBJECT-TYPE
      SYNTAX      SEQUENCE OF CoherenceClusterSystemResourceEntry
      MAX-ACCESS  not-accessible
      STATUS      current
      DESCRIPTION "This bean defines a system-level Coherence cluster resource. It links to a separate descriptor that specifies the definition. "
      ::= { wls 1615  }
      
   
   coherenceClusterSystemResourceEntry OBJECT-TYPE
      SYNTAX      CoherenceClusterSystemResourceEntry
      MAX-ACCESS  not-accessible
      STATUS      current
      DESCRIPTION "Generated SNMP Table Entry."
      INDEX { coherenceClusterSystemResourceIndex}
      ::= { coherenceClusterSystemResourceTable 1 }
      
   CoherenceClusterSystemResourceEntry ::=
      SEQUENCE
      {
         coherenceClusterSystemResourceIndex OCTET STRING,
         coherenceClusterSystemResourceObjectName OCTET STRING,
         coherenceClusterSystemResourceType OCTET STRING,
         coherenceClusterSystemResourceCompatibilityName OCTET STRING,
         coherenceClusterSystemResourceModuleType OCTET STRING,
         coherenceClusterSystemResourceSourcePath OCTET STRING,
         coherenceClusterSystemResourceDescriptorFileName OCTET STRING,
         coherenceClusterSystemResourceName OCTET STRING,
         coherenceClusterSystemResourceCustomClusterConfigurationFileName OCTET STRING,
         coherenceClusterSystemResourceDeploymentPrincipalName OCTET STRING,
         coherenceClusterSystemResourceUsingCustomClusterConfigurationFile OCTET STRING,
         coherenceClusterSystemResourceDeploymentOrder Integer32,
         coherenceClusterSystemResourceReportGroupFile OCTET STRING,
         coherenceClusterSystemResourceTags OCTET STRING,
         coherenceClusterSystemResourceClusterHosts OCTET STRING,
         coherenceClusterSystemResourcePersistenceSnapshotDirectory OCTET STRING,
         coherenceClusterSystemResourceFederationRemoteClusterListenPort INTEGER,
         coherenceClusterSystemResourceFederationRemoteClusterName OCTET STRING,
         coherenceClusterSystemResourcePersistenceActiveDirectory OCTET STRING,
         coherenceClusterSystemResourceCustomConfigFileLastUpdatedTime Counter64,
         coherenceClusterSystemResourcePersistenceTrashDirectory OCTET STRING,
         coherenceClusterSystemResourcePersistenceDefaultMode OCTET STRING,
         coherenceClusterSystemResourceFederationRemoteParticipantHosts OCTET STRING,
         coherenceClusterSystemResourceFederationTopology OCTET STRING
      }
      
   
   coherenceClusterSystemResourceIndex OBJECT-TYPE
      SYNTAX      OCTET STRING
      MAX-ACCESS  not-accessible
      STATUS      current
      DESCRIPTION "Index column"
      ::= { coherenceClusterSystemResourceEntry 1  }
   
   
   coherenceClusterSystemResourceObjectName OBJECT-TYPE
      SYNTAX      OCTET STRING
      MAX-ACCESS  read-only
      STATUS      current
      DESCRIPTION "ObjectName column"
      ::= { coherenceClusterSystemResourceEntry 2  }
   
   
   coherenceClusterSystemResourceType OBJECT-TYPE
      SYNTAX      OCTET STRING
      MAX-ACCESS  read-only
      STATUS      current
      DESCRIPTION "Returns the type of the MBean. "
      ::= { coherenceClusterSystemResourceEntry 3  }
   
   
   coherenceClusterSystemResourceCompatibilityName OBJECT-TYPE
      SYNTAX      OCTET STRING
      MAX-ACCESS  read-only
      STATUS      current
      DESCRIPTION " This is only set for beans created as a result of conversion from an 8.1 application configured using ApplicationMBean and ComponentMBean.  Standalone modules in 8.1 have both an ApplicationMBean name and ComponentMBean name. This attribute stores the name of the latter, to be used when the server creates the transient ComponentMBean for backward compatibility. "
      ::= { coherenceClusterSystemResourceEntry 4  }
   
   
   coherenceClusterSystemResourceModuleType OBJECT-TYPE
      SYNTAX      OCTET STRING
      MAX-ACCESS  read-only
      STATUS      current
      DESCRIPTION "The values match those defined by jsr88. This attribute may move to another MBean. "
      ::= { coherenceClusterSystemResourceEntry 5  }
   
   
   coherenceClusterSystemResourceSourcePath OBJECT-TYPE
      SYNTAX      OCTET STRING
      MAX-ACCESS  read-only
      STATUS      current
      DESCRIPTION " "
      ::= { coherenceClusterSystemResourceEntry 6  }
   
   
   coherenceClusterSystemResourceDescriptorFileName OBJECT-TYPE
      SYNTAX      OCTET STRING
      MAX-ACCESS  read-only
      STATUS      current
      DESCRIPTION "The name of the file that contains the module configuration. By default the file resides in the DOMAIN_DIR/config/coherence/bean_name directory.  The module file derives its name from the bean name using the following pattern:  &lt;beanName&gt;.xml Note that this is a read-only property that can only be set when the bean is created. "
      ::= { coherenceClusterSystemResourceEntry 7  }
   
   
   coherenceClusterSystemResourceName OBJECT-TYPE
      SYNTAX      OCTET STRING
      MAX-ACCESS  read-only
      STATUS      current
      DESCRIPTION "The user-specified name of this MBean instance.  This name is included as one of the key properties in the MBean's javax.management.ObjectName:  Name=user-specified-name "
      ::= { coherenceClusterSystemResourceEntry 8  }
   
   
   coherenceClusterSystemResourceCustomClusterConfigurationFileName OBJECT-TYPE
      SYNTAX      OCTET STRING
      MAX-ACCESS  read-only
      STATUS      current
      DESCRIPTION " The external custom Coherence cluster configuration file.  "
      ::= { coherenceClusterSystemResourceEntry 9  }
   
   
   coherenceClusterSystemResourceDeploymentPrincipalName OBJECT-TYPE
      SYNTAX      OCTET STRING
      MAX-ACCESS  read-only
      STATUS      current
      DESCRIPTION "A string value that indicates the principal that should be used when deploying the file or archive during startup and shutdown. This principal will be used to set the current subject when calling out into application code for interfaces such as ApplicationLifecycleListener. If no principal name is specified, then the anonymous principal will be used. "
      ::= { coherenceClusterSystemResourceEntry 10  }
   
   
   coherenceClusterSystemResourceUsingCustomClusterConfigurationFile OBJECT-TYPE
      SYNTAX      OCTET STRING
      MAX-ACCESS  read-only
      STATUS      current
      DESCRIPTION ""
      ::= { coherenceClusterSystemResourceEntry 11  }
   
   
   coherenceClusterSystemResourceDeploymentOrder OBJECT-TYPE
      SYNTAX      Integer32
      MAX-ACCESS  read-only
      STATUS      current
      DESCRIPTION "An integer value that indicates when this unit is deployed, relative to other deployable units on a server, during startup.  Units with lower values are deployed before those with higher values. "
      ::= { coherenceClusterSystemResourceEntry 12  }
   
   
   coherenceClusterSystemResourceReportGroupFile OBJECT-TYPE
      SYNTAX      OCTET STRING
      MAX-ACCESS  read-only
      STATUS      current
      DESCRIPTION "Get the report group file representing the superset of runtime metrics to be collected for this cluster. "
      ::= { coherenceClusterSystemResourceEntry 13  }
   
   
   coherenceClusterSystemResourceTags OBJECT-TYPE
      SYNTAX      OCTET STRING
      MAX-ACCESS  read-only
      STATUS      current
      DESCRIPTION "Return all tags on this Configuration MBean "
      ::= { coherenceClusterSystemResourceEntry 14  }
   
   
   coherenceClusterSystemResourceClusterHosts OBJECT-TYPE
      SYNTAX      OCTET STRING
      MAX-ACCESS  read-only
      STATUS      current
      DESCRIPTION "The list of hostnames of the managed servers belonging to this Coherence cluster. "
      ::= { coherenceClusterSystemResourceEntry 15  }
   
   
   coherenceClusterSystemResourcePersistenceSnapshotDirectory OBJECT-TYPE
      SYNTAX      OCTET STRING
      MAX-ACCESS  read-only
      STATUS      current
      DESCRIPTION "The snapshot directory for the default persistence environment. If no value is specified, the directory which will be used is coherence/snapshots sub-directory under Domain Home directory.  "
      ::= { coherenceClusterSystemResourceEntry 16  }
   
   
   coherenceClusterSystemResourceFederationRemoteClusterListenPort OBJECT-TYPE
      SYNTAX      INTEGER
      MAX-ACCESS  read-only
      STATUS      current
      DESCRIPTION "The Coherence Cluster Listen Port of the remote participant.  "
      ::= { coherenceClusterSystemResourceEntry 17  }
   
   
   coherenceClusterSystemResourceFederationRemoteClusterName OBJECT-TYPE
      SYNTAX      OCTET STRING
      MAX-ACCESS  read-only
      STATUS      current
      DESCRIPTION "The Coherence Cluster Name of the remote participant cluster.  "
      ::= { coherenceClusterSystemResourceEntry 18  }
   
   
   coherenceClusterSystemResourcePersistenceActiveDirectory OBJECT-TYPE
      SYNTAX      OCTET STRING
      MAX-ACCESS  read-only
      STATUS      current
      DESCRIPTION "The active directory for the default persistence environment. If no value is specified, the directory which will be used is the coherence/active sub-directory under Domain Home directory.  "
      ::= { coherenceClusterSystemResourceEntry 19  }
   
   
   coherenceClusterSystemResourceCustomConfigFileLastUpdatedTime OBJECT-TYPE
      SYNTAX      Counter64
      MAX-ACCESS  read-only
      STATUS      current
      DESCRIPTION "The time when the custom configuration file used by the cluster was last updated "
      ::= { coherenceClusterSystemResourceEntry 20  }
   
   
   coherenceClusterSystemResourcePersistenceTrashDirectory OBJECT-TYPE
      SYNTAX      OCTET STRING
      MAX-ACCESS  read-only
      STATUS      current
      DESCRIPTION "The trash directory for the default persistence environment. If no value is specified, the directory which will be used is coherence/trash sub-directory under Domain Home directory.  "
      ::= { coherenceClusterSystemResourceEntry 21  }
   
   
   coherenceClusterSystemResourcePersistenceDefaultMode OBJECT-TYPE
      SYNTAX      OCTET STRING
      MAX-ACCESS  read-only
      STATUS      current
      DESCRIPTION "The default persistence mode.  "
      ::= { coherenceClusterSystemResourceEntry 22  }
   
   
   coherenceClusterSystemResourceFederationRemoteParticipantHosts OBJECT-TYPE
      SYNTAX      OCTET STRING
      MAX-ACCESS  read-only
      STATUS      current
      DESCRIPTION "The list of remote participant hosts, who will be added as participants in the federation topology.  "
      ::= { coherenceClusterSystemResourceEntry 23  }
   
   
   coherenceClusterSystemResourceFederationTopology OBJECT-TYPE
      SYNTAX      OCTET STRING
      MAX-ACCESS  read-only
      STATUS      current
      DESCRIPTION "The federation topology.  "
      ::= { coherenceClusterSystemResourceEntry 24  }
   
   
   jPATable OBJECT-TYPE
      SYNTAX      SEQUENCE OF JPAEntry
      MAX-ACCESS  not-accessible
      STATUS      current
      DESCRIPTION "This interface provides access to the JPA configuration attributes.  The methods defined herein are applicable for JPA configuration at the domain level. "
      ::= { wls 1620  }
      
   
   jPAEntry OBJECT-TYPE
      SYNTAX      JPAEntry
      MAX-ACCESS  not-accessible
      STATUS      current
      DESCRIPTION "Generated SNMP Table Entry."
      INDEX { jPAIndex}
      ::= { jPATable 1 }
      
   JPAEntry ::=
      SEQUENCE
      {
         jPAIndex             OCTET STRING,
         jPAObjectName        OCTET STRING,
         jPAType              OCTET STRING,
         jPADefaultJPAProvider OCTET STRING,
         jPAName              OCTET STRING,
         jPATags              OCTET STRING
      }
      
   
   jPAIndex OBJECT-TYPE
      SYNTAX      OCTET STRING
      MAX-ACCESS  not-accessible
      STATUS      current
      DESCRIPTION "Index column"
      ::= { jPAEntry 1  }
   
   
   jPAObjectName OBJECT-TYPE
      SYNTAX      OCTET STRING
      MAX-ACCESS  read-only
      STATUS      current
      DESCRIPTION "ObjectName column"
      ::= { jPAEntry 2  }
   
   
   jPAType OBJECT-TYPE
      SYNTAX      OCTET STRING
      MAX-ACCESS  read-only
      STATUS      current
      DESCRIPTION "Returns the type of the MBean. "
      ::= { jPAEntry 3  }
   
   
   jPADefaultJPAProvider OBJECT-TYPE
      SYNTAX      OCTET STRING
      MAX-ACCESS  read-only
      STATUS      current
      DESCRIPTION "The configured default JPA provider for the domain. "
      ::= { jPAEntry 4  }
   
   
   jPAName OBJECT-TYPE
      SYNTAX      OCTET STRING
      MAX-ACCESS  read-only
      STATUS      current
      DESCRIPTION "The user-specified name of this MBean instance.  This name is included as one of the key properties in the MBean's javax.management.ObjectName:  Name=user-specified-name "
      ::= { jPAEntry 5  }
   
   
   jPATags OBJECT-TYPE
      SYNTAX      OCTET STRING
      MAX-ACCESS  read-only
      STATUS      current
      DESCRIPTION "Return all tags on this Configuration MBean "
      ::= { jPAEntry 6  }
   
   
   webServiceBufferingTable OBJECT-TYPE
      SYNTAX      SEQUENCE OF WebServiceBufferingEntry
      MAX-ACCESS  not-accessible
      STATUS      current
      DESCRIPTION "Represents buffering configuration for web services. "
      ::= { wls 1625  }
      
   
   webServiceBufferingEntry OBJECT-TYPE
      SYNTAX      WebServiceBufferingEntry
      MAX-ACCESS  not-accessible
      STATUS      current
      DESCRIPTION "Generated SNMP Table Entry."
      INDEX { webServiceBufferingIndex}
      ::= { webServiceBufferingTable 1 }
      
   WebServiceBufferingEntry ::=
      SEQUENCE
      {
         webServiceBufferingIndex OCTET STRING,
         webServiceBufferingObjectName OCTET STRING,
         webServiceBufferingType OCTET STRING,
         webServiceBufferingRetryDelay OCTET STRING,
         webServiceBufferingName OCTET STRING,
         webServiceBufferingRetryCount Integer32,
         webServiceBufferingTags OCTET STRING
      }
      
   
   webServiceBufferingIndex OBJECT-TYPE
      SYNTAX      OCTET STRING
      MAX-ACCESS  not-accessible
      STATUS      current
      DESCRIPTION "Index column"
      ::= { webServiceBufferingEntry 1  }
   
   
   webServiceBufferingObjectName OBJECT-TYPE
      SYNTAX      OCTET STRING
      MAX-ACCESS  read-only
      STATUS      current
      DESCRIPTION "ObjectName column"
      ::= { webServiceBufferingEntry 2  }
   
   
   webServiceBufferingType OBJECT-TYPE
      SYNTAX      OCTET STRING
      MAX-ACCESS  read-only
      STATUS      current
      DESCRIPTION "Returns the type of the MBean. "
      ::= { webServiceBufferingEntry 3  }
   
   
   webServiceBufferingRetryDelay OBJECT-TYPE
      SYNTAX      OCTET STRING
      MAX-ACCESS  read-only
      STATUS      current
      DESCRIPTION "The amount time between retries of a buffered request and response. Note, this value is only applicable when RetryCount > 0. String value in 'Duration' format. Defaults to 'P0DT30S' (30 seconds). "
      ::= { webServiceBufferingEntry 4  }
   
   
   webServiceBufferingName OBJECT-TYPE
      SYNTAX      OCTET STRING
      MAX-ACCESS  read-only
      STATUS      current
      DESCRIPTION "The user-specified name of this MBean instance.  This name is included as one of the key properties in the MBean's javax.management.ObjectName:  Name=user-specified-name "
      ::= { webServiceBufferingEntry 5  }
   
   
   webServiceBufferingRetryCount OBJECT-TYPE
      SYNTAX      Integer32
      MAX-ACCESS  read-only
      STATUS      current
      DESCRIPTION "The number of times a buffered request or response can be retried before it is abandoned (and moved to any error queue defined for the buffer queue) "
      ::= { webServiceBufferingEntry 6  }
   
   
   webServiceBufferingTags OBJECT-TYPE
      SYNTAX      OCTET STRING
      MAX-ACCESS  read-only
      STATUS      current
      DESCRIPTION "Return all tags on this Configuration MBean "
      ::= { webServiceBufferingEntry 7  }
   
   
   webServiceLogicalStoreTable OBJECT-TYPE
      SYNTAX      SEQUENCE OF WebServiceLogicalStoreEntry
      MAX-ACCESS  not-accessible
      STATUS      current
      DESCRIPTION "Represents a logical store for web services. "
      ::= { wls 1630  }
      
   
   webServiceLogicalStoreEntry OBJECT-TYPE
      SYNTAX      WebServiceLogicalStoreEntry
      MAX-ACCESS  not-accessible
      STATUS      current
      DESCRIPTION "Generated SNMP Table Entry."
      INDEX { webServiceLogicalStoreIndex}
      ::= { webServiceLogicalStoreTable 1 }
      
   WebServiceLogicalStoreEntry ::=
      SEQUENCE
      {
         webServiceLogicalStoreIndex OCTET STRING,
         webServiceLogicalStoreObjectName OCTET STRING,
         webServiceLogicalStoreType OCTET STRING,
         webServiceLogicalStoreCleanerInterval OCTET STRING,
         webServiceLogicalStorePhysicalStoreName OCTET STRING,
         webServiceLogicalStoreResponseBufferingQueueJndiName OCTET STRING,
         webServiceLogicalStoreName OCTET STRING,
         webServiceLogicalStoreDefaultMaximumObjectLifetime OCTET STRING,
         webServiceLogicalStoreRequestBufferingQueueJndiName OCTET STRING,
         webServiceLogicalStorePersistenceStrategy OCTET STRING,
         webServiceLogicalStoreTags OCTET STRING
      }
      
   
   webServiceLogicalStoreIndex OBJECT-TYPE
      SYNTAX      OCTET STRING
      MAX-ACCESS  not-accessible
      STATUS      current
      DESCRIPTION "Index column"
      ::= { webServiceLogicalStoreEntry 1  }
   
   
   webServiceLogicalStoreObjectName OBJECT-TYPE
      SYNTAX      OCTET STRING
      MAX-ACCESS  read-only
      STATUS      current
      DESCRIPTION "ObjectName column"
      ::= { webServiceLogicalStoreEntry 2  }
   
   
   webServiceLogicalStoreType OBJECT-TYPE
      SYNTAX      OCTET STRING
      MAX-ACCESS  read-only
      STATUS      current
      DESCRIPTION "Returns the type of the MBean. "
      ::= { webServiceLogicalStoreEntry 3  }
   
   
   webServiceLogicalStoreCleanerInterval OBJECT-TYPE
      SYNTAX      OCTET STRING
      MAX-ACCESS  read-only
      STATUS      current
      DESCRIPTION "Get the interval at which the persistent store will be cleaned "
      ::= { webServiceLogicalStoreEntry 4  }
   
   
   webServiceLogicalStorePhysicalStoreName OBJECT-TYPE
      SYNTAX      OCTET STRING
      MAX-ACCESS  read-only
      STATUS      current
      DESCRIPTION "Get the name of the physical store to be used by this logical store. This property is recommended for use only when running off server or in other cases where a buffering queue JNDI name cannot be set via setBufferingQueueJndiName. If a buffering queue JNDI name is set to a non-null/non-empty value, this property is ignored. Defaults to '' to indicate the default WLS file store should be used.  This property is ignored if persistence strategy is IN_MEMORY. "
      ::= { webServiceLogicalStoreEntry 5  }
   
   
   webServiceLogicalStoreResponseBufferingQueueJndiName OBJECT-TYPE
      SYNTAX      OCTET STRING
      MAX-ACCESS  read-only
      STATUS      current
      DESCRIPTION "Get the JNDI name of the response buffering queue that web services should use. If this is null, the request buffering queue is used. "
      ::= { webServiceLogicalStoreEntry 6  }
   
   
   webServiceLogicalStoreName OBJECT-TYPE
      SYNTAX      OCTET STRING
      MAX-ACCESS  read-only
      STATUS      current
      DESCRIPTION "Get the name of this logical store. "
      ::= { webServiceLogicalStoreEntry 7  }
   
   
   webServiceLogicalStoreDefaultMaximumObjectLifetime OBJECT-TYPE
      SYNTAX      OCTET STRING
      MAX-ACCESS  read-only
      STATUS      current
      DESCRIPTION "Get the default max time an object can remain in the store. This can be overridden on individual objects placed in the store (internally, but not via this API). "
      ::= { webServiceLogicalStoreEntry 8  }
   
   
   webServiceLogicalStoreRequestBufferingQueueJndiName OBJECT-TYPE
      SYNTAX      OCTET STRING
      MAX-ACCESS  read-only
      STATUS      current
      DESCRIPTION "Get the JNDI name of the buffering queue that web services should use. (Both for buffering and to  find the physical store for this logical store). Defaults to '' to indicate the PhysicalStoreName property should be used.  This property is ignored if persistence strategy is IN_MEMORY. "
      ::= { webServiceLogicalStoreEntry 9  }
   
   
   webServiceLogicalStorePersistenceStrategy OBJECT-TYPE
      SYNTAX      OCTET STRING
      MAX-ACCESS  read-only
      STATUS      current
      DESCRIPTION "Get the persistence strategy in use by this logical store. Any physical store configured for use with this logical store should support this strategy. "
      ::= { webServiceLogicalStoreEntry 10  }
   
   
   webServiceLogicalStoreTags OBJECT-TYPE
      SYNTAX      OCTET STRING
      MAX-ACCESS  read-only
      STATUS      current
      DESCRIPTION "Return all tags on this Configuration MBean "
      ::= { webServiceLogicalStoreEntry 11  }
   
   
   webServicePersistenceTable OBJECT-TYPE
      SYNTAX      SEQUENCE OF WebServicePersistenceEntry
      MAX-ACCESS  not-accessible
      STATUS      current
      DESCRIPTION "Represents persistence configuration for web services. "
      ::= { wls 1635  }
      
   
   webServicePersistenceEntry OBJECT-TYPE
      SYNTAX      WebServicePersistenceEntry
      MAX-ACCESS  not-accessible
      STATUS      current
      DESCRIPTION "Generated SNMP Table Entry."
      INDEX { webServicePersistenceIndex}
      ::= { webServicePersistenceTable 1 }
      
   WebServicePersistenceEntry ::=
      SEQUENCE
      {
         webServicePersistenceIndex OCTET STRING,
         webServicePersistenceObjectName OCTET STRING,
         webServicePersistenceType OCTET STRING,
         webServicePersistenceDefaultLogicalStoreName OCTET STRING,
         webServicePersistenceName OCTET STRING,
         webServicePersistenceTags OCTET STRING
      }
      
   
   webServicePersistenceIndex OBJECT-TYPE
      SYNTAX      OCTET STRING
      MAX-ACCESS  not-accessible
      STATUS      current
      DESCRIPTION "Index column"
      ::= { webServicePersistenceEntry 1  }
   
   
   webServicePersistenceObjectName OBJECT-TYPE
      SYNTAX      OCTET STRING
      MAX-ACCESS  read-only
      STATUS      current
      DESCRIPTION "ObjectName column"
      ::= { webServicePersistenceEntry 2  }
   
   
   webServicePersistenceType OBJECT-TYPE
      SYNTAX      OCTET STRING
      MAX-ACCESS  read-only
      STATUS      current
      DESCRIPTION "Returns the type of the MBean. "
      ::= { webServicePersistenceEntry 3  }
   
   
   webServicePersistenceDefaultLogicalStoreName OBJECT-TYPE
      SYNTAX      OCTET STRING
      MAX-ACCESS  read-only
      STATUS      current
      DESCRIPTION "Get the name of the logical store to use, by default, for all web services persistent state in this server. "
      ::= { webServicePersistenceEntry 4  }
   
   
   webServicePersistenceName OBJECT-TYPE
      SYNTAX      OCTET STRING
      MAX-ACCESS  read-only
      STATUS      current
      DESCRIPTION "The user-specified name of this MBean instance.  This name is included as one of the key properties in the MBean's javax.management.ObjectName:  Name=user-specified-name "
      ::= { webServicePersistenceEntry 5  }
   
   
   webServicePersistenceTags OBJECT-TYPE
      SYNTAX      OCTET STRING
      MAX-ACCESS  read-only
      STATUS      current
      DESCRIPTION "Return all tags on this Configuration MBean "
      ::= { webServicePersistenceEntry 6  }
   
   
   webServicePhysicalStoreTable OBJECT-TYPE
      SYNTAX      SEQUENCE OF WebServicePhysicalStoreEntry
      MAX-ACCESS  not-accessible
      STATUS      current
      DESCRIPTION "Represents a physical store for web services. Used only for non-WLS containers (e.g. other app-server or standalone client). "
      ::= { wls 1640  }
      
   
   webServicePhysicalStoreEntry OBJECT-TYPE
      SYNTAX      WebServicePhysicalStoreEntry
      MAX-ACCESS  not-accessible
      STATUS      current
      DESCRIPTION "Generated SNMP Table Entry."
      INDEX { webServicePhysicalStoreIndex}
      ::= { webServicePhysicalStoreTable 1 }
      
   WebServicePhysicalStoreEntry ::=
      SEQUENCE
      {
         webServicePhysicalStoreIndex OCTET STRING,
         webServicePhysicalStoreObjectName OCTET STRING,
         webServicePhysicalStoreType OCTET STRING,
         webServicePhysicalStoreLocation OCTET STRING,
         webServicePhysicalStoreName OCTET STRING,
         webServicePhysicalStoreStoreType OCTET STRING,
         webServicePhysicalStoreSynchronousWritePolicy OCTET STRING,
         webServicePhysicalStoreTags OCTET STRING
      }
      
   
   webServicePhysicalStoreIndex OBJECT-TYPE
      SYNTAX      OCTET STRING
      MAX-ACCESS  not-accessible
      STATUS      current
      DESCRIPTION "Index column"
      ::= { webServicePhysicalStoreEntry 1  }
   
   
   webServicePhysicalStoreObjectName OBJECT-TYPE
      SYNTAX      OCTET STRING
      MAX-ACCESS  read-only
      STATUS      current
      DESCRIPTION "ObjectName column"
      ::= { webServicePhysicalStoreEntry 2  }
   
   
   webServicePhysicalStoreType OBJECT-TYPE
      SYNTAX      OCTET STRING
      MAX-ACCESS  read-only
      STATUS      current
      DESCRIPTION "Returns the type of the MBean. "
      ::= { webServicePhysicalStoreEntry 3  }
   
   
   webServicePhysicalStoreLocation OBJECT-TYPE
      SYNTAX      OCTET STRING
      MAX-ACCESS  read-only
      STATUS      current
      DESCRIPTION "For file stores, specifies the directory that will hold all files related to the store. The actual file names are controlled internally by the file store implementation. For other types of stores, this location may be a URL or URI, or other description string. "
      ::= { webServicePhysicalStoreEntry 4  }
   
   
   webServicePhysicalStoreName OBJECT-TYPE
      SYNTAX      OCTET STRING
      MAX-ACCESS  read-only
      STATUS      current
      DESCRIPTION "Get the name of this physical store. "
      ::= { webServicePhysicalStoreEntry 5  }
   
   
   webServicePhysicalStoreStoreType OBJECT-TYPE
      SYNTAX      OCTET STRING
      MAX-ACCESS  read-only
      STATUS      current
      DESCRIPTION "Get the type of this physical store. "
      ::= { webServicePhysicalStoreEntry 6  }
   
   
   webServicePhysicalStoreSynchronousWritePolicy OBJECT-TYPE
      SYNTAX      OCTET STRING
      MAX-ACCESS  read-only
      STATUS      current
      DESCRIPTION "Specifies the algorithm used when performing synchronous writes to the physical store. "
      ::= { webServicePhysicalStoreEntry 7  }
   
   
   webServicePhysicalStoreTags OBJECT-TYPE
      SYNTAX      OCTET STRING
      MAX-ACCESS  read-only
      STATUS      current
      DESCRIPTION "Return all tags on this Configuration MBean "
      ::= { webServicePhysicalStoreEntry 8  }
   
   
   webServiceReliabilityTable OBJECT-TYPE
      SYNTAX      SEQUENCE OF WebServiceReliabilityEntry
      MAX-ACCESS  not-accessible
      STATUS      current
      DESCRIPTION "Represents reliability configuration for web services. "
      ::= { wls 1645  }
      
   
   webServiceReliabilityEntry OBJECT-TYPE
      SYNTAX      WebServiceReliabilityEntry
      MAX-ACCESS  not-accessible
      STATUS      current
      DESCRIPTION "Generated SNMP Table Entry."
      INDEX { webServiceReliabilityIndex}
      ::= { webServiceReliabilityTable 1 }
      
   WebServiceReliabilityEntry ::=
      SEQUENCE
      {
         webServiceReliabilityIndex OCTET STRING,
         webServiceReliabilityObjectName OCTET STRING,
         webServiceReliabilityBaseRetransmissionInterval OCTET STRING,
         webServiceReliabilityInactivityTimeout OCTET STRING,
         webServiceReliabilityAcknowledgementInterval OCTET STRING,
         webServiceReliabilityType OCTET STRING,
         webServiceReliabilityNonBufferedDestination OCTET STRING,
         webServiceReliabilityName OCTET STRING,
         webServiceReliabilityNonBufferedSource OCTET STRING,
         webServiceReliabilitySequenceExpiration OCTET STRING,
         webServiceReliabilityRetransmissionExponentialBackoff OCTET STRING,
         webServiceReliabilityTags OCTET STRING
      }
      
   
   webServiceReliabilityIndex OBJECT-TYPE
      SYNTAX      OCTET STRING
      MAX-ACCESS  not-accessible
      STATUS      current
      DESCRIPTION "Index column"
      ::= { webServiceReliabilityEntry 1  }
   
   
   webServiceReliabilityObjectName OBJECT-TYPE
      SYNTAX      OCTET STRING
      MAX-ACCESS  read-only
      STATUS      current
      DESCRIPTION "ObjectName column"
      ::= { webServiceReliabilityEntry 2  }
   
   
   webServiceReliabilityBaseRetransmissionInterval OBJECT-TYPE
      SYNTAX      OCTET STRING
      MAX-ACCESS  read-only
      STATUS      current
      DESCRIPTION "The interval of time that must pass before a message will be retransmitted to the RM destination (in the event a prior transmission failed). String value in 'Duration' format. Defaults to 'P0DT3S' (3 seconds). Set at sequence creation time, and cannot be reset. "
      ::= { webServiceReliabilityEntry 3  }
   
   
   webServiceReliabilityInactivityTimeout OBJECT-TYPE
      SYNTAX      OCTET STRING
      MAX-ACCESS  read-only
      STATUS      current
      DESCRIPTION "If during this duration, an endpoint (RM source or RM destination) has received no application or control messages, the endpoint MAY consider the RM Sequence to have been terminated due to inactivity. String value in 'Duration' format. Defaults to 'P0DT600S' (600 seconds). Implementations of RM source and RM destination are free to manage resources associated with the sequence as they please, but in general, there are no guarantees that the sequence will be useable by either party after the inactivity timeout expires. Set at sequence creation time, and cannot be reset. "
      ::= { webServiceReliabilityEntry 4  }
   
   
   webServiceReliabilityAcknowledgementInterval OBJECT-TYPE
      SYNTAX      OCTET STRING
      MAX-ACCESS  read-only
      STATUS      current
      DESCRIPTION "The maximum time a pending acknowledgement (set after the destination accepts a message) can wait before being delivered back to the RM source. String value in 'Duration' format. Defaults to 'P0DT0.2S' (200 milliseconds). Set at sequence creation time, and cannot be reset. "
      ::= { webServiceReliabilityEntry 5  }
   
   
   webServiceReliabilityType OBJECT-TYPE
      SYNTAX      OCTET STRING
      MAX-ACCESS  read-only
      STATUS      current
      DESCRIPTION "Returns the type of the MBean. "
      ::= { webServiceReliabilityEntry 6  }
   
   
   webServiceReliabilityNonBufferedDestination OBJECT-TYPE
      SYNTAX      OCTET STRING
      MAX-ACCESS  read-only
      STATUS      current
      DESCRIPTION "A boolean flag indicating that RM destinations, by default, will receive non-buffered. Defaults to false. Note, changes to this default will only be picked up by new reliable sequences. Existing reliable sequences have their persistence handling set at creation time and these values will not change. "
      ::= { webServiceReliabilityEntry 7  }
   
   
   webServiceReliabilityName OBJECT-TYPE
      SYNTAX      OCTET STRING
      MAX-ACCESS  read-only
      STATUS      current
      DESCRIPTION "The user-specified name of this MBean instance.  This name is included as one of the key properties in the MBean's javax.management.ObjectName:  Name=user-specified-name "
      ::= { webServiceReliabilityEntry 8  }
   
   
   webServiceReliabilityNonBufferedSource OBJECT-TYPE
      SYNTAX      OCTET STRING
      MAX-ACCESS  read-only
      STATUS      current
      DESCRIPTION "A boolean flag indicating that RM sources, by default, will send non-buffered. Defaults to false. Note, changes to this default will only be picked up by new reliable sequences. Existing reliable sequences have their persistence handling set at creation time and these values will not change. "
      ::= { webServiceReliabilityEntry 9  }
   
   
   webServiceReliabilitySequenceExpiration OBJECT-TYPE
      SYNTAX      OCTET STRING
      MAX-ACCESS  read-only
      STATUS      current
      DESCRIPTION "This is the maximum lifetime of a sequence. If this limit is reached before the sequence naturally completes, it will be forcibly terminated. String value in 'Duration' format. Defaults to 'P1D' (1 day). Set at sequence creation time, and cannot be reset. "
      ::= { webServiceReliabilityEntry 10  }
   
   
   webServiceReliabilityRetransmissionExponentialBackoff OBJECT-TYPE
      SYNTAX      OCTET STRING
      MAX-ACCESS  read-only
      STATUS      current
      DESCRIPTION "A boolean flag indicating that the retransmission interval will be adjusted using the exponential backoff algorithm ([Tanenbaum]). Defaults to false. Set at sequence creation time, and cannot be reset. "
      ::= { webServiceReliabilityEntry 11  }
   
   
   webServiceReliabilityTags OBJECT-TYPE
      SYNTAX      OCTET STRING
      MAX-ACCESS  read-only
      STATUS      current
      DESCRIPTION "Return all tags on this Configuration MBean "
      ::= { webServiceReliabilityEntry 12  }
   
   
   webServiceRequestBufferingQueueTable OBJECT-TYPE
      SYNTAX      SEQUENCE OF WebServiceRequestBufferingQueueEntry
      MAX-ACCESS  not-accessible
      STATUS      current
      DESCRIPTION "Represents request buffering queue configuration for web services. "
      ::= { wls 1650  }
      
   
   webServiceRequestBufferingQueueEntry OBJECT-TYPE
      SYNTAX      WebServiceRequestBufferingQueueEntry
      MAX-ACCESS  not-accessible
      STATUS      current
      DESCRIPTION "Generated SNMP Table Entry."
      INDEX { webServiceRequestBufferingQueueIndex}
      ::= { webServiceRequestBufferingQueueTable 1 }
      
   WebServiceRequestBufferingQueueEntry ::=
      SEQUENCE
      {
         webServiceRequestBufferingQueueIndex OCTET STRING,
         webServiceRequestBufferingQueueObjectName OCTET STRING,
         webServiceRequestBufferingQueueEnabled OCTET STRING,
         webServiceRequestBufferingQueueType OCTET STRING,
         webServiceRequestBufferingQueueTransactionEnabled OCTET STRING,
         webServiceRequestBufferingQueueName OCTET STRING,
         webServiceRequestBufferingQueueConnectionFactoryJndiName OCTET STRING,
         webServiceRequestBufferingQueueTags OCTET STRING
      }
      
   
   webServiceRequestBufferingQueueIndex OBJECT-TYPE
      SYNTAX      OCTET STRING
      MAX-ACCESS  not-accessible
      STATUS      current
      DESCRIPTION "Index column"
      ::= { webServiceRequestBufferingQueueEntry 1  }
   
   
   webServiceRequestBufferingQueueObjectName OBJECT-TYPE
      SYNTAX      OCTET STRING
      MAX-ACCESS  read-only
      STATUS      current
      DESCRIPTION "ObjectName column"
      ::= { webServiceRequestBufferingQueueEntry 2  }
   
   
   webServiceRequestBufferingQueueEnabled OBJECT-TYPE
      SYNTAX      OCTET STRING
      MAX-ACCESS  read-only
      STATUS      current
      DESCRIPTION "A boolean flag indicating whether buffering is enabled (request buffering if this is the request queue, or response buffering if this is the response queue). Defaults to false. "
      ::= { webServiceRequestBufferingQueueEntry 3  }
   
   
   webServiceRequestBufferingQueueType OBJECT-TYPE
      SYNTAX      OCTET STRING
      MAX-ACCESS  read-only
      STATUS      current
      DESCRIPTION "Returns the type of the MBean. "
      ::= { webServiceRequestBufferingQueueEntry 4  }
   
   
   webServiceRequestBufferingQueueTransactionEnabled OBJECT-TYPE
      SYNTAX      OCTET STRING
      MAX-ACCESS  read-only
      STATUS      current
      DESCRIPTION "A boolean flag indicating whether transactions should be used when buffering a message onto or consuming a message off of this queue. Defaults to false. "
      ::= { webServiceRequestBufferingQueueEntry 5  }
   
   
   webServiceRequestBufferingQueueName OBJECT-TYPE
      SYNTAX      OCTET STRING
      MAX-ACCESS  read-only
      STATUS      current
      DESCRIPTION "Get the name of this buffering queue. This name is the JNDI name of the queue to be used for buffering. "
      ::= { webServiceRequestBufferingQueueEntry 6  }
   
   
   webServiceRequestBufferingQueueConnectionFactoryJndiName OBJECT-TYPE
      SYNTAX      OCTET STRING
      MAX-ACCESS  read-only
      STATUS      current
      DESCRIPTION "The JNDI name of the connection factory to use when buffering messages onto this queue. Defaults to the 'default' JMS connection factory. "
      ::= { webServiceRequestBufferingQueueEntry 7  }
   
   
   webServiceRequestBufferingQueueTags OBJECT-TYPE
      SYNTAX      OCTET STRING
      MAX-ACCESS  read-only
      STATUS      current
      DESCRIPTION "Return all tags on this Configuration MBean "
      ::= { webServiceRequestBufferingQueueEntry 8  }
   
   
   webServiceResponseBufferingQueueTable OBJECT-TYPE
      SYNTAX      SEQUENCE OF WebServiceResponseBufferingQueueEntry
      MAX-ACCESS  not-accessible
      STATUS      current
      DESCRIPTION "Represents response buffering queue configuration for web services. "
      ::= { wls 1655  }
      
   
   webServiceResponseBufferingQueueEntry OBJECT-TYPE
      SYNTAX      WebServiceResponseBufferingQueueEntry
      MAX-ACCESS  not-accessible
      STATUS      current
      DESCRIPTION "Generated SNMP Table Entry."
      INDEX { webServiceResponseBufferingQueueIndex}
      ::= { webServiceResponseBufferingQueueTable 1 }
      
   WebServiceResponseBufferingQueueEntry ::=
      SEQUENCE
      {
         webServiceResponseBufferingQueueIndex OCTET STRING,
         webServiceResponseBufferingQueueObjectName OCTET STRING,
         webServiceResponseBufferingQueueEnabled OCTET STRING,
         webServiceResponseBufferingQueueType OCTET STRING,
         webServiceResponseBufferingQueueTransactionEnabled OCTET STRING,
         webServiceResponseBufferingQueueName OCTET STRING,
         webServiceResponseBufferingQueueConnectionFactoryJndiName OCTET STRING,
         webServiceResponseBufferingQueueTags OCTET STRING
      }
      
   
   webServiceResponseBufferingQueueIndex OBJECT-TYPE
      SYNTAX      OCTET STRING
      MAX-ACCESS  not-accessible
      STATUS      current
      DESCRIPTION "Index column"
      ::= { webServiceResponseBufferingQueueEntry 1  }
   
   
   webServiceResponseBufferingQueueObjectName OBJECT-TYPE
      SYNTAX      OCTET STRING
      MAX-ACCESS  read-only
      STATUS      current
      DESCRIPTION "ObjectName column"
      ::= { webServiceResponseBufferingQueueEntry 2  }
   
   
   webServiceResponseBufferingQueueEnabled OBJECT-TYPE
      SYNTAX      OCTET STRING
      MAX-ACCESS  read-only
      STATUS      current
      DESCRIPTION "A boolean flag indicating whether buffering is enabled (request buffering if this is the request queue, or response buffering if this is the response queue). Defaults to false. "
      ::= { webServiceResponseBufferingQueueEntry 3  }
   
   
   webServiceResponseBufferingQueueType OBJECT-TYPE
      SYNTAX      OCTET STRING
      MAX-ACCESS  read-only
      STATUS      current
      DESCRIPTION "Returns the type of the MBean. "
      ::= { webServiceResponseBufferingQueueEntry 4  }
   
   
   webServiceResponseBufferingQueueTransactionEnabled OBJECT-TYPE
      SYNTAX      OCTET STRING
      MAX-ACCESS  read-only
      STATUS      current
      DESCRIPTION "A boolean flag indicating whether transactions should be used when buffering a message onto or consuming a message off of this queue. Defaults to false. "
      ::= { webServiceResponseBufferingQueueEntry 5  }
   
   
   webServiceResponseBufferingQueueName OBJECT-TYPE
      SYNTAX      OCTET STRING
      MAX-ACCESS  read-only
      STATUS      current
      DESCRIPTION "Get the name of this buffering queue. This name is the JNDI name of the queue to be used for buffering. "
      ::= { webServiceResponseBufferingQueueEntry 6  }
   
   
   webServiceResponseBufferingQueueConnectionFactoryJndiName OBJECT-TYPE
      SYNTAX      OCTET STRING
      MAX-ACCESS  read-only
      STATUS      current
      DESCRIPTION "The JNDI name of the connection factory to use when buffering messages onto this queue. Defaults to the 'default' JMS connection factory. "
      ::= { webServiceResponseBufferingQueueEntry 7  }
   
   
   webServiceResponseBufferingQueueTags OBJECT-TYPE
      SYNTAX      OCTET STRING
      MAX-ACCESS  read-only
      STATUS      current
      DESCRIPTION "Return all tags on this Configuration MBean "
      ::= { webServiceResponseBufferingQueueEntry 8  }
   
   
   appDeploymentRuntimeTable OBJECT-TYPE
      SYNTAX      SEQUENCE OF AppDeploymentRuntimeEntry
      MAX-ACCESS  not-accessible
      STATUS      current
      DESCRIPTION "This MBean provides deployment operations for an application. Currently only start and stop are supported. In the future, this MBean may be enhanced with operations to support deployment applications to the domain as well as extended WLS deployment features such as production redeployment and partial deployment of modules in an enterprise application. "
      ::= { wls 1660  }
      
   
   appDeploymentRuntimeEntry OBJECT-TYPE
      SYNTAX      AppDeploymentRuntimeEntry
      MAX-ACCESS  not-accessible
      STATUS      current
      DESCRIPTION "Generated SNMP Table Entry."
      INDEX { appDeploymentRuntimeIndex}
      ::= { appDeploymentRuntimeTable 1 }
      
   AppDeploymentRuntimeEntry ::=
      SEQUENCE
      {
         appDeploymentRuntimeIndex OCTET STRING,
         appDeploymentRuntimeObjectName OCTET STRING,
         appDeploymentRuntimeApplicationName OCTET STRING,
         appDeploymentRuntimeApplicationVersion OCTET STRING,
         appDeploymentRuntimeType OCTET STRING,
         appDeploymentRuntimeModules OCTET STRING,
         appDeploymentRuntimeName OCTET STRING,
         appDeploymentRuntimePartitionName OCTET STRING
      }
      
   
   appDeploymentRuntimeIndex OBJECT-TYPE
      SYNTAX      OCTET STRING
      MAX-ACCESS  not-accessible
      STATUS      current
      DESCRIPTION "Index column"
      ::= { appDeploymentRuntimeEntry 1  }
   
   
   appDeploymentRuntimeObjectName OBJECT-TYPE
      SYNTAX      OCTET STRING
      MAX-ACCESS  read-only
      STATUS      current
      DESCRIPTION "ObjectName column"
      ::= { appDeploymentRuntimeEntry 2  }
   
   
   appDeploymentRuntimeApplicationName OBJECT-TYPE
      SYNTAX      OCTET STRING
      MAX-ACCESS  read-only
      STATUS      current
      DESCRIPTION "The application's name. "
      ::= { appDeploymentRuntimeEntry 3  }
   
   
   appDeploymentRuntimeApplicationVersion OBJECT-TYPE
      SYNTAX      OCTET STRING
      MAX-ACCESS  read-only
      STATUS      current
      DESCRIPTION "The application's version identifier. "
      ::= { appDeploymentRuntimeEntry 4  }
   
   
   appDeploymentRuntimeType OBJECT-TYPE
      SYNTAX      OCTET STRING
      MAX-ACCESS  read-only
      STATUS      current
      DESCRIPTION "Returns the type of the MBean. "
      ::= { appDeploymentRuntimeEntry 5  }
   
   
   appDeploymentRuntimeModules OBJECT-TYPE
      SYNTAX      OCTET STRING
      MAX-ACCESS  read-only
      STATUS      current
      DESCRIPTION "The list of modules for the application. These modules can be used in module level targeting. "
      ::= { appDeploymentRuntimeEntry 6  }
   
   
   appDeploymentRuntimeName OBJECT-TYPE
      SYNTAX      OCTET STRING
      MAX-ACCESS  read-only
      STATUS      current
      DESCRIPTION "The name of this configuration. WebLogic Server uses an MBean to implement and persist the configuration. "
      ::= { appDeploymentRuntimeEntry 7  }
   
   
   appDeploymentRuntimePartitionName OBJECT-TYPE
      SYNTAX      OCTET STRING
      MAX-ACCESS  read-only
      STATUS      current
      DESCRIPTION "The name of the partition the application is in. "
      ::= { appDeploymentRuntimeEntry 8  }
   
   
   coherenceClusterRuntimeTable OBJECT-TYPE
      SYNTAX      SEQUENCE OF CoherenceClusterRuntimeEntry
      MAX-ACCESS  not-accessible
      STATUS      current
      DESCRIPTION "Coherence cluster run-time information. "
      ::= { wls 1665  }
      
   
   coherenceClusterRuntimeEntry OBJECT-TYPE
      SYNTAX      CoherenceClusterRuntimeEntry
      MAX-ACCESS  not-accessible
      STATUS      current
      DESCRIPTION "Generated SNMP Table Entry."
      INDEX { coherenceClusterRuntimeIndex}
      ::= { coherenceClusterRuntimeTable 1 }
      
   CoherenceClusterRuntimeEntry ::=
      SEQUENCE
      {
         coherenceClusterRuntimeIndex OCTET STRING,
         coherenceClusterRuntimeObjectName OCTET STRING,
         coherenceClusterRuntimeClusterSize Integer32,
         coherenceClusterRuntimeLicenseMode OCTET STRING,
         coherenceClusterRuntimeType OCTET STRING,
         coherenceClusterRuntimeMembers OCTET STRING,
         coherenceClusterRuntimeName OCTET STRING,
         coherenceClusterRuntimeClusterName OCTET STRING,
         coherenceClusterRuntimeVersion OCTET STRING
      }
      
   
   coherenceClusterRuntimeIndex OBJECT-TYPE
      SYNTAX      OCTET STRING
      MAX-ACCESS  not-accessible
      STATUS      current
      DESCRIPTION "Index column"
      ::= { coherenceClusterRuntimeEntry 1  }
   
   
   coherenceClusterRuntimeObjectName OBJECT-TYPE
      SYNTAX      OCTET STRING
      MAX-ACCESS  read-only
      STATUS      current
      DESCRIPTION "ObjectName column"
      ::= { coherenceClusterRuntimeEntry 2  }
   
   
   coherenceClusterRuntimeClusterSize OBJECT-TYPE
      SYNTAX      Integer32
      MAX-ACCESS  read-only
      STATUS      current
      DESCRIPTION "The size of the Coherence cluster.  "
      ::= { coherenceClusterRuntimeEntry 3  }
   
   
   coherenceClusterRuntimeLicenseMode OBJECT-TYPE
      SYNTAX      OCTET STRING
      MAX-ACCESS  read-only
      STATUS      current
      DESCRIPTION "The license mode for the Coherence cluster. Possible values are Evaluation, Development, or Production. "
      ::= { coherenceClusterRuntimeEntry 4  }
   
   
   coherenceClusterRuntimeType OBJECT-TYPE
      SYNTAX      OCTET STRING
      MAX-ACCESS  read-only
      STATUS      current
      DESCRIPTION "Returns the type of the MBean. "
      ::= { coherenceClusterRuntimeEntry 5  }
   
   
   coherenceClusterRuntimeMembers OBJECT-TYPE
      SYNTAX      OCTET STRING
      MAX-ACCESS  read-only
      STATUS      current
      DESCRIPTION "Identifiers for the available Coherence cluster members.  "
      ::= { coherenceClusterRuntimeEntry 6  }
   
   
   coherenceClusterRuntimeName OBJECT-TYPE
      SYNTAX      OCTET STRING
      MAX-ACCESS  read-only
      STATUS      current
      DESCRIPTION "The name of this configuration. WebLogic Server uses an MBean to implement and persist the configuration. "
      ::= { coherenceClusterRuntimeEntry 7  }
   
   
   coherenceClusterRuntimeClusterName OBJECT-TYPE
      SYNTAX      OCTET STRING
      MAX-ACCESS  read-only
      STATUS      current
      DESCRIPTION "The name of the Coherence cluster.  "
      ::= { coherenceClusterRuntimeEntry 8  }
   
   
   coherenceClusterRuntimeVersion OBJECT-TYPE
      SYNTAX      OCTET STRING
      MAX-ACCESS  read-only
      STATUS      current
      DESCRIPTION "The Coherence cluster version.  "
      ::= { coherenceClusterRuntimeEntry 9  }
   
   
   deploymentManagerTable OBJECT-TYPE
      SYNTAX      SEQUENCE OF DeploymentManagerEntry
      MAX-ACCESS  not-accessible
      STATUS      current
      DESCRIPTION "This MBean provides deployment operations.  A DeploymentManager object is a stateless interface into the WebLogic Server deployment framework. It currently provides access to the AppDeploymentRuntimeMBeans that allow the user to start and stop deployments. In the future, this MBean may be enhanced with operations to support deployment applications to the domain, as well as extended WebLogic Server deployment features, such as production redeployment and partial deployment of modules in an enterprise application.  This MBean emits notifications when an application is created or removed and when the application state changes.  The notification types are:  appdeployment.created appdeployment.deleted appdeployment.state.new appdeployment.state.prepared appdeployment.state.admin appdeployment.state.active appdeployment.state.retired appdeployment.state.failed appdeployment.state.update.pending appdeployment.state.unknown   The userdata is the object name of the application. "
      ::= { wls 1670  }
      
   
   deploymentManagerEntry OBJECT-TYPE
      SYNTAX      DeploymentManagerEntry
      MAX-ACCESS  not-accessible
      STATUS      current
      DESCRIPTION "Generated SNMP Table Entry."
      INDEX { deploymentManagerIndex}
      ::= { deploymentManagerTable 1 }
      
   DeploymentManagerEntry ::=
      SEQUENCE
      {
         deploymentManagerIndex OCTET STRING,
         deploymentManagerObjectName OCTET STRING,
         deploymentManagerMaximumDeploymentProgressObjectsCount Integer32,
         deploymentManagerType OCTET STRING,
         deploymentManagerName OCTET STRING
      }
      
   
   deploymentManagerIndex OBJECT-TYPE
      SYNTAX      OCTET STRING
      MAX-ACCESS  not-accessible
      STATUS      current
      DESCRIPTION "Index column"
      ::= { deploymentManagerEntry 1  }
   
   
   deploymentManagerObjectName OBJECT-TYPE
      SYNTAX      OCTET STRING
      MAX-ACCESS  read-only
      STATUS      current
      DESCRIPTION "ObjectName column"
      ::= { deploymentManagerEntry 2  }
   
   
   deploymentManagerMaximumDeploymentProgressObjectsCount OBJECT-TYPE
      SYNTAX      Integer32
      MAX-ACCESS  read-only
      STATUS      current
      DESCRIPTION "The maximum number of progress objects allowed. "
      ::= { deploymentManagerEntry 3  }
   
   
   deploymentManagerType OBJECT-TYPE
      SYNTAX      OCTET STRING
      MAX-ACCESS  read-only
      STATUS      current
      DESCRIPTION "Returns the type of the MBean. "
      ::= { deploymentManagerEntry 4  }
   
   
   deploymentManagerName OBJECT-TYPE
      SYNTAX      OCTET STRING
      MAX-ACCESS  read-only
      STATUS      current
      DESCRIPTION "The name of this configuration. WebLogic Server uses an MBean to implement and persist the configuration. "
      ::= { deploymentManagerEntry 5  }
   
   
   deploymentProgressObjectTable OBJECT-TYPE
      SYNTAX      SEQUENCE OF DeploymentProgressObjectEntry
      MAX-ACCESS  not-accessible
      STATUS      current
      DESCRIPTION "This MBean is the user API for monitoring deployment operations and exists only on an Administration Server. Currently only start and stop operations initiated by {@link AppDeploymentRuntimeMBean} are supported. "
      ::= { wls 1675  }
      
   
   deploymentProgressObjectEntry OBJECT-TYPE
      SYNTAX      DeploymentProgressObjectEntry
      MAX-ACCESS  not-accessible
      STATUS      current
      DESCRIPTION "Generated SNMP Table Entry."
      INDEX { deploymentProgressObjectIndex}
      ::= { deploymentProgressObjectTable 1 }
      
   DeploymentProgressObjectEntry ::=
      SEQUENCE
      {
         deploymentProgressObjectIndex OCTET STRING,
         deploymentProgressObjectObjectName OCTET STRING,
         deploymentProgressObjectApplicationName OCTET STRING,
         deploymentProgressObjectType OCTET STRING,
         deploymentProgressObjectName OCTET STRING,
         deploymentProgressObjectMessages OCTET STRING,
         deploymentProgressObjectState OCTET STRING,
         deploymentProgressObjectBeginTime Counter64,
         deploymentProgressObjectFailedTargets OCTET STRING,
         deploymentProgressObjectEndTime Counter64,
         deploymentProgressObjectOperationType Integer32,
         deploymentProgressObjectTargets OCTET STRING
      }
      
   
   deploymentProgressObjectIndex OBJECT-TYPE
      SYNTAX      OCTET STRING
      MAX-ACCESS  not-accessible
      STATUS      current
      DESCRIPTION "Index column"
      ::= { deploymentProgressObjectEntry 1  }
   
   
   deploymentProgressObjectObjectName OBJECT-TYPE
      SYNTAX      OCTET STRING
      MAX-ACCESS  read-only
      STATUS      current
      DESCRIPTION "ObjectName column"
      ::= { deploymentProgressObjectEntry 2  }
   
   
   deploymentProgressObjectApplicationName OBJECT-TYPE
      SYNTAX      OCTET STRING
      MAX-ACCESS  read-only
      STATUS      current
      DESCRIPTION "The name of the application for the current deployment operation. "
      ::= { deploymentProgressObjectEntry 3  }
   
   
   deploymentProgressObjectType OBJECT-TYPE
      SYNTAX      OCTET STRING
      MAX-ACCESS  read-only
      STATUS      current
      DESCRIPTION "Returns the type of the MBean. "
      ::= { deploymentProgressObjectEntry 4  }
   
   
   deploymentProgressObjectName OBJECT-TYPE
      SYNTAX      OCTET STRING
      MAX-ACCESS  read-only
      STATUS      current
      DESCRIPTION "The name of this configuration. WebLogic Server uses an MBean to implement and persist the configuration. "
      ::= { deploymentProgressObjectEntry 5  }
   
   
   deploymentProgressObjectMessages OBJECT-TYPE
      SYNTAX      OCTET STRING
      MAX-ACCESS  read-only
      STATUS      current
      DESCRIPTION "Provides an ordered array of status messages generated for the current deployment operation. "
      ::= { deploymentProgressObjectEntry 6  }
   
   
   deploymentProgressObjectState OBJECT-TYPE
      SYNTAX      OCTET STRING
      MAX-ACCESS  read-only
      STATUS      current
      DESCRIPTION "The state of the current deployment operation. Possible values are STATE_INITIALIZED, STATE_RUNNING, STATE_COMPLETED, STATE_FAILED and STATE_DEFERRED. "
      ::= { deploymentProgressObjectEntry 7  }
   
   
   deploymentProgressObjectBeginTime OBJECT-TYPE
      SYNTAX      Counter64
      MAX-ACCESS  read-only
      STATUS      current
      DESCRIPTION "The time that the current deployment operation began. The value is in milliseconds consistent with the system time. "
      ::= { deploymentProgressObjectEntry 8  }
   
   
   deploymentProgressObjectFailedTargets OBJECT-TYPE
      SYNTAX      OCTET STRING
      MAX-ACCESS  read-only
      STATUS      current
      DESCRIPTION "The targets on which the current deployment operation failed. "
      ::= { deploymentProgressObjectEntry 9  }
   
   
   deploymentProgressObjectEndTime OBJECT-TYPE
      SYNTAX      Counter64
      MAX-ACCESS  read-only
      STATUS      current
      DESCRIPTION "The time that the current deployment operation ended. The value is in milliseconds consistent with the system time. If the operation has not ended, the value will be zero. "
      ::= { deploymentProgressObjectEntry 11  }
   
   
   deploymentProgressObjectOperationType OBJECT-TYPE
      SYNTAX      Integer32
      MAX-ACCESS  read-only
      STATUS      current
      DESCRIPTION "The deployment operation type for the current deployment operation. Possible values are 1 (start) and 2 (stop). "
      ::= { deploymentProgressObjectEntry 12  }
   
   
   deploymentProgressObjectTargets OBJECT-TYPE
      SYNTAX      OCTET STRING
      MAX-ACCESS  read-only
      STATUS      current
      DESCRIPTION "The targets specified for the current deployment operation. "
      ::= { deploymentProgressObjectEntry 13  }
   
   
   webServiceRuntimeTable OBJECT-TYPE
      SYNTAX      SEQUENCE OF WebServiceRuntimeEntry
      MAX-ACCESS  not-accessible
      STATUS      current
      DESCRIPTION "Describes the state of a single webservice."
      ::= { wls 1680  }
      
   
   webServiceRuntimeEntry OBJECT-TYPE
      SYNTAX      WebServiceRuntimeEntry
      MAX-ACCESS  not-accessible
      STATUS      current
      DESCRIPTION "Generated SNMP Table Entry."
      INDEX { webServiceRuntimeIndex}
      ::= { webServiceRuntimeTable 1 }
      
   WebServiceRuntimeEntry ::=
      SEQUENCE
      {
         webServiceRuntimeIndex OCTET STRING,
         webServiceRuntimeObjectName OCTET STRING,
         webServiceRuntimeType OCTET STRING,
         webServiceRuntimeHomePageURL OCTET STRING,
         webServiceRuntimeLastResetTime OCTET STRING,
         webServiceRuntimeWSDLHitCount Integer32,
         webServiceRuntimeName OCTET STRING,
         webServiceRuntimeMalformedRequestCount Integer32,
         webServiceRuntimeServiceName OCTET STRING,
         webServiceRuntimeHomePageHitCount Integer32,
         webServiceRuntimeWSDLUrl OCTET STRING,
         webServiceRuntimeURI OCTET STRING
      }
      
   
   webServiceRuntimeIndex OBJECT-TYPE
      SYNTAX      OCTET STRING
      MAX-ACCESS  not-accessible
      STATUS      current
      DESCRIPTION "Index column"
      ::= { webServiceRuntimeEntry 1  }
   
   
   webServiceRuntimeObjectName OBJECT-TYPE
      SYNTAX      OCTET STRING
      MAX-ACCESS  read-only
      STATUS      current
      DESCRIPTION "ObjectName column"
      ::= { webServiceRuntimeEntry 2  }
   
   
   webServiceRuntimeType OBJECT-TYPE
      SYNTAX      OCTET STRING
      MAX-ACCESS  read-only
      STATUS      current
      DESCRIPTION "Returns the type of the MBean."
      ::= { webServiceRuntimeEntry 3  }
   
   
   webServiceRuntimeHomePageURL OBJECT-TYPE
      SYNTAX      OCTET STRING
      MAX-ACCESS  read-only
      STATUS      current
      DESCRIPTION "Provides the URL from which the home page for this webservice can be retrieved."
      ::= { webServiceRuntimeEntry 4  }
   
   
   webServiceRuntimeLastResetTime OBJECT-TYPE
      SYNTAX      OCTET STRING
      MAX-ACCESS  read-only
      STATUS      current
      DESCRIPTION "Provides the Date on which reset() was last called for this mbean, or null if it has never been called."
      ::= { webServiceRuntimeEntry 5  }
   
   
   webServiceRuntimeWSDLHitCount OBJECT-TYPE
      SYNTAX      Integer32
      MAX-ACCESS  read-only
      STATUS      current
      DESCRIPTION "Provides a count of the number of times that this service's WSDL has been retrieved since this webservice was deployed."
      ::= { webServiceRuntimeEntry 6  }
   
   
   webServiceRuntimeName OBJECT-TYPE
      SYNTAX      OCTET STRING
      MAX-ACCESS  read-only
      STATUS      current
      DESCRIPTION "The name of this configuration. WebLogic Server uses an MBean to implement and persist the configuration."
      ::= { webServiceRuntimeEntry 7  }
   
   
   webServiceRuntimeMalformedRequestCount OBJECT-TYPE
      SYNTAX      Integer32
      MAX-ACCESS  read-only
      STATUS      current
      DESCRIPTION "Provides a count of the number of times that this service has received a malformed or otherwise invalid request."
      ::= { webServiceRuntimeEntry 8  }
   
   
   webServiceRuntimeServiceName OBJECT-TYPE
      SYNTAX      OCTET STRING
      MAX-ACCESS  read-only
      STATUS      current
      DESCRIPTION "Provides the name of this service."
      ::= { webServiceRuntimeEntry 9  }
   
   
   webServiceRuntimeHomePageHitCount OBJECT-TYPE
      SYNTAX      Integer32
      MAX-ACCESS  read-only
      STATUS      current
      DESCRIPTION "Provides a count of the number of times that this service's home page has been visited since this webservice was deployed."
      ::= { webServiceRuntimeEntry 10  }
   
   
   webServiceRuntimeWSDLUrl OBJECT-TYPE
      SYNTAX      OCTET STRING
      MAX-ACCESS  read-only
      STATUS      current
      DESCRIPTION "Provides the URL from which the WSDL for this webservice can be retrieved."
      ::= { webServiceRuntimeEntry 11  }
   
   
   webServiceRuntimeURI OBJECT-TYPE
      SYNTAX      OCTET STRING
      MAX-ACCESS  read-only
      STATUS      current
      DESCRIPTION "Provides the URI of this service."
      ::= { webServiceRuntimeEntry 12  }
   
   
   wseeClientOperationRuntimeTable OBJECT-TYPE
      SYNTAX      SEQUENCE OF WseeClientOperationRuntimeEntry
      MAX-ACCESS  not-accessible
      STATUS      current
      DESCRIPTION "Describes the state of a particular Web Service operation, such as deployment state and runtime statistics about the execution of the operation. This MBean can describe the operation on a web service client or service. Request statistics relate to outgoing requests on a client or incoming requests on a service. Response statistics relate to an incoming response on a client or an outgoing response on a service. Time values are reported in milliseconds "
      ::= { wls 1685  }
      
   
   wseeClientOperationRuntimeEntry OBJECT-TYPE
      SYNTAX      WseeClientOperationRuntimeEntry
      MAX-ACCESS  not-accessible
      STATUS      current
      DESCRIPTION "Generated SNMP Table Entry."
      INDEX { wseeClientOperationRuntimeIndex}
      ::= { wseeClientOperationRuntimeTable 1 }
      
   WseeClientOperationRuntimeEntry ::=
      SEQUENCE
      {
         wseeClientOperationRuntimeIndex OCTET STRING,
         wseeClientOperationRuntimeObjectName OCTET STRING,
         wseeClientOperationRuntimeType OCTET STRING,
         wseeClientOperationRuntimeLastResponseTime Counter64,
         wseeClientOperationRuntimeOperationName OCTET STRING,
         wseeClientOperationRuntimeResponseErrorCount Integer32,
         wseeClientOperationRuntimeResponseTimeLow Counter64,
         wseeClientOperationRuntimeResponseTimeTotal Counter64,
         wseeClientOperationRuntimeDispatchTimeTotal Counter64,
         wseeClientOperationRuntimeDispatchTimeLow Counter64,
         wseeClientOperationRuntimeExecutionTimeAverage Counter64,
         wseeClientOperationRuntimeResponseCount Integer32,
         wseeClientOperationRuntimeExecutionTimeHigh Counter64,
         wseeClientOperationRuntimeInvocationCount Integer32,
         wseeClientOperationRuntimeErrorCount Integer32,
         wseeClientOperationRuntimeLastResponseErrorTime Counter64,
         wseeClientOperationRuntimeLastResponseError OCTET STRING,
         wseeClientOperationRuntimeDispatchTimeHigh Counter64,
         wseeClientOperationRuntimeResponseTimeAverage Counter64,
         wseeClientOperationRuntimeDispatchTimeAverage Counter64,
         wseeClientOperationRuntimeLastError OCTET STRING,
         wseeClientOperationRuntimeExecutionTimeLow Counter64,
         wseeClientOperationRuntimeName OCTET STRING,
         wseeClientOperationRuntimeLastInvocationTime Counter64,
         wseeClientOperationRuntimeExecutionTimeTotal Counter64,
         wseeClientOperationRuntimeResponseTimeHigh Counter64,
         wseeClientOperationRuntimeLastErrorTime Counter64
      }
      
   
   wseeClientOperationRuntimeIndex OBJECT-TYPE
      SYNTAX      OCTET STRING
      MAX-ACCESS  not-accessible
      STATUS      current
      DESCRIPTION "Index column"
      ::= { wseeClientOperationRuntimeEntry 1  }
   
   
   wseeClientOperationRuntimeObjectName OBJECT-TYPE
      SYNTAX      OCTET STRING
      MAX-ACCESS  read-only
      STATUS      current
      DESCRIPTION "ObjectName column"
      ::= { wseeClientOperationRuntimeEntry 2  }
   
   
   wseeClientOperationRuntimeType OBJECT-TYPE
      SYNTAX      OCTET STRING
      MAX-ACCESS  read-only
      STATUS      current
      DESCRIPTION "Returns the type of the MBean. "
      ::= { wseeClientOperationRuntimeEntry 3  }
   
   
   wseeClientOperationRuntimeLastResponseTime OBJECT-TYPE
      SYNTAX      Counter64
      MAX-ACCESS  read-only
      STATUS      current
      DESCRIPTION "Time on WebLogic Server of the last response to arrive for this client/service (or 0 if no responses have been received) expressed as the number of milliseconds since midnight, January 1, 1970 UTC. "
      ::= { wseeClientOperationRuntimeEntry 4  }
   
   
   wseeClientOperationRuntimeOperationName OBJECT-TYPE
      SYNTAX      OCTET STRING
      MAX-ACCESS  read-only
      STATUS      current
      DESCRIPTION "Name of the operation for which runtime information is being provided. "
      ::= { wseeClientOperationRuntimeEntry 5  }
   
   
   wseeClientOperationRuntimeResponseErrorCount OBJECT-TYPE
      SYNTAX      Integer32
      MAX-ACCESS  read-only
      STATUS      current
      DESCRIPTION "Total number of errors from responses generated from operation invocations. "
      ::= { wseeClientOperationRuntimeEntry 6  }
   
   
   wseeClientOperationRuntimeResponseTimeLow OBJECT-TYPE
      SYNTAX      Counter64
      MAX-ACCESS  read-only
      STATUS      current
      DESCRIPTION "Lowest response time from the responses generated from operation invocations. "
      ::= { wseeClientOperationRuntimeEntry 7  }
   
   
   wseeClientOperationRuntimeResponseTimeTotal OBJECT-TYPE
      SYNTAX      Counter64
      MAX-ACCESS  read-only
      STATUS      current
      DESCRIPTION "Total time for all responses generated from operation invocations. "
      ::= { wseeClientOperationRuntimeEntry 8  }
   
   
   wseeClientOperationRuntimeDispatchTimeTotal OBJECT-TYPE
      SYNTAX      Counter64
      MAX-ACCESS  read-only
      STATUS      current
      DESCRIPTION "Total time for all operation dispatches in the current measurement period.  Dispatch time refers to the time for WebLogic Server to process the invocation.  The measurement period typically starts when WebLogic Server is first started. "
      ::= { wseeClientOperationRuntimeEntry 9  }
   
   
   wseeClientOperationRuntimeDispatchTimeLow OBJECT-TYPE
      SYNTAX      Counter64
      MAX-ACCESS  read-only
      STATUS      current
      DESCRIPTION "Shortest operation dispatch time for the current measurement period.  Dispatch time refers to the time for WebLogic Server to process the invocation.  The measurement period typically starts when WebLogic Server is first started. "
      ::= { wseeClientOperationRuntimeEntry 10  }
   
   
   wseeClientOperationRuntimeExecutionTimeAverage OBJECT-TYPE
      SYNTAX      Counter64
      MAX-ACCESS  read-only
      STATUS      current
      DESCRIPTION "Average operation execution time. "
      ::= { wseeClientOperationRuntimeEntry 11  }
   
   
   wseeClientOperationRuntimeResponseCount OBJECT-TYPE
      SYNTAX      Integer32
      MAX-ACCESS  read-only
      STATUS      current
      DESCRIPTION "Total number of oresponses generated from operation invocations. "
      ::= { wseeClientOperationRuntimeEntry 12  }
   
   
   wseeClientOperationRuntimeExecutionTimeHigh OBJECT-TYPE
      SYNTAX      Counter64
      MAX-ACCESS  read-only
      STATUS      current
      DESCRIPTION "Longest operation execution time. "
      ::= { wseeClientOperationRuntimeEntry 13  }
   
   
   wseeClientOperationRuntimeInvocationCount OBJECT-TYPE
      SYNTAX      Integer32
      MAX-ACCESS  read-only
      STATUS      current
      DESCRIPTION "Total number of operation invocations in the current measurement period.  The measurement period typically starts when WebLogic Server is first started. "
      ::= { wseeClientOperationRuntimeEntry 14  }
   
   
   wseeClientOperationRuntimeErrorCount OBJECT-TYPE
      SYNTAX      Integer32
      MAX-ACCESS  read-only
      STATUS      current
      DESCRIPTION "Number of errors sending or receiving a request. "
      ::= { wseeClientOperationRuntimeEntry 15  }
   
   
   wseeClientOperationRuntimeLastResponseErrorTime OBJECT-TYPE
      SYNTAX      Counter64
      MAX-ACCESS  read-only
      STATUS      current
      DESCRIPTION "Time on WebLogic Server of the last error sending or receiving a response (or 0 if no failures have occurred) expressed as the number of milliseconds since midnight, January 1, 1970 UTC. "
      ::= { wseeClientOperationRuntimeEntry 16  }
   
   
   wseeClientOperationRuntimeLastResponseError OBJECT-TYPE
      SYNTAX      OCTET STRING
      MAX-ACCESS  read-only
      STATUS      current
      DESCRIPTION "Last response error to arrive for this client/service (or null if no errors have occurred). "
      ::= { wseeClientOperationRuntimeEntry 17  }
   
   
   wseeClientOperationRuntimeDispatchTimeHigh OBJECT-TYPE
      SYNTAX      Counter64
      MAX-ACCESS  read-only
      STATUS      current
      DESCRIPTION "Longest operation dispatch time for the current measurement period.  Dispatch time refers to the time for WebLogic Server to process the invocation.  The measurement period typically starts when WebLogic Server is first started. "
      ::= { wseeClientOperationRuntimeEntry 18  }
   
   
   wseeClientOperationRuntimeResponseTimeAverage OBJECT-TYPE
      SYNTAX      Counter64
      MAX-ACCESS  read-only
      STATUS      current
      DESCRIPTION "Average response time from the responses generated from operation invocations.  "
      ::= { wseeClientOperationRuntimeEntry 19  }
   
   
   wseeClientOperationRuntimeDispatchTimeAverage OBJECT-TYPE
      SYNTAX      Counter64
      MAX-ACCESS  read-only
      STATUS      current
      DESCRIPTION "Average operation dispatch time for the current measurement period.  Dispatch time refers to the time for WebLogic Server to process the invocation.  The measurement period typically starts when WebLogic Server is first started. "
      ::= { wseeClientOperationRuntimeEntry 20  }
   
   
   wseeClientOperationRuntimeLastError OBJECT-TYPE
      SYNTAX      OCTET STRING
      MAX-ACCESS  read-only
      STATUS      current
      DESCRIPTION "Last error that occurred processing a request. "
      ::= { wseeClientOperationRuntimeEntry 21  }
   
   
   wseeClientOperationRuntimeExecutionTimeLow OBJECT-TYPE
      SYNTAX      Counter64
      MAX-ACCESS  read-only
      STATUS      current
      DESCRIPTION "Shortest operation execution time. "
      ::= { wseeClientOperationRuntimeEntry 22  }
   
   
   wseeClientOperationRuntimeName OBJECT-TYPE
      SYNTAX      OCTET STRING
      MAX-ACCESS  read-only
      STATUS      current
      DESCRIPTION "The name of this configuration. WebLogic Server uses an MBean to implement and persist the configuration. "
      ::= { wseeClientOperationRuntimeEntry 23  }
   
   
   wseeClientOperationRuntimeLastInvocationTime OBJECT-TYPE
      SYNTAX      Counter64
      MAX-ACCESS  read-only
      STATUS      current
      DESCRIPTION "Time of the last operation request to be sent or received (or 0 if no requests have been sent or received). "
      ::= { wseeClientOperationRuntimeEntry 24  }
   
   
   wseeClientOperationRuntimeExecutionTimeTotal OBJECT-TYPE
      SYNTAX      Counter64
      MAX-ACCESS  read-only
      STATUS      current
      DESCRIPTION "Total time for all operation executions. "
      ::= { wseeClientOperationRuntimeEntry 25  }
   
   
   wseeClientOperationRuntimeResponseTimeHigh OBJECT-TYPE
      SYNTAX      Counter64
      MAX-ACCESS  read-only
      STATUS      current
      DESCRIPTION "Longest response time from the responses generated from operation invocations. "
      ::= { wseeClientOperationRuntimeEntry 26  }
   
   
   wseeClientOperationRuntimeLastErrorTime OBJECT-TYPE
      SYNTAX      Counter64
      MAX-ACCESS  read-only
      STATUS      current
      DESCRIPTION "Time on WebLogic Server of the last error for a request (sending or receiving) was detected expressed as the number of milliseconds since midnight, January 1, 1970 UTC. "
      ::= { wseeClientOperationRuntimeEntry 27  }
   
   
   wseeClientPortRuntimeTable OBJECT-TYPE
      SYNTAX      SEQUENCE OF WseeClientPortRuntimeEntry
      MAX-ACCESS  not-accessible
      STATUS      current
      DESCRIPTION "Describes the state of a particular Web Service port.   "
      ::= { wls 1690  }
      
   
   wseeClientPortRuntimeEntry OBJECT-TYPE
      SYNTAX      WseeClientPortRuntimeEntry
      MAX-ACCESS  not-accessible
      STATUS      current
      DESCRIPTION "Generated SNMP Table Entry."
      INDEX { wseeClientPortRuntimeIndex}
      ::= { wseeClientPortRuntimeTable 1 }
      
   WseeClientPortRuntimeEntry ::=
      SEQUENCE
      {
         wseeClientPortRuntimeIndex OCTET STRING,
         wseeClientPortRuntimeObjectName OCTET STRING,
         wseeClientPortRuntimeType OCTET STRING,
         wseeClientPortRuntimeTotalFaults Integer32,
         wseeClientPortRuntimePolicyFaults Integer32,
         wseeClientPortRuntimePortName OCTET STRING,
         wseeClientPortRuntimeName OCTET STRING,
         wseeClientPortRuntimeTransportProtocolType OCTET STRING,
         wseeClientPortRuntimeStartTime Counter64,
         wseeClientPortRuntimePoolTotalPooledClientTakeCount INTEGER,
         wseeClientPortRuntimePoolTakenCount INTEGER,
         wseeClientPortRuntimePoolTotalConversationalClientTakeCount INTEGER,
         wseeClientPortRuntimeTotalSecurityFaults INTEGER,
         wseeClientPortRuntimePoolCapacity INTEGER,
         wseeClientPortRuntimePoolTotalSimpleClientCreateCount INTEGER,
         wseeClientPortRuntimePoolFreeCount INTEGER
      }
      
   
   wseeClientPortRuntimeIndex OBJECT-TYPE
      SYNTAX      OCTET STRING
      MAX-ACCESS  not-accessible
      STATUS      current
      DESCRIPTION "Index column"
      ::= { wseeClientPortRuntimeEntry 1  }
   
   
   wseeClientPortRuntimeObjectName OBJECT-TYPE
      SYNTAX      OCTET STRING
      MAX-ACCESS  read-only
      STATUS      current
      DESCRIPTION "ObjectName column"
      ::= { wseeClientPortRuntimeEntry 2  }
   
   
   wseeClientPortRuntimeType OBJECT-TYPE
      SYNTAX      OCTET STRING
      MAX-ACCESS  read-only
      STATUS      current
      DESCRIPTION "Returns the type of the MBean. "
      ::= { wseeClientPortRuntimeEntry 3  }
   
   
   wseeClientPortRuntimeTotalFaults OBJECT-TYPE
      SYNTAX      Integer32
      MAX-ACCESS  read-only
      STATUS      current
      DESCRIPTION "Total number of security faults and violations. "
      ::= { wseeClientPortRuntimeEntry 4  }
   
   
   wseeClientPortRuntimePolicyFaults OBJECT-TYPE
      SYNTAX      Integer32
      MAX-ACCESS  read-only
      STATUS      current
      DESCRIPTION "Total number of policy faults. "
      ::= { wseeClientPortRuntimeEntry 5  }
   
   
   wseeClientPortRuntimePortName OBJECT-TYPE
      SYNTAX      OCTET STRING
      MAX-ACCESS  read-only
      STATUS      current
      DESCRIPTION "Name of this port.  This attribute corresponds to the 'name' attribute of the 'port' element in the WSDL that describes the Web service.  Programmers specify the name of the port using the portName attribute of the &#64;WLXXXTransport annotation, where XXX refers to the type of transport (HTTP, HTTPS, or JMS).  Programmers can also use the WLXXXTransport child element of the jwsc Ant task to specify this attribute. "
      ::= { wseeClientPortRuntimeEntry 6  }
   
   
   wseeClientPortRuntimeName OBJECT-TYPE
      SYNTAX      OCTET STRING
      MAX-ACCESS  read-only
      STATUS      current
      DESCRIPTION "The name of this configuration. WebLogic Server uses an MBean to implement and persist the configuration. "
      ::= { wseeClientPortRuntimeEntry 7  }
   
   
   wseeClientPortRuntimeTransportProtocolType OBJECT-TYPE
      SYNTAX      OCTET STRING
      MAX-ACCESS  read-only
      STATUS      current
      DESCRIPTION "Transport protocol used to invoke this Web service, such as HTTP, HTTPS, or JMS.  This attribute determines the transport that is published in the endpoint address section of the WSDL of the Web Service. Programmers specify the transport by the type of &#64;WLXXXTransport JWS annotation they specify, where XXX refers to the type of transport (HTTP, HTTPS, or JMS).  Programmers can also use the WLXXXTransport child element of the jwsc Ant task to specify this attribute. "
      ::= { wseeClientPortRuntimeEntry 8  }
   
   
   wseeClientPortRuntimeStartTime OBJECT-TYPE
      SYNTAX      Counter64
      MAX-ACCESS  read-only
      STATUS      current
      DESCRIPTION "Date and time that the Web service endpoint started. "
      ::= { wseeClientPortRuntimeEntry 9  }
   
   
   wseeClientPortRuntimePoolTotalPooledClientTakeCount OBJECT-TYPE
      SYNTAX      INTEGER
      MAX-ACCESS  read-only
      STATUS      current
      DESCRIPTION "Total number of client instances that have been taken from the pool over the lifetime of the pool for this client port runtime, or 0 if no pool has been initialized for it. Note, this value can exceed the capacity of the pool because client instances are released back into the pool to be taken again later. "
      ::= { wseeClientPortRuntimeEntry 10  }
   
   
   wseeClientPortRuntimePoolTakenCount OBJECT-TYPE
      SYNTAX      INTEGER
      MAX-ACCESS  read-only
      STATUS      current
      DESCRIPTION "Number of taken client instances in the pool for this client port runtime, or 0 if no pool has been initialized for it. "
      ::= { wseeClientPortRuntimeEntry 11  }
   
   
   wseeClientPortRuntimePoolTotalConversationalClientTakeCount OBJECT-TYPE
      SYNTAX      INTEGER
      MAX-ACCESS  read-only
      STATUS      current
      DESCRIPTION "Total number of conversational client instances that have been taken from the pool over the lifetime of the pool for this client port runtime, or 0 if no pool has been initialized for it. Note, conversational client instances are managed separately from simple pooled client instances, and are not subject to the capacity setting for this pool. Thus, using conversational client instances won't increase the values you see for getPoolFreeCount() or getPoolTakenCount(). "
      ::= { wseeClientPortRuntimeEntry 12  }
   
   
   wseeClientPortRuntimeTotalSecurityFaults OBJECT-TYPE
      SYNTAX      INTEGER
      MAX-ACCESS  read-only
      STATUS      current
      DESCRIPTION "Total number of security faults and violations. "
      ::= { wseeClientPortRuntimeEntry 13  }
   
   
   wseeClientPortRuntimePoolCapacity OBJECT-TYPE
      SYNTAX      INTEGER
      MAX-ACCESS  read-only
      STATUS      current
      DESCRIPTION "Capacity of the pool of client instances for this client port runtime, or 0 if no pool has been initialized for it. "
      ::= { wseeClientPortRuntimeEntry 14  }
   
   
   wseeClientPortRuntimePoolTotalSimpleClientCreateCount OBJECT-TYPE
      SYNTAX      INTEGER
      MAX-ACCESS  read-only
      STATUS      current
      DESCRIPTION "Total number of simple (non-pooled, non-conversational) client instances that have been created over the life of this client port runtime (i.e. using the same client identity and port name). Note, if a non-zero capacity is given for the pool associated with the client identity for this client port runtime, then all client instances retrieved for it will come from the pool, and the simple client create count will be 0. "
      ::= { wseeClientPortRuntimeEntry 15  }
   
   
   wseeClientPortRuntimePoolFreeCount OBJECT-TYPE
      SYNTAX      INTEGER
      MAX-ACCESS  read-only
      STATUS      current
      DESCRIPTION "Number of free client instances in the pool for this client port runtime, or 0 if no pool has been initialized for it. "
      ::= { wseeClientPortRuntimeEntry 16  }
   
   
   wseeClientRuntimeTable OBJECT-TYPE
      SYNTAX      SEQUENCE OF WseeClientRuntimeEntry
      MAX-ACCESS  not-accessible
      STATUS      current
      DESCRIPTION "Describes the state of a particular Web Service client (Port/Dispatch instance that includes a ClientIdentityFeature).   "
      ::= { wls 1695  }
      
   
   wseeClientRuntimeEntry OBJECT-TYPE
      SYNTAX      WseeClientRuntimeEntry
      MAX-ACCESS  not-accessible
      STATUS      current
      DESCRIPTION "Generated SNMP Table Entry."
      INDEX { wseeClientRuntimeIndex}
      ::= { wseeClientRuntimeTable 1 }
      
   WseeClientRuntimeEntry ::=
      SEQUENCE
      {
         wseeClientRuntimeIndex OCTET STRING,
         wseeClientRuntimeObjectName OCTET STRING,
         wseeClientRuntimeType OCTET STRING,
         wseeClientRuntimeClientID OCTET STRING,
         wseeClientRuntimeName OCTET STRING
      }
      
   
   wseeClientRuntimeIndex OBJECT-TYPE
      SYNTAX      OCTET STRING
      MAX-ACCESS  not-accessible
      STATUS      current
      DESCRIPTION "Index column"
      ::= { wseeClientRuntimeEntry 1  }
   
   
   wseeClientRuntimeObjectName OBJECT-TYPE
      SYNTAX      OCTET STRING
      MAX-ACCESS  read-only
      STATUS      current
      DESCRIPTION "ObjectName column"
      ::= { wseeClientRuntimeEntry 2  }
   
   
   wseeClientRuntimeType OBJECT-TYPE
      SYNTAX      OCTET STRING
      MAX-ACCESS  read-only
      STATUS      current
      DESCRIPTION "Returns the type of the MBean. "
      ::= { wseeClientRuntimeEntry 3  }
   
   
   wseeClientRuntimeClientID OBJECT-TYPE
      SYNTAX      OCTET STRING
      MAX-ACCESS  read-only
      STATUS      current
      DESCRIPTION "Gets the client ID for this client. "
      ::= { wseeClientRuntimeEntry 4  }
   
   
   wseeClientRuntimeName OBJECT-TYPE
      SYNTAX      OCTET STRING
      MAX-ACCESS  read-only
      STATUS      current
      DESCRIPTION "The name of this configuration. WebLogic Server uses an MBean to implement and persist the configuration. "
      ::= { wseeClientRuntimeEntry 5  }
   
   
   wseeClusterFrontEndRuntimeTable OBJECT-TYPE
      SYNTAX      SEQUENCE OF WseeClusterFrontEndRuntimeEntry
      MAX-ACCESS  not-accessible
      STATUS      current
      DESCRIPTION "Encapsulates runtime information about a particular Web Service cluster front-end instance. This MBean represents a cluster front-end instance (e.g. HttpClusterServlet) that contains a cluster routing function.  "
      ::= { wls 1700  }
      
   
   wseeClusterFrontEndRuntimeEntry OBJECT-TYPE
      SYNTAX      WseeClusterFrontEndRuntimeEntry
      MAX-ACCESS  not-accessible
      STATUS      current
      DESCRIPTION "Generated SNMP Table Entry."
      INDEX { wseeClusterFrontEndRuntimeIndex}
      ::= { wseeClusterFrontEndRuntimeTable 1 }
      
   WseeClusterFrontEndRuntimeEntry ::=
      SEQUENCE
      {
         wseeClusterFrontEndRuntimeIndex OCTET STRING,
         wseeClusterFrontEndRuntimeObjectName OCTET STRING,
         wseeClusterFrontEndRuntimeType OCTET STRING,
         wseeClusterFrontEndRuntimeName OCTET STRING
      }
      
   
   wseeClusterFrontEndRuntimeIndex OBJECT-TYPE
      SYNTAX      OCTET STRING
      MAX-ACCESS  not-accessible
      STATUS      current
      DESCRIPTION "Index column"
      ::= { wseeClusterFrontEndRuntimeEntry 1  }
   
   
   wseeClusterFrontEndRuntimeObjectName OBJECT-TYPE
      SYNTAX      OCTET STRING
      MAX-ACCESS  read-only
      STATUS      current
      DESCRIPTION "ObjectName column"
      ::= { wseeClusterFrontEndRuntimeEntry 2  }
   
   
   wseeClusterFrontEndRuntimeType OBJECT-TYPE
      SYNTAX      OCTET STRING
      MAX-ACCESS  read-only
      STATUS      current
      DESCRIPTION "Returns the type of the MBean. "
      ::= { wseeClusterFrontEndRuntimeEntry 3  }
   
   
   wseeClusterFrontEndRuntimeName OBJECT-TYPE
      SYNTAX      OCTET STRING
      MAX-ACCESS  read-only
      STATUS      current
      DESCRIPTION "The name of this configuration. WebLogic Server uses an MBean to implement and persist the configuration. "
      ::= { wseeClusterFrontEndRuntimeEntry 4  }
   
   
   wseeClusterRoutingRuntimeTable OBJECT-TYPE
      SYNTAX      SEQUENCE OF WseeClusterRoutingRuntimeEntry
      MAX-ACCESS  not-accessible
      STATUS      current
      DESCRIPTION "Encapsulates runtime information about a particular Web Service cluster routing instance (whether it be a front-end router or an in-place router). "
      ::= { wls 1705  }
      
   
   wseeClusterRoutingRuntimeEntry OBJECT-TYPE
      SYNTAX      WseeClusterRoutingRuntimeEntry
      MAX-ACCESS  not-accessible
      STATUS      current
      DESCRIPTION "Generated SNMP Table Entry."
      INDEX { wseeClusterRoutingRuntimeIndex}
      ::= { wseeClusterRoutingRuntimeTable 1 }
      
   WseeClusterRoutingRuntimeEntry ::=
      SEQUENCE
      {
         wseeClusterRoutingRuntimeIndex OCTET STRING,
         wseeClusterRoutingRuntimeObjectName OCTET STRING,
         wseeClusterRoutingRuntimeType OCTET STRING,
         wseeClusterRoutingRuntimeLastRoutingFailure OCTET STRING,
         wseeClusterRoutingRuntimeRoutedRequestCount Integer32,
         wseeClusterRoutingRuntimeName OCTET STRING,
         wseeClusterRoutingRuntimeRoutedResponseCount Integer32,
         wseeClusterRoutingRuntimeRoutingFailureCount Integer32,
         wseeClusterRoutingRuntimeRequestCount Integer32,
         wseeClusterRoutingRuntimeResponseCount Integer32,
         wseeClusterRoutingRuntimeLastRoutingFailureTime Counter64
      }
      
   
   wseeClusterRoutingRuntimeIndex OBJECT-TYPE
      SYNTAX      OCTET STRING
      MAX-ACCESS  not-accessible
      STATUS      current
      DESCRIPTION "Index column"
      ::= { wseeClusterRoutingRuntimeEntry 1  }
   
   
   wseeClusterRoutingRuntimeObjectName OBJECT-TYPE
      SYNTAX      OCTET STRING
      MAX-ACCESS  read-only
      STATUS      current
      DESCRIPTION "ObjectName column"
      ::= { wseeClusterRoutingRuntimeEntry 2  }
   
   
   wseeClusterRoutingRuntimeType OBJECT-TYPE
      SYNTAX      OCTET STRING
      MAX-ACCESS  read-only
      STATUS      current
      DESCRIPTION "Returns the type of the MBean. "
      ::= { wseeClusterRoutingRuntimeEntry 3  }
   
   
   wseeClusterRoutingRuntimeLastRoutingFailure OBJECT-TYPE
      SYNTAX      OCTET STRING
      MAX-ACCESS  read-only
      STATUS      current
      DESCRIPTION "The exception that caused the last routing failure, or null if no failures have occurred. "
      ::= { wseeClusterRoutingRuntimeEntry 4  }
   
   
   wseeClusterRoutingRuntimeRoutedRequestCount OBJECT-TYPE
      SYNTAX      Integer32
      MAX-ACCESS  read-only
      STATUS      current
      DESCRIPTION "The number of requests that were routed to a specific server instance via routing information in the request (not just load balanced) since the server started. "
      ::= { wseeClusterRoutingRuntimeEntry 5  }
   
   
   wseeClusterRoutingRuntimeName OBJECT-TYPE
      SYNTAX      OCTET STRING
      MAX-ACCESS  read-only
      STATUS      current
      DESCRIPTION "The name of this configuration. WebLogic Server uses an MBean to implement and persist the configuration. "
      ::= { wseeClusterRoutingRuntimeEntry 6  }
   
   
   wseeClusterRoutingRuntimeRoutedResponseCount OBJECT-TYPE
      SYNTAX      Integer32
      MAX-ACCESS  read-only
      STATUS      current
      DESCRIPTION "The number of responses that were routed to a specific server instance via routing information in the response (not just load balanced) since the server started. "
      ::= { wseeClusterRoutingRuntimeEntry 7  }
   
   
   wseeClusterRoutingRuntimeRoutingFailureCount OBJECT-TYPE
      SYNTAX      Integer32
      MAX-ACCESS  read-only
      STATUS      current
      DESCRIPTION "The number of times a message failed to be routed, since the server started. "
      ::= { wseeClusterRoutingRuntimeEntry 8  }
   
   
   wseeClusterRoutingRuntimeRequestCount OBJECT-TYPE
      SYNTAX      Integer32
      MAX-ACCESS  read-only
      STATUS      current
      DESCRIPTION "The number of requests (messages with no RelatesTo header) that have come through this front-end since the server started. "
      ::= { wseeClusterRoutingRuntimeEntry 9  }
   
   
   wseeClusterRoutingRuntimeResponseCount OBJECT-TYPE
      SYNTAX      Integer32
      MAX-ACCESS  read-only
      STATUS      current
      DESCRIPTION "The number of responses (messages with a RelatesTo header) that have come through this front-end since the server started. "
      ::= { wseeClusterRoutingRuntimeEntry 10  }
   
   
   wseeClusterRoutingRuntimeLastRoutingFailureTime OBJECT-TYPE
      SYNTAX      Counter64
      MAX-ACCESS  read-only
      STATUS      current
      DESCRIPTION "The time (in milliseconds since epoch) of the last routing failure (or 0 if no failures have occurred). "
      ::= { wseeClusterRoutingRuntimeEntry 11  }
   
   
   wseeMcRuntimeTable OBJECT-TYPE
      SYNTAX      SEQUENCE OF WseeMcRuntimeEntry
      MAX-ACCESS  not-accessible
      STATUS      current
      DESCRIPTION "Describes the state of MakeConnection pending message lists "
      ::= { wls 1710  }
      
   
   wseeMcRuntimeEntry OBJECT-TYPE
      SYNTAX      WseeMcRuntimeEntry
      MAX-ACCESS  not-accessible
      STATUS      current
      DESCRIPTION "Generated SNMP Table Entry."
      INDEX { wseeMcRuntimeIndex}
      ::= { wseeMcRuntimeTable 1 }
      
   WseeMcRuntimeEntry ::=
      SEQUENCE
      {
         wseeMcRuntimeIndex   OCTET STRING,
         wseeMcRuntimeObjectName OCTET STRING,
         wseeMcRuntimeType    OCTET STRING,
         wseeMcRuntimeName    OCTET STRING
      }
      
   
   wseeMcRuntimeIndex OBJECT-TYPE
      SYNTAX      OCTET STRING
      MAX-ACCESS  not-accessible
      STATUS      current
      DESCRIPTION "Index column"
      ::= { wseeMcRuntimeEntry 1  }
   
   
   wseeMcRuntimeObjectName OBJECT-TYPE
      SYNTAX      OCTET STRING
      MAX-ACCESS  read-only
      STATUS      current
      DESCRIPTION "ObjectName column"
      ::= { wseeMcRuntimeEntry 2  }
   
   
   wseeMcRuntimeType OBJECT-TYPE
      SYNTAX      OCTET STRING
      MAX-ACCESS  read-only
      STATUS      current
      DESCRIPTION "Returns the type of the MBean. "
      ::= { wseeMcRuntimeEntry 3  }
   
   
   wseeMcRuntimeName OBJECT-TYPE
      SYNTAX      OCTET STRING
      MAX-ACCESS  read-only
      STATUS      current
      DESCRIPTION "The name of this configuration. WebLogic Server uses an MBean to implement and persist the configuration. "
      ::= { wseeMcRuntimeEntry 4  }
   
   
   wseeOperationConfigurationRuntimeTable OBJECT-TYPE
      SYNTAX      SEQUENCE OF WseeOperationConfigurationRuntimeEntry
      MAX-ACCESS  not-accessible
      STATUS      current
      DESCRIPTION " Encapsulates runtime information about a particular operation. The subject name attribute of this MBean will be the value of the local part of operation QName.  "
      ::= { wls 1715  }
      
   
   wseeOperationConfigurationRuntimeEntry OBJECT-TYPE
      SYNTAX      WseeOperationConfigurationRuntimeEntry
      MAX-ACCESS  not-accessible
      STATUS      current
      DESCRIPTION "Generated SNMP Table Entry."
      INDEX { wseeOperationConfigurationRuntimeIndex}
      ::= { wseeOperationConfigurationRuntimeTable 1 }
      
   WseeOperationConfigurationRuntimeEntry ::=
      SEQUENCE
      {
         wseeOperationConfigurationRuntimeIndex OCTET STRING,
         wseeOperationConfigurationRuntimeObjectName OCTET STRING,
         wseeOperationConfigurationRuntimePolicySubjectType OCTET STRING,
         wseeOperationConfigurationRuntimePolicyAttachmentSupport OCTET STRING,
         wseeOperationConfigurationRuntimePolicySubjectResourcePattern OCTET STRING,
         wseeOperationConfigurationRuntimeType OCTET STRING,
         wseeOperationConfigurationRuntimeName OCTET STRING,
         wseeOperationConfigurationRuntimePolicySubjectName OCTET STRING
      }
      
   
   wseeOperationConfigurationRuntimeIndex OBJECT-TYPE
      SYNTAX      OCTET STRING
      MAX-ACCESS  not-accessible
      STATUS      current
      DESCRIPTION "Index column"
      ::= { wseeOperationConfigurationRuntimeEntry 1  }
   
   
   wseeOperationConfigurationRuntimeObjectName OBJECT-TYPE
      SYNTAX      OCTET STRING
      MAX-ACCESS  read-only
      STATUS      current
      DESCRIPTION "ObjectName column"
      ::= { wseeOperationConfigurationRuntimeEntry 2  }
   
   
   wseeOperationConfigurationRuntimePolicySubjectType OBJECT-TYPE
      SYNTAX      OCTET STRING
      MAX-ACCESS  read-only
      STATUS      current
      DESCRIPTION "Get subject type for this operation MBean. "
      ::= { wseeOperationConfigurationRuntimeEntry 3  }
   
   
   wseeOperationConfigurationRuntimePolicyAttachmentSupport OBJECT-TYPE
      SYNTAX      OCTET STRING
      MAX-ACCESS  read-only
      STATUS      current
      DESCRIPTION "Get attachment support for this operation MBean. "
      ::= { wseeOperationConfigurationRuntimeEntry 4  }
   
   
   wseeOperationConfigurationRuntimePolicySubjectResourcePattern OBJECT-TYPE
      SYNTAX      OCTET STRING
      MAX-ACCESS  read-only
      STATUS      current
      DESCRIPTION "The policySubject parameter must uniquely identify what application, module, service, and port (port or operation for WLS Policy) is targeted. The syntax currently used by JRF for Java EE Webservice Endpoints will be used: /{domain}/{instance}/{app}/WEBs|EJBs/{module }/WEBSERVICECLIENTs/{service-ref-name}/PORTs/{port}/OPERATIONs/{operation} "
      ::= { wseeOperationConfigurationRuntimeEntry 5  }
   
   
   wseeOperationConfigurationRuntimeType OBJECT-TYPE
      SYNTAX      OCTET STRING
      MAX-ACCESS  read-only
      STATUS      current
      DESCRIPTION "Returns the type of the MBean. "
      ::= { wseeOperationConfigurationRuntimeEntry 6  }
   
   
   wseeOperationConfigurationRuntimeName OBJECT-TYPE
      SYNTAX      OCTET STRING
      MAX-ACCESS  read-only
      STATUS      current
      DESCRIPTION "The name of this configuration. WebLogic Server uses an MBean to implement and persist the configuration. "
      ::= { wseeOperationConfigurationRuntimeEntry 7  }
   
   
   wseeOperationConfigurationRuntimePolicySubjectName OBJECT-TYPE
      SYNTAX      OCTET STRING
      MAX-ACCESS  read-only
      STATUS      current
      DESCRIPTION "Get subject name for this operation MBean. "
      ::= { wseeOperationConfigurationRuntimeEntry 8  }
   
   
   wseePolicySubjectManagerRuntimeTable OBJECT-TYPE
      SYNTAX      SEQUENCE OF WseePolicySubjectManagerRuntimeEntry
      MAX-ACCESS  not-accessible
      STATUS      current
      DESCRIPTION " "
      ::= { wls 1720  }
      
   
   wseePolicySubjectManagerRuntimeEntry OBJECT-TYPE
      SYNTAX      WseePolicySubjectManagerRuntimeEntry
      MAX-ACCESS  not-accessible
      STATUS      current
      DESCRIPTION "Generated SNMP Table Entry."
      INDEX { wseePolicySubjectManagerRuntimeIndex}
      ::= { wseePolicySubjectManagerRuntimeTable 1 }
      
   WseePolicySubjectManagerRuntimeEntry ::=
      SEQUENCE
      {
         wseePolicySubjectManagerRuntimeIndex OCTET STRING,
         wseePolicySubjectManagerRuntimeObjectName OCTET STRING,
         wseePolicySubjectManagerRuntimeType OCTET STRING,
         wseePolicySubjectManagerRuntimeName OCTET STRING
      }
      
   
   wseePolicySubjectManagerRuntimeIndex OBJECT-TYPE
      SYNTAX      OCTET STRING
      MAX-ACCESS  not-accessible
      STATUS      current
      DESCRIPTION "Index column"
      ::= { wseePolicySubjectManagerRuntimeEntry 1  }
   
   
   wseePolicySubjectManagerRuntimeObjectName OBJECT-TYPE
      SYNTAX      OCTET STRING
      MAX-ACCESS  read-only
      STATUS      current
      DESCRIPTION "ObjectName column"
      ::= { wseePolicySubjectManagerRuntimeEntry 2  }
   
   
   wseePolicySubjectManagerRuntimeType OBJECT-TYPE
      SYNTAX      OCTET STRING
      MAX-ACCESS  read-only
      STATUS      current
      DESCRIPTION "Returns the type of the MBean. "
      ::= { wseePolicySubjectManagerRuntimeEntry 3  }
   
   
   wseePolicySubjectManagerRuntimeName OBJECT-TYPE
      SYNTAX      OCTET STRING
      MAX-ACCESS  read-only
      STATUS      current
      DESCRIPTION "The name of this configuration. WebLogic Server uses an MBean to implement and persist the configuration. "
      ::= { wseePolicySubjectManagerRuntimeEntry 4  }
   
   
   wseePortPolicyRuntimeTable OBJECT-TYPE
      SYNTAX      SEQUENCE OF WseePortPolicyRuntimeEntry
      MAX-ACCESS  not-accessible
      STATUS      current
      DESCRIPTION "Describes the Web service security policy state of a particular Web service port. "
      ::= { wls 1725  }
      
   
   wseePortPolicyRuntimeEntry OBJECT-TYPE
      SYNTAX      WseePortPolicyRuntimeEntry
      MAX-ACCESS  not-accessible
      STATUS      current
      DESCRIPTION "Generated SNMP Table Entry."
      INDEX { wseePortPolicyRuntimeIndex}
      ::= { wseePortPolicyRuntimeTable 1 }
      
   WseePortPolicyRuntimeEntry ::=
      SEQUENCE
      {
         wseePortPolicyRuntimeIndex OCTET STRING,
         wseePortPolicyRuntimeObjectName OCTET STRING,
         wseePortPolicyRuntimeTotalViolations Integer32,
         wseePortPolicyRuntimeType OCTET STRING,
         wseePortPolicyRuntimeTotalFaults Integer32,
         wseePortPolicyRuntimeConfidentialityViolations Integer32,
         wseePortPolicyRuntimeAuthenticationViolations Integer32,
         wseePortPolicyRuntimePolicyFaults Integer32,
         wseePortPolicyRuntimeIntegrityViolations Integer32,
         wseePortPolicyRuntimeAuthenticationSuccesses Integer32,
         wseePortPolicyRuntimeName OCTET STRING,
         wseePortPolicyRuntimeAuthorizationSuccesses Integer32,
         wseePortPolicyRuntimeConfidentialitySuccesses Integer32,
         wseePortPolicyRuntimeAuthorizationViolations Integer32,
         wseePortPolicyRuntimeIntegritySuccesses Integer32,
         wseePortPolicyRuntimeTotalSecurityFaults INTEGER
      }
      
   
   wseePortPolicyRuntimeIndex OBJECT-TYPE
      SYNTAX      OCTET STRING
      MAX-ACCESS  not-accessible
      STATUS      current
      DESCRIPTION "Index column"
      ::= { wseePortPolicyRuntimeEntry 1  }
   
   
   wseePortPolicyRuntimeObjectName OBJECT-TYPE
      SYNTAX      OCTET STRING
      MAX-ACCESS  read-only
      STATUS      current
      DESCRIPTION "ObjectName column"
      ::= { wseePortPolicyRuntimeEntry 2  }
   
   
   wseePortPolicyRuntimeTotalViolations OBJECT-TYPE
      SYNTAX      Integer32
      MAX-ACCESS  read-only
      STATUS      current
      DESCRIPTION " Total number of authentication, integrity, and confidentialy violations. Both outgoing and incoming message processing can add to the violation count.  "
      ::= { wseePortPolicyRuntimeEntry 3  }
   
   
   wseePortPolicyRuntimeType OBJECT-TYPE
      SYNTAX      OCTET STRING
      MAX-ACCESS  read-only
      STATUS      current
      DESCRIPTION "Returns the type of the MBean. "
      ::= { wseePortPolicyRuntimeEntry 4  }
   
   
   wseePortPolicyRuntimeTotalFaults OBJECT-TYPE
      SYNTAX      Integer32
      MAX-ACCESS  read-only
      STATUS      current
      DESCRIPTION " Total number of security faults and violations generated by this port.  "
      ::= { wseePortPolicyRuntimeEntry 5  }
   
   
   wseePortPolicyRuntimeConfidentialityViolations OBJECT-TYPE
      SYNTAX      Integer32
      MAX-ACCESS  read-only
      STATUS      current
      DESCRIPTION " Total number of confidentiality violations generated for this port. Both outgoing and incoming message processing can add to the violation count.  "
      ::= { wseePortPolicyRuntimeEntry 6  }
   
   
   wseePortPolicyRuntimeAuthenticationViolations OBJECT-TYPE
      SYNTAX      Integer32
      MAX-ACCESS  read-only
      STATUS      current
      DESCRIPTION " Total number of authentication violations generated for this port. Only incoming message processing can add to the violation count.  "
      ::= { wseePortPolicyRuntimeEntry 7  }
   
   
   wseePortPolicyRuntimePolicyFaults OBJECT-TYPE
      SYNTAX      Integer32
      MAX-ACCESS  read-only
      STATUS      current
      DESCRIPTION " Total number of policy faults generated for this port.  "
      ::= { wseePortPolicyRuntimeEntry 8  }
   
   
   wseePortPolicyRuntimeIntegrityViolations OBJECT-TYPE
      SYNTAX      Integer32
      MAX-ACCESS  read-only
      STATUS      current
      DESCRIPTION " Total number of integrity violations generated for this port. Both outgoing and incoming message processing can add to the violation count.  "
      ::= { wseePortPolicyRuntimeEntry 9  }
   
   
   wseePortPolicyRuntimeAuthenticationSuccesses OBJECT-TYPE
      SYNTAX      Integer32
      MAX-ACCESS  read-only
      STATUS      current
      DESCRIPTION " Total number of authentication successes detected for this port. Only incoming message processing can add to the success count.  "
      ::= { wseePortPolicyRuntimeEntry 10  }
   
   
   wseePortPolicyRuntimeName OBJECT-TYPE
      SYNTAX      OCTET STRING
      MAX-ACCESS  read-only
      STATUS      current
      DESCRIPTION "The name of this configuration. WebLogic Server uses an MBean to implement and persist the configuration. "
      ::= { wseePortPolicyRuntimeEntry 11  }
   
   
   wseePortPolicyRuntimeAuthorizationSuccesses OBJECT-TYPE
      SYNTAX      Integer32
      MAX-ACCESS  read-only
      STATUS      current
      DESCRIPTION " Total number of authorization successes detected for this port.  "
      ::= { wseePortPolicyRuntimeEntry 12  }
   
   
   wseePortPolicyRuntimeConfidentialitySuccesses OBJECT-TYPE
      SYNTAX      Integer32
      MAX-ACCESS  read-only
      STATUS      current
      DESCRIPTION " Total number of confidentiality successes generated for this port. Both outgoing and incoming message processing can add to the success count.  "
      ::= { wseePortPolicyRuntimeEntry 13  }
   
   
   wseePortPolicyRuntimeAuthorizationViolations OBJECT-TYPE
      SYNTAX      Integer32
      MAX-ACCESS  read-only
      STATUS      current
      DESCRIPTION " Total number of authorization violations generated for this port.  "
      ::= { wseePortPolicyRuntimeEntry 14  }
   
   
   wseePortPolicyRuntimeIntegritySuccesses OBJECT-TYPE
      SYNTAX      Integer32
      MAX-ACCESS  read-only
      STATUS      current
      DESCRIPTION " Total number of integrity successes generated for this port. Both outgoing and incoming message processing can add to the success count.  "
      ::= { wseePortPolicyRuntimeEntry 15  }
   
   
   wseePortPolicyRuntimeTotalSecurityFaults OBJECT-TYPE
      SYNTAX      INTEGER
      MAX-ACCESS  read-only
      STATUS      current
      DESCRIPTION " Total number of security faults and violations generated for this port.  "
      ::= { wseePortPolicyRuntimeEntry 16  }
   
   
   wseeV2RuntimeTable OBJECT-TYPE
      SYNTAX      SEQUENCE OF WseeV2RuntimeEntry
      MAX-ACCESS  not-accessible
      STATUS      current
      DESCRIPTION "Encapsulates runtime information about a particular Web Service. The name attribute of this MBean will be the value of the webservice-description-name element in webservices.xml "
      ::= { wls 1730  }
      
   
   wseeV2RuntimeEntry OBJECT-TYPE
      SYNTAX      WseeV2RuntimeEntry
      MAX-ACCESS  not-accessible
      STATUS      current
      DESCRIPTION "Generated SNMP Table Entry."
      INDEX { wseeV2RuntimeIndex}
      ::= { wseeV2RuntimeTable 1 }
      
   WseeV2RuntimeEntry ::=
      SEQUENCE
      {
         wseeV2RuntimeIndex   OCTET STRING,
         wseeV2RuntimeObjectName OCTET STRING,
         wseeV2RuntimeImplementationType OCTET STRING,
         wseeV2RuntimeType    OCTET STRING,
         wseeV2RuntimeTotalFaults Integer32,
         wseeV2RuntimeWebserviceDescriptionName OCTET STRING,
         wseeV2RuntimePolicyFaults Integer32,
         wseeV2RuntimeName    OCTET STRING,
         wseeV2RuntimeServiceName OCTET STRING,
         wseeV2RuntimeContextPath OCTET STRING,
         wseeV2RuntimeStartTime Counter64,
         wseeV2RuntimeURI     OCTET STRING,
         wseeV2RuntimeTotalSecurityFaults INTEGER
      }
      
   
   wseeV2RuntimeIndex OBJECT-TYPE
      SYNTAX      OCTET STRING
      MAX-ACCESS  not-accessible
      STATUS      current
      DESCRIPTION "Index column"
      ::= { wseeV2RuntimeEntry 1  }
   
   
   wseeV2RuntimeObjectName OBJECT-TYPE
      SYNTAX      OCTET STRING
      MAX-ACCESS  read-only
      STATUS      current
      DESCRIPTION "ObjectName column"
      ::= { wseeV2RuntimeEntry 2  }
   
   
   wseeV2RuntimeImplementationType OBJECT-TYPE
      SYNTAX      OCTET STRING
      MAX-ACCESS  read-only
      STATUS      current
      DESCRIPTION "Specifies the implementation type of this service.  Valid values include: JAX-WS 2.0 JAX-RPC 1.1 "
      ::= { wseeV2RuntimeEntry 3  }
   
   
   wseeV2RuntimeType OBJECT-TYPE
      SYNTAX      OCTET STRING
      MAX-ACCESS  read-only
      STATUS      current
      DESCRIPTION "Returns the type of the MBean. "
      ::= { wseeV2RuntimeEntry 4  }
   
   
   wseeV2RuntimeTotalFaults OBJECT-TYPE
      SYNTAX      Integer32
      MAX-ACCESS  read-only
      STATUS      current
      DESCRIPTION "Total number of faults generated by this endpoint. "
      ::= { wseeV2RuntimeEntry 5  }
   
   
   wseeV2RuntimeWebserviceDescriptionName OBJECT-TYPE
      SYNTAX      OCTET STRING
      MAX-ACCESS  read-only
      STATUS      current
      DESCRIPTION "webservice description name for this webservice "
      ::= { wseeV2RuntimeEntry 6  }
   
   
   wseeV2RuntimePolicyFaults OBJECT-TYPE
      SYNTAX      Integer32
      MAX-ACCESS  read-only
      STATUS      current
      DESCRIPTION "Total number of faults generated by security policy handler. "
      ::= { wseeV2RuntimeEntry 7  }
   
   
   wseeV2RuntimeName OBJECT-TYPE
      SYNTAX      OCTET STRING
      MAX-ACCESS  read-only
      STATUS      current
      DESCRIPTION "The name of this configuration. WebLogic Server uses an MBean to implement and persist the configuration. "
      ::= { wseeV2RuntimeEntry 8  }
   
   
   wseeV2RuntimeServiceName OBJECT-TYPE
      SYNTAX      OCTET STRING
      MAX-ACCESS  read-only
      STATUS      current
      DESCRIPTION "Specifies the qualified name of this Web service.  This attribute is calculated based on actual MBean type and of the form:  WseeRuntimeMBean: &lt;app name&gt;#&lt;app version&gt;!&lt;service name&gt;. WseeV2RuntimeMBean: &lt;app name&gt;#&lt;app version&gt;!&lt;web WAR name or EJB JAR name&gt;!&lt;service name&gt;. "
      ::= { wseeV2RuntimeEntry 9  }
   
   
   wseeV2RuntimeContextPath OBJECT-TYPE
      SYNTAX      OCTET STRING
      MAX-ACCESS  read-only
      STATUS      current
      DESCRIPTION "Specifies the context path of this web service. This attribute corresponds to the initial part of the endpoint address in the WSDL that describes the Web Service.  It is specified at development time in JAX-RPC services using the contextPath attribute of the &#64;WLXXXTransport JWS annotation, where XXX refers to the transport, such as HTTP, HTTPS, or JMS. For JAX-WS services the context path is set either during compilation of the service, or by the module (web or EJB) hosting the service. "
      ::= { wseeV2RuntimeEntry 10  }
   
   
   wseeV2RuntimeStartTime OBJECT-TYPE
      SYNTAX      Counter64
      MAX-ACCESS  read-only
      STATUS      current
      DESCRIPTION "Date and time that the Web service starts. "
      ::= { wseeV2RuntimeEntry 11  }
   
   
   wseeV2RuntimeURI OBJECT-TYPE
      SYNTAX      OCTET STRING
      MAX-ACCESS  read-only
      STATUS      current
      DESCRIPTION "Specifies the URI of this Web service.  This attribute corresponds to the final part of the endpoint address in the WSDL that describes the Web Services. It is specified at development time for JAX-RPC services using the serviceURI attribute of the &#64;WLXXXTransport JWS annotation, where XXX refers to the transport, such as HTTP, HTTPS, or JMS. For JAX-WS services, this can be set during compilation. "
      ::= { wseeV2RuntimeEntry 12  }
   
   
   wseeV2RuntimeTotalSecurityFaults OBJECT-TYPE
      SYNTAX      INTEGER
      MAX-ACCESS  read-only
      STATUS      current
      DESCRIPTION "Total number of faults generated by this endpoint. "
      ::= { wseeV2RuntimeEntry 13  }
   
   
   wseeWsrmRuntimeTable OBJECT-TYPE
      SYNTAX      SEQUENCE OF WseeWsrmRuntimeEntry
      MAX-ACCESS  not-accessible
      STATUS      current
      DESCRIPTION "Encapsulates runtime information about WS-RM functionality. If this MBean is parented by a WseePortRuntimeMBean instance, this MBean represents WS-RM resources contained in a particular Web Service or web service client. If this MBean is parented by ServerRuntimeMBean, this MBean represents WS-RM resources for the entire server/VM (spanning across applications, web services, clients, etc.) "
      ::= { wls 1735  }
      
   
   wseeWsrmRuntimeEntry OBJECT-TYPE
      SYNTAX      WseeWsrmRuntimeEntry
      MAX-ACCESS  not-accessible
      STATUS      current
      DESCRIPTION "Generated SNMP Table Entry."
      INDEX { wseeWsrmRuntimeIndex}
      ::= { wseeWsrmRuntimeTable 1 }
      
   WseeWsrmRuntimeEntry ::=
      SEQUENCE
      {
         wseeWsrmRuntimeIndex OCTET STRING,
         wseeWsrmRuntimeObjectName OCTET STRING,
         wseeWsrmRuntimeType  OCTET STRING,
         wseeWsrmRuntimeName  OCTET STRING,
         wseeWsrmRuntimeSequenceIds OCTET STRING
      }
      
   
   wseeWsrmRuntimeIndex OBJECT-TYPE
      SYNTAX      OCTET STRING
      MAX-ACCESS  not-accessible
      STATUS      current
      DESCRIPTION "Index column"
      ::= { wseeWsrmRuntimeEntry 1  }
   
   
   wseeWsrmRuntimeObjectName OBJECT-TYPE
      SYNTAX      OCTET STRING
      MAX-ACCESS  read-only
      STATUS      current
      DESCRIPTION "ObjectName column"
      ::= { wseeWsrmRuntimeEntry 2  }
   
   
   wseeWsrmRuntimeType OBJECT-TYPE
      SYNTAX      OCTET STRING
      MAX-ACCESS  read-only
      STATUS      current
      DESCRIPTION "Returns the type of the MBean. "
      ::= { wseeWsrmRuntimeEntry 3  }
   
   
   wseeWsrmRuntimeName OBJECT-TYPE
      SYNTAX      OCTET STRING
      MAX-ACCESS  read-only
      STATUS      current
      DESCRIPTION "The name of this configuration. WebLogic Server uses an MBean to implement and persist the configuration. "
      ::= { wseeWsrmRuntimeEntry 4  }
   
   
   wseeWsrmRuntimeSequenceIds OBJECT-TYPE
      SYNTAX      OCTET STRING
      MAX-ACCESS  read-only
      STATUS      current
      DESCRIPTION "A list of sequence IDs representing active sequences being managed on the WS-RM destination (receiving side). "
      ::= { wseeWsrmRuntimeEntry 5  }
   
   
   coherenceServerTable OBJECT-TYPE
      SYNTAX      SEQUENCE OF CoherenceServerEntry
      MAX-ACCESS  not-accessible
      STATUS      current
      DESCRIPTION "This class represents a Coherence stand-alone server. "
      ::= { wls 1740  }
      
   
   coherenceServerEntry OBJECT-TYPE
      SYNTAX      CoherenceServerEntry
      MAX-ACCESS  not-accessible
      STATUS      current
      DESCRIPTION "Generated SNMP Table Entry."
      INDEX { coherenceServerIndex}
      ::= { coherenceServerTable 1 }
      
   CoherenceServerEntry ::=
      SEQUENCE
      {
         coherenceServerIndex OCTET STRING,
         coherenceServerObjectName OCTET STRING,
         coherenceServerRestartDelaySeconds Integer32,
         coherenceServerType  OCTET STRING,
         coherenceServerNMSocketCreateTimeoutInMillis Integer32,
         coherenceServerUnicastListenPort Integer32,
         coherenceServerUnicastPortAutoAdjust OCTET STRING,
         coherenceServerName  OCTET STRING,
         coherenceServerUnicastListenAddress OCTET STRING,
         coherenceServerRestartIntervalSeconds Integer32,
         coherenceServerRestartMax Integer32,
         coherenceServerAutoRestart OCTET STRING,
         coherenceServerUnicastPortAutoAdjustAttempts INTEGER,
         coherenceServerTags  OCTET STRING
      }
      
   
   coherenceServerIndex OBJECT-TYPE
      SYNTAX      OCTET STRING
      MAX-ACCESS  not-accessible
      STATUS      current
      DESCRIPTION "Index column"
      ::= { coherenceServerEntry 1  }
   
   
   coherenceServerObjectName OBJECT-TYPE
      SYNTAX      OCTET STRING
      MAX-ACCESS  read-only
      STATUS      current
      DESCRIPTION "ObjectName column"
      ::= { coherenceServerEntry 2  }
   
   
   coherenceServerRestartDelaySeconds OBJECT-TYPE
      SYNTAX      Integer32
      MAX-ACCESS  read-only
      STATUS      current
      DESCRIPTION " The number of seconds the Node Manager should wait before restarting this server.    After killing a server process, the system might need several seconds to release the TCP port(s) the server was using. If Node Manager attempts to restart the Managed Server while its ports are still active, the startup attempt fails.    If AutoMigration is enabled and RestartDelaySeconds is 0, the RestartDelaySeconds is automatically set to the lease time. This prevents the server from failing to restart after migration when the previous lease is still valid.  "
      ::= { coherenceServerEntry 3  }
   
   
   coherenceServerType OBJECT-TYPE
      SYNTAX      OCTET STRING
      MAX-ACCESS  read-only
      STATUS      current
      DESCRIPTION "Returns the type of the MBean. "
      ::= { coherenceServerEntry 4  }
   
   
   coherenceServerNMSocketCreateTimeoutInMillis OBJECT-TYPE
      SYNTAX      Integer32
      MAX-ACCESS  read-only
      STATUS      current
      DESCRIPTION "Returns the timeout value to be used by NodeManagerRuntime when creating a socket connection to the agent. Default set high as SSH agent may require a high connection establishment time. "
      ::= { coherenceServerEntry 5  }
   
   
   coherenceServerUnicastListenPort OBJECT-TYPE
      SYNTAX      Integer32
      MAX-ACCESS  read-only
      STATUS      current
      DESCRIPTION "The port for the cluster unicast listener. "
      ::= { coherenceServerEntry 6  }
   
   
   coherenceServerUnicastPortAutoAdjust OBJECT-TYPE
      SYNTAX      OCTET STRING
      MAX-ACCESS  read-only
      STATUS      current
      DESCRIPTION " Specifies whether the unicast port will be automatically incremented if the port cannot be bound because it is already in use.  "
      ::= { coherenceServerEntry 7  }
   
   
   coherenceServerName OBJECT-TYPE
      SYNTAX      OCTET STRING
      MAX-ACCESS  read-only
      STATUS      current
      DESCRIPTION "An alphanumeric name for this server instance. (Spaces are not valid.)  The name must be unique for all configuration objects in the domain. Within a domain, each server, machine, cluster, JDBC connection pool, virtual host, and any other resource type must be named uniquely and must not use the same name as the domain.  The server name is not used as part of the URL for applications that are deployed on the server. It is for your identification purposes only. The server name displays in the Administration Console, and if you use WebLogic Server command-line utilities or APIs, you use this name to identify the server.  After you have created a server, you cannot change its name. Instead, clone the server and provide a new name for the clone. "
      ::= { coherenceServerEntry 8  }
   
   
   coherenceServerUnicastListenAddress OBJECT-TYPE
      SYNTAX      OCTET STRING
      MAX-ACCESS  read-only
      STATUS      current
      DESCRIPTION "The IP address for the cluster unicast listener. This attribute may be used to override the value of the referenced Coherence cluster. "
      ::= { coherenceServerEntry 9  }
   
   
   coherenceServerRestartIntervalSeconds OBJECT-TYPE
      SYNTAX      Integer32
      MAX-ACCESS  read-only
      STATUS      current
      DESCRIPTION " The number of seconds during which this server can be restarted, up to the number of times specified in RestartMax.  "
      ::= { coherenceServerEntry 10  }
   
   
   coherenceServerRestartMax OBJECT-TYPE
      SYNTAX      Integer32
      MAX-ACCESS  read-only
      STATUS      current
      DESCRIPTION " The number of times that the Node Manager can restart this server within the interval specified in RestartIntervalSeconds.  "
      ::= { coherenceServerEntry 11  }
   
   
   coherenceServerAutoRestart OBJECT-TYPE
      SYNTAX      OCTET STRING
      MAX-ACCESS  read-only
      STATUS      current
      DESCRIPTION " Specifies whether the Node Manager can automatically restart this server if it crashes or otherwise goes down unexpectedly.  "
      ::= { coherenceServerEntry 12  }
   
   
   coherenceServerUnicastPortAutoAdjustAttempts OBJECT-TYPE
      SYNTAX      INTEGER
      MAX-ACCESS  read-only
      STATUS      current
      DESCRIPTION " Gets the upper bound of the unicast port. A positive value indicates the unicast port is automatically incremented if the specified port cannot be bound because it is already in use.  "
      ::= { coherenceServerEntry 13  }
   
   
   coherenceServerTags OBJECT-TYPE
      SYNTAX      OCTET STRING
      MAX-ACCESS  read-only
      STATUS      current
      DESCRIPTION "Return all tags on this Configuration MBean "
      ::= { coherenceServerEntry 14  }
   
   
   coherenceServerStartTable OBJECT-TYPE
      SYNTAX      SEQUENCE OF CoherenceServerStartEntry
      MAX-ACCESS  not-accessible
      STATUS      current
      DESCRIPTION "This bean is used to configure the attributes necessary to start up a server on a remote machine.  The following describes how NodeManager applies each property when starting the Coherence server.  #getJavaVendor The NodeManager does not pass this value invoking a java command line to start the server.  It does pass this value in the environment variable JAVA_VENDOR to the start script.   #getJavaHome This value can also be specified conveniently in the nodemanager .properties file using the coherence.startup.JavaHome or property. The NodeManager will pass this value to a start script using the JAVA_HOME environment variable.  When issuing a java command line to start the server, the NodeManager will use the java executable from the specified location.    #getClassPath The NodeManager will pass this value to a start script using the JAVA_OPTIONS environment variable containing -Djava.class.path.  When issuinga java command line to start the server, the NodeManager will pass -Djava.class.path.  #getMWHome This value can also be specified conveniently in the nodemanager .properties file using the coherence.startup.MWHome property. The NodeManager does not pass this value directly when starting a server.  However, it uses this value to construct an appropriate classpath for starting the server.  #getArguments This value can also be specified conveniently in the nodemanager .properties file using the coherence.startup.Arguments property. The NodeManager will pass this value to a start script using the JAVA_OPTIONS environment variable.  When issuing a java command line to start the server, the NodeManager will pass the arguments as options.  "
      ::= { wls 1745  }
      
   
   coherenceServerStartEntry OBJECT-TYPE
      SYNTAX      CoherenceServerStartEntry
      MAX-ACCESS  not-accessible
      STATUS      current
      DESCRIPTION "Generated SNMP Table Entry."
      INDEX { coherenceServerStartIndex}
      ::= { coherenceServerStartTable 1 }
      
   CoherenceServerStartEntry ::=
      SEQUENCE
      {
         coherenceServerStartIndex OCTET STRING,
         coherenceServerStartObjectName OCTET STRING,
         coherenceServerStartJavaHome OCTET STRING,
         coherenceServerStartBeaHome OCTET STRING,
         coherenceServerStartArguments OCTET STRING,
         coherenceServerStartType OCTET STRING,
         coherenceServerStartJavaVendor OCTET STRING,
         coherenceServerStartName OCTET STRING,
         coherenceServerStartRootDirectory OCTET STRING,
         coherenceServerStartClassPath OCTET STRING,
         coherenceServerStartMWHome OCTET STRING,
         coherenceServerStartTags OCTET STRING
      }
      
   
   coherenceServerStartIndex OBJECT-TYPE
      SYNTAX      OCTET STRING
      MAX-ACCESS  not-accessible
      STATUS      current
      DESCRIPTION "Index column"
      ::= { coherenceServerStartEntry 1  }
   
   
   coherenceServerStartObjectName OBJECT-TYPE
      SYNTAX      OCTET STRING
      MAX-ACCESS  read-only
      STATUS      current
      DESCRIPTION "ObjectName column"
      ::= { coherenceServerStartEntry 2  }
   
   
   coherenceServerStartJavaHome OBJECT-TYPE
      SYNTAX      OCTET STRING
      MAX-ACCESS  read-only
      STATUS      current
      DESCRIPTION "The Java home directory (path on the machine running Node Manager) to use when starting this server.  Specify the parent directory of the JDK's bin directory. For example, c:&#92;bea&#92;jdk141. "
      ::= { coherenceServerStartEntry 3  }
   
   
   coherenceServerStartBeaHome OBJECT-TYPE
      SYNTAX      OCTET STRING
      MAX-ACCESS  read-only
      STATUS      current
      DESCRIPTION "The BEA home directory (path on the machine running Node Manager) to use when starting this server.  Specify the directory on the Node Manager machine under which all of Oracle's BEA products were installed. For example, c:&#92Oracle&#92Middleware&#92. "
      ::= { coherenceServerStartEntry 4  }
   
   
   coherenceServerStartArguments OBJECT-TYPE
      SYNTAX      OCTET STRING
      MAX-ACCESS  read-only
      STATUS      current
      DESCRIPTION "The arguments to use when starting this server.  These are the first arguments appended immediately after java portion of the startup command. For example, you can set Java heap memory or specify any weblogic.nodemanager.server.provider.WeblogicCacheServer option.  Separate arguments with a space. "
      ::= { coherenceServerStartEntry 5  }
   
   
   coherenceServerStartType OBJECT-TYPE
      SYNTAX      OCTET STRING
      MAX-ACCESS  read-only
      STATUS      current
      DESCRIPTION "Returns the type of the MBean. "
      ::= { coherenceServerStartEntry 6  }
   
   
   coherenceServerStartJavaVendor OBJECT-TYPE
      SYNTAX      OCTET STRING
      MAX-ACCESS  read-only
      STATUS      current
      DESCRIPTION "The Java Vendor value to use when starting this server.   If the server is part of a cluster and configured for automatic migration across possibly different platforms with different vendors providing the JDKs, then, both JavaVendor and JavaHome should be set in the generated configuration file instead. "
      ::= { coherenceServerStartEntry 7  }
   
   
   coherenceServerStartName OBJECT-TYPE
      SYNTAX      OCTET STRING
      MAX-ACCESS  read-only
      STATUS      current
      DESCRIPTION "The user-specified name of this MBean instance.  This name is included as one of the key properties in the MBean's javax.management.ObjectName:  Name=user-specified-name "
      ::= { coherenceServerStartEntry 8  }
   
   
   coherenceServerStartRootDirectory OBJECT-TYPE
      SYNTAX      OCTET STRING
      MAX-ACCESS  read-only
      STATUS      current
      DESCRIPTION "The directory that this server uses as its root directory. This directory must be on the computer that hosts the Node Manager. If you do not specify a Root Directory value, the domain directory is used by default.  "
      ::= { coherenceServerStartEntry 9  }
   
   
   coherenceServerStartClassPath OBJECT-TYPE
      SYNTAX      OCTET STRING
      MAX-ACCESS  read-only
      STATUS      current
      DESCRIPTION "The classpath (path on the machine running Node Manager) to use when starting this server.  If you need to add user classes to the classpath, in addition you will need to add the following: FEATURES_HOME/weblogic.server.modules.coherence.integration.jar:COHERENCE_HOME/lib/coherence.jar  where FEATURES_HOME is the features directory (typically $WL_HOME/modules/features) and COHERENCE_HOME the coherence directory (typically $ORACLE_HOME/coherence) on the Node Manager machine. If you do not specify a classpath the above will be used automatically.   The operating system determines which character separates path elements. On Windows, use a semicolon (;). On UNIX a colon (:). "
      ::= { coherenceServerStartEntry 10  }
   
   
   coherenceServerStartMWHome OBJECT-TYPE
      SYNTAX      OCTET STRING
      MAX-ACCESS  read-only
      STATUS      current
      DESCRIPTION "The MWHome directory (path on the machine running Node Manager) to use when starting this server.  Specify the directory on the Node Manager machine under which all of Oracle's MW products were installed. For example, c:&#92;Oracle&#92;Middleware&#92;. "
      ::= { coherenceServerStartEntry 11  }
   
   
   coherenceServerStartTags OBJECT-TYPE
      SYNTAX      OCTET STRING
      MAX-ACCESS  read-only
      STATUS      current
      DESCRIPTION "Return all tags on this Configuration MBean "
      ::= { coherenceServerStartEntry 12  }
   
   
   coherenceServerLifeCycleRuntimeTable OBJECT-TYPE
      SYNTAX      SEQUENCE OF CoherenceServerLifeCycleRuntimeEntry
      MAX-ACCESS  not-accessible
      STATUS      current
      DESCRIPTION "Provides methods that transition servers from one state to another. This class is instantiated only on the Administration Server, but you can use it to transition the states of all managed Coherence cache servers.  To start Coherence cache servers, you must first configure a Node Manager on each Coherence cache server's host machine."
      ::= { wls 1750  }
      
   
   coherenceServerLifeCycleRuntimeEntry OBJECT-TYPE
      SYNTAX      CoherenceServerLifeCycleRuntimeEntry
      MAX-ACCESS  not-accessible
      STATUS      current
      DESCRIPTION "Generated SNMP Table Entry."
      INDEX { coherenceServerLifeCycleRuntimeIndex}
      ::= { coherenceServerLifeCycleRuntimeTable 1 }
      
   CoherenceServerLifeCycleRuntimeEntry ::=
      SEQUENCE
      {
         coherenceServerLifeCycleRuntimeIndex OCTET STRING,
         coherenceServerLifeCycleRuntimeObjectName OCTET STRING,
         coherenceServerLifeCycleRuntimeType OCTET STRING,
         coherenceServerLifeCycleRuntimeNodeManagerRestartCount Integer32,
         coherenceServerLifeCycleRuntimeName OCTET STRING,
         coherenceServerLifeCycleRuntimeState OCTET STRING
      }
      
   
   coherenceServerLifeCycleRuntimeIndex OBJECT-TYPE
      SYNTAX      OCTET STRING
      MAX-ACCESS  not-accessible
      STATUS      current
      DESCRIPTION "Index column"
      ::= { coherenceServerLifeCycleRuntimeEntry 1  }
   
   
   coherenceServerLifeCycleRuntimeObjectName OBJECT-TYPE
      SYNTAX      OCTET STRING
      MAX-ACCESS  read-only
      STATUS      current
      DESCRIPTION "ObjectName column"
      ::= { coherenceServerLifeCycleRuntimeEntry 2  }
   
   
   coherenceServerLifeCycleRuntimeType OBJECT-TYPE
      SYNTAX      OCTET STRING
      MAX-ACCESS  read-only
      STATUS      current
      DESCRIPTION "Returns the type of the MBean."
      ::= { coherenceServerLifeCycleRuntimeEntry 3  }
   
   
   coherenceServerLifeCycleRuntimeNodeManagerRestartCount OBJECT-TYPE
      SYNTAX      Integer32
      MAX-ACCESS  read-only
      STATUS      current
      DESCRIPTION "The number of times the server has been restarted using the Node Manager since its creation. The first start does not count. The count is valid only if the Node Manager is used to start and restart the server every time."
      ::= { coherenceServerLifeCycleRuntimeEntry 4  }
   
   
   coherenceServerLifeCycleRuntimeName OBJECT-TYPE
      SYNTAX      OCTET STRING
      MAX-ACCESS  read-only
      STATUS      current
      DESCRIPTION "The name of this configuration. WebLogic Server uses an MBean to implement and persist the configuration."
      ::= { coherenceServerLifeCycleRuntimeEntry 5  }
   
   
   coherenceServerLifeCycleRuntimeState OBJECT-TYPE
      SYNTAX      OCTET STRING
      MAX-ACCESS  read-only
      STATUS      current
      DESCRIPTION "The current state of the server. Server states are described in 'Managing Server Startup and Shutdown for Oracle WebLogic Server.'"
      ::= { coherenceServerLifeCycleRuntimeEntry 6  }
   
   
   coherenceServerLifeCycleTaskRuntimeTable OBJECT-TYPE
      SYNTAX      SEQUENCE OF CoherenceServerLifeCycleTaskRuntimeEntry
      MAX-ACCESS  not-accessible
      STATUS      current
      DESCRIPTION "Exposes monitoring information about a server's life cycle. Remote clients as well as clients running within a server can access this information.  An operation (task) to change a server's state will fork a separate thread to perform the actual work and immediately return an instance of this MBean to the caller. The caller can then use this MBean to track the task's progress as desired. "
      ::= { wls 1755  }
      
   
   coherenceServerLifeCycleTaskRuntimeEntry OBJECT-TYPE
      SYNTAX      CoherenceServerLifeCycleTaskRuntimeEntry
      MAX-ACCESS  not-accessible
      STATUS      current
      DESCRIPTION "Generated SNMP Table Entry."
      INDEX { coherenceServerLifeCycleTaskRuntimeIndex}
      ::= { coherenceServerLifeCycleTaskRuntimeTable 1 }
      
   CoherenceServerLifeCycleTaskRuntimeEntry ::=
      SEQUENCE
      {
         coherenceServerLifeCycleTaskRuntimeIndex OCTET STRING,
         coherenceServerLifeCycleTaskRuntimeObjectName OCTET STRING,
         coherenceServerLifeCycleTaskRuntimeOperation OCTET STRING,
         coherenceServerLifeCycleTaskRuntimeDescription OCTET STRING,
         coherenceServerLifeCycleTaskRuntimeType OCTET STRING,
         coherenceServerLifeCycleTaskRuntimeRunning OCTET STRING,
         coherenceServerLifeCycleTaskRuntimeSystemTask OCTET STRING,
         coherenceServerLifeCycleTaskRuntimeServerName OCTET STRING,
         coherenceServerLifeCycleTaskRuntimeName OCTET STRING,
         coherenceServerLifeCycleTaskRuntimeStatus OCTET STRING,
         coherenceServerLifeCycleTaskRuntimeBeginTime Counter64,
         coherenceServerLifeCycleTaskRuntimeEndTime Counter64,
         coherenceServerLifeCycleTaskRuntimeProgress OCTET STRING
      }
      
   
   coherenceServerLifeCycleTaskRuntimeIndex OBJECT-TYPE
      SYNTAX      OCTET STRING
      MAX-ACCESS  not-accessible
      STATUS      current
      DESCRIPTION "Index column"
      ::= { coherenceServerLifeCycleTaskRuntimeEntry 1  }
   
   
   coherenceServerLifeCycleTaskRuntimeObjectName OBJECT-TYPE
      SYNTAX      OCTET STRING
      MAX-ACCESS  read-only
      STATUS      current
      DESCRIPTION "ObjectName column"
      ::= { coherenceServerLifeCycleTaskRuntimeEntry 2  }
   
   
   coherenceServerLifeCycleTaskRuntimeOperation OBJECT-TYPE
      SYNTAX      OCTET STRING
      MAX-ACCESS  read-only
      STATUS      current
      DESCRIPTION "Gets the name of the method that was invoked on the ServerLifeCycleRuntime to initiate this task. "
      ::= { coherenceServerLifeCycleTaskRuntimeEntry 3  }
   
   
   coherenceServerLifeCycleTaskRuntimeDescription OBJECT-TYPE
      SYNTAX      OCTET STRING
      MAX-ACCESS  read-only
      STATUS      current
      DESCRIPTION "A description of this task. "
      ::= { coherenceServerLifeCycleTaskRuntimeEntry 4  }
   
   
   coherenceServerLifeCycleTaskRuntimeType OBJECT-TYPE
      SYNTAX      OCTET STRING
      MAX-ACCESS  read-only
      STATUS      current
      DESCRIPTION "Returns the type of the MBean. "
      ::= { coherenceServerLifeCycleTaskRuntimeEntry 5  }
   
   
   coherenceServerLifeCycleTaskRuntimeRunning OBJECT-TYPE
      SYNTAX      OCTET STRING
      MAX-ACCESS  read-only
      STATUS      current
      DESCRIPTION "Indicates whether the task is still running. "
      ::= { coherenceServerLifeCycleTaskRuntimeEntry 6  }
   
   
   coherenceServerLifeCycleTaskRuntimeSystemTask OBJECT-TYPE
      SYNTAX      OCTET STRING
      MAX-ACCESS  read-only
      STATUS      current
      DESCRIPTION "Indicates whether this task was initiated by the server versus a user. "
      ::= { coherenceServerLifeCycleTaskRuntimeEntry 7  }
   
   
   coherenceServerLifeCycleTaskRuntimeServerName OBJECT-TYPE
      SYNTAX      OCTET STRING
      MAX-ACCESS  read-only
      STATUS      current
      DESCRIPTION "The name of the server. "
      ::= { coherenceServerLifeCycleTaskRuntimeEntry 8  }
   
   
   coherenceServerLifeCycleTaskRuntimeName OBJECT-TYPE
      SYNTAX      OCTET STRING
      MAX-ACCESS  read-only
      STATUS      current
      DESCRIPTION "The name of this configuration. WebLogic Server uses an MBean to implement and persist the configuration. "
      ::= { coherenceServerLifeCycleTaskRuntimeEntry 9  }
   
   
   coherenceServerLifeCycleTaskRuntimeStatus OBJECT-TYPE
      SYNTAX      OCTET STRING
      MAX-ACCESS  read-only
      STATUS      current
      DESCRIPTION "The status of this task. "
      ::= { coherenceServerLifeCycleTaskRuntimeEntry 10  }
   
   
   coherenceServerLifeCycleTaskRuntimeBeginTime OBJECT-TYPE
      SYNTAX      Counter64
      MAX-ACCESS  read-only
      STATUS      current
      DESCRIPTION "The time at which this task was started. "
      ::= { coherenceServerLifeCycleTaskRuntimeEntry 11  }
   
   
   coherenceServerLifeCycleTaskRuntimeEndTime OBJECT-TYPE
      SYNTAX      Counter64
      MAX-ACCESS  read-only
      STATUS      current
      DESCRIPTION "The time at which this task was completed.  A value of -1 indicates that the task is currently running. "
      ::= { coherenceServerLifeCycleTaskRuntimeEntry 12  }
   
   
   coherenceServerLifeCycleTaskRuntimeProgress OBJECT-TYPE
      SYNTAX      OCTET STRING
      MAX-ACCESS  read-only
      STATUS      current
      DESCRIPTION "The progress of this task. "
      ::= { coherenceServerLifeCycleTaskRuntimeEntry 13  }
   
   
   jdbcOracleDataSourceInstanceRuntimeTable OBJECT-TYPE
      SYNTAX      SEQUENCE OF JdbcOracleDataSourceInstanceRuntimeEntry
      MAX-ACCESS  not-accessible
      STATUS      current
      DESCRIPTION "Runtime MBean for monitoring a JDBC GridLink Data Source instance. "
      ::= { wls 1760  }
      
   
   jdbcOracleDataSourceInstanceRuntimeEntry OBJECT-TYPE
      SYNTAX      JdbcOracleDataSourceInstanceRuntimeEntry
      MAX-ACCESS  not-accessible
      STATUS      current
      DESCRIPTION "Generated SNMP Table Entry."
      INDEX { jdbcOracleDataSourceInstanceRuntimeIndex}
      ::= { jdbcOracleDataSourceInstanceRuntimeTable 1 }
      
   JdbcOracleDataSourceInstanceRuntimeEntry ::=
      SEQUENCE
      {
         jdbcOracleDataSourceInstanceRuntimeIndex OCTET STRING,
         jdbcOracleDataSourceInstanceRuntimeObjectName OCTET STRING,
         jdbcOracleDataSourceInstanceRuntimeEnabled OCTET STRING,
         jdbcOracleDataSourceInstanceRuntimeActiveConnectionsCurrentCount Integer32,
         jdbcOracleDataSourceInstanceRuntimeType OCTET STRING,
         jdbcOracleDataSourceInstanceRuntimeNumAvailable Integer32,
         jdbcOracleDataSourceInstanceRuntimeSignature OCTET STRING,
         jdbcOracleDataSourceInstanceRuntimeCurrentWeight Integer32,
         jdbcOracleDataSourceInstanceRuntimeName OCTET STRING,
         jdbcOracleDataSourceInstanceRuntimeConnectionsTotalCount Integer32,
         jdbcOracleDataSourceInstanceRuntimeReserveRequestCount Counter64,
         jdbcOracleDataSourceInstanceRuntimeState OCTET STRING,
         jdbcOracleDataSourceInstanceRuntimeNumUnavailable Integer32,
         jdbcOracleDataSourceInstanceRuntimeCurrCapacity Integer32,
         jdbcOracleDataSourceInstanceRuntimeInstanceName OCTET STRING,
         jdbcOracleDataSourceInstanceRuntimeAffEnabled OCTET STRING
      }
      
   
   jdbcOracleDataSourceInstanceRuntimeIndex OBJECT-TYPE
      SYNTAX      OCTET STRING
      MAX-ACCESS  not-accessible
      STATUS      current
      DESCRIPTION "Index column"
      ::= { jdbcOracleDataSourceInstanceRuntimeEntry 1  }
   
   
   jdbcOracleDataSourceInstanceRuntimeObjectName OBJECT-TYPE
      SYNTAX      OCTET STRING
      MAX-ACCESS  read-only
      STATUS      current
      DESCRIPTION "ObjectName column"
      ::= { jdbcOracleDataSourceInstanceRuntimeEntry 2  }
   
   
   jdbcOracleDataSourceInstanceRuntimeEnabled OBJECT-TYPE
      SYNTAX      OCTET STRING
      MAX-ACCESS  read-only
      STATUS      current
      DESCRIPTION "Indicates whether the instance is enabled or disabled:  true if the instance is enabled. false if the instance is disabled.  "
      ::= { jdbcOracleDataSourceInstanceRuntimeEntry 3  }
   
   
   jdbcOracleDataSourceInstanceRuntimeActiveConnectionsCurrentCount OBJECT-TYPE
      SYNTAX      Integer32
      MAX-ACCESS  read-only
      STATUS      current
      DESCRIPTION " The number of connections currently in use by applications.  "
      ::= { jdbcOracleDataSourceInstanceRuntimeEntry 4  }
   
   
   jdbcOracleDataSourceInstanceRuntimeType OBJECT-TYPE
      SYNTAX      OCTET STRING
      MAX-ACCESS  read-only
      STATUS      current
      DESCRIPTION "Returns the type of the MBean. "
      ::= { jdbcOracleDataSourceInstanceRuntimeEntry 5  }
   
   
   jdbcOracleDataSourceInstanceRuntimeNumAvailable OBJECT-TYPE
      SYNTAX      Integer32
      MAX-ACCESS  read-only
      STATUS      current
      DESCRIPTION " The number of database connections currently available (not in use) in this data source for this instance.  "
      ::= { jdbcOracleDataSourceInstanceRuntimeEntry 6  }
   
   
   jdbcOracleDataSourceInstanceRuntimeSignature OBJECT-TYPE
      SYNTAX      OCTET STRING
      MAX-ACCESS  read-only
      STATUS      current
      DESCRIPTION "The signature that uniquely identifies the instance. "
      ::= { jdbcOracleDataSourceInstanceRuntimeEntry 7  }
   
   
   jdbcOracleDataSourceInstanceRuntimeCurrentWeight OBJECT-TYPE
      SYNTAX      Integer32
      MAX-ACCESS  read-only
      STATUS      current
      DESCRIPTION "The current weight of the instance. "
      ::= { jdbcOracleDataSourceInstanceRuntimeEntry 8  }
   
   
   jdbcOracleDataSourceInstanceRuntimeName OBJECT-TYPE
      SYNTAX      OCTET STRING
      MAX-ACCESS  read-only
      STATUS      current
      DESCRIPTION "The name of this configuration. WebLogic Server uses an MBean to implement and persist the configuration. "
      ::= { jdbcOracleDataSourceInstanceRuntimeEntry 9  }
   
   
   jdbcOracleDataSourceInstanceRuntimeConnectionsTotalCount OBJECT-TYPE
      SYNTAX      Integer32
      MAX-ACCESS  read-only
      STATUS      current
      DESCRIPTION " The cumulative total number of database connections created in this instance since the data source was deployed.  "
      ::= { jdbcOracleDataSourceInstanceRuntimeEntry 10  }
   
   
   jdbcOracleDataSourceInstanceRuntimeReserveRequestCount OBJECT-TYPE
      SYNTAX      Counter64
      MAX-ACCESS  read-only
      STATUS      current
      DESCRIPTION " The cumulative, running count of requests for a connection from this instance.  "
      ::= { jdbcOracleDataSourceInstanceRuntimeEntry 11  }
   
   
   jdbcOracleDataSourceInstanceRuntimeState OBJECT-TYPE
      SYNTAX      OCTET STRING
      MAX-ACCESS  read-only
      STATUS      current
      DESCRIPTION " The current state of the instance within the data source.   Possible states are:   Enabled - the instance is enabled indicating that there are connections established Disabled - the instance is disabled due to unavailability  "
      ::= { jdbcOracleDataSourceInstanceRuntimeEntry 12  }
   
   
   jdbcOracleDataSourceInstanceRuntimeNumUnavailable OBJECT-TYPE
      SYNTAX      Integer32
      MAX-ACCESS  read-only
      STATUS      current
      DESCRIPTION " The number of database connections that are currently unavailable (in use or being tested by the system) in this instance.  "
      ::= { jdbcOracleDataSourceInstanceRuntimeEntry 13  }
   
   
   jdbcOracleDataSourceInstanceRuntimeCurrCapacity OBJECT-TYPE
      SYNTAX      Integer32
      MAX-ACCESS  read-only
      STATUS      current
      DESCRIPTION " The current count of JDBC connections in the connection pool in the data source for this instance.  "
      ::= { jdbcOracleDataSourceInstanceRuntimeEntry 14  }
   
   
   jdbcOracleDataSourceInstanceRuntimeInstanceName OBJECT-TYPE
      SYNTAX      OCTET STRING
      MAX-ACCESS  read-only
      STATUS      current
      DESCRIPTION "The name of this instance. "
      ::= { jdbcOracleDataSourceInstanceRuntimeEntry 15  }
   
   
   jdbcOracleDataSourceInstanceRuntimeAffEnabled OBJECT-TYPE
      SYNTAX      OCTET STRING
      MAX-ACCESS  read-only
      STATUS      current
      DESCRIPTION "The value from the latest load-balancing advisory aff flag for a GridLink data source instance. "
      ::= { jdbcOracleDataSourceInstanceRuntimeEntry 16  }
   
   
   jdbcOracleDataSourceRuntimeTable OBJECT-TYPE
      SYNTAX      SEQUENCE OF JdbcOracleDataSourceRuntimeEntry
      MAX-ACCESS  not-accessible
      STATUS      current
      DESCRIPTION "Runtime MBean that represents a JDBC RAC JDBC data source. "
      ::= { wls 1765  }
      
   
   jdbcOracleDataSourceRuntimeEntry OBJECT-TYPE
      SYNTAX      JdbcOracleDataSourceRuntimeEntry
      MAX-ACCESS  not-accessible
      STATUS      current
      DESCRIPTION "Generated SNMP Table Entry."
      INDEX { jdbcOracleDataSourceRuntimeIndex}
      ::= { jdbcOracleDataSourceRuntimeTable 1 }
      
   JdbcOracleDataSourceRuntimeEntry ::=
      SEQUENCE
      {
         jdbcOracleDataSourceRuntimeIndex OCTET STRING,
         jdbcOracleDataSourceRuntimeObjectName OCTET STRING,
         jdbcOracleDataSourceRuntimeActiveConnectionsCurrentCount Integer32,
         jdbcOracleDataSourceRuntimeWaitingForConnectionFailureTotal Counter64,
         jdbcOracleDataSourceRuntimeFailedRCLBBasedBorrowCount Counter64,
         jdbcOracleDataSourceRuntimeWaitingForConnectionTotal Counter64,
         jdbcOracleDataSourceRuntimeConnectionsTotalCount Integer32,
         jdbcOracleDataSourceRuntimeSuccessfulRCLBBasedBorrowCount Counter64,
         jdbcOracleDataSourceRuntimeDriverVersion OCTET STRING,
         jdbcOracleDataSourceRuntimeWaitingForConnectionCurrentCount Integer32,
         jdbcOracleDataSourceRuntimeLeakedConnectionCount Integer32,
         jdbcOracleDataSourceRuntimeHighestNumUnavailable Integer32,
         jdbcOracleDataSourceRuntimePrepStmtCacheAccessCount Counter64,
         jdbcOracleDataSourceRuntimeWaitSecondsHighCount Integer32,
         jdbcOracleDataSourceRuntimeActiveConnectionsHighCount Integer32,
         jdbcOracleDataSourceRuntimeFailedAffinityBasedBorrowCount Counter64,
         jdbcOracleDataSourceRuntimePrepStmtCacheHitCount Integer32,
         jdbcOracleDataSourceRuntimeActiveConnectionsAverageCount Integer32,
         jdbcOracleDataSourceRuntimeVersionJDBCDriver OCTET STRING,
         jdbcOracleDataSourceRuntimeDatabaseProductVersion OCTET STRING,
         jdbcOracleDataSourceRuntimeSuccessfulAffinityBasedBorrowCount Counter64,
         jdbcOracleDataSourceRuntimePrepStmtCacheDeleteCount Counter64,
         jdbcOracleDataSourceRuntimeReserveRequestCount Counter64,
         jdbcOracleDataSourceRuntimeFailuresToReconnectCount Integer32,
         jdbcOracleDataSourceRuntimeWaitingForConnectionHighCount Integer32,
         jdbcOracleDataSourceRuntimePrepStmtCacheMissCount Integer32,
         jdbcOracleDataSourceRuntimeEnabled OCTET STRING,
         jdbcOracleDataSourceRuntimeFailedReserveRequestCount Counter64,
         jdbcOracleDataSourceRuntimeType OCTET STRING,
         jdbcOracleDataSourceRuntimeHighestNumAvailable Integer32,
         jdbcOracleDataSourceRuntimeDatabaseProductName OCTET STRING,
         jdbcOracleDataSourceRuntimeCurrCapacityHighCount Integer32,
         jdbcOracleDataSourceRuntimePrepStmtCacheCurrentSize Integer32,
         jdbcOracleDataSourceRuntimeServiceName OCTET STRING,
         jdbcOracleDataSourceRuntimeWaitingForConnectionSuccessTotal Counter64,
         jdbcOracleDataSourceRuntimeNumUnavailable Integer32,
         jdbcOracleDataSourceRuntimePrepStmtCacheAddCount Counter64,
         jdbcOracleDataSourceRuntimeDriverName OCTET STRING,
         jdbcOracleDataSourceRuntimeNumAvailable Integer32,
         jdbcOracleDataSourceRuntimeModuleId OCTET STRING,
         jdbcOracleDataSourceRuntimeName OCTET STRING,
         jdbcOracleDataSourceRuntimeState OCTET STRING,
         jdbcOracleDataSourceRuntimeConnectionDelayTime Integer32,
         jdbcOracleDataSourceRuntimeDeploymentState Integer32,
         jdbcOracleDataSourceRuntimeCurrCapacity Integer32,
         jdbcOracleDataSourceRuntimeRepurposeCount Counter64,
         jdbcOracleDataSourceRuntimeUnresolvedTotalCount Counter64,
         jdbcOracleDataSourceRuntimeResolvedAsCommittedTotalCount Counter64,
         jdbcOracleDataSourceRuntimeCommitOutcomeRetryTotalCount Counter64,
         jdbcOracleDataSourceRuntimeResolvedAsNotCommittedTotalCount Counter64,
         jdbcOracleDataSourceRuntimeFailedRepurposeCount Counter64
      }
      
   
   jdbcOracleDataSourceRuntimeIndex OBJECT-TYPE
      SYNTAX      OCTET STRING
      MAX-ACCESS  not-accessible
      STATUS      current
      DESCRIPTION "Index column"
      ::= { jdbcOracleDataSourceRuntimeEntry 1  }
   
   
   jdbcOracleDataSourceRuntimeObjectName OBJECT-TYPE
      SYNTAX      OCTET STRING
      MAX-ACCESS  read-only
      STATUS      current
      DESCRIPTION "ObjectName column"
      ::= { jdbcOracleDataSourceRuntimeEntry 2  }
   
   
   jdbcOracleDataSourceRuntimeActiveConnectionsCurrentCount OBJECT-TYPE
      SYNTAX      Integer32
      MAX-ACCESS  read-only
      STATUS      current
      DESCRIPTION "The number of connections currently in use by applications. "
      ::= { jdbcOracleDataSourceRuntimeEntry 3  }
   
   
   jdbcOracleDataSourceRuntimeWaitingForConnectionFailureTotal OBJECT-TYPE
      SYNTAX      Counter64
      MAX-ACCESS  read-only
      STATUS      current
      DESCRIPTION "The cumulative, running count of requests for a connection from this data source that had to wait before getting a connection and eventually failed to get a connection.  Waiting connection requests can fail for a variety of reasons, including waiting for longer than the ConnectionReserveTimeoutSeconds. "
      ::= { jdbcOracleDataSourceRuntimeEntry 4  }
   
   
   jdbcOracleDataSourceRuntimeFailedRCLBBasedBorrowCount OBJECT-TYPE
      SYNTAX      Counter64
      MAX-ACCESS  read-only
      STATUS      current
      DESCRIPTION "The number of reserve requests for which a connection was not found based on the runtime connection load balancing policy. "
      ::= { jdbcOracleDataSourceRuntimeEntry 5  }
   
   
   jdbcOracleDataSourceRuntimeWaitingForConnectionTotal OBJECT-TYPE
      SYNTAX      Counter64
      MAX-ACCESS  read-only
      STATUS      current
      DESCRIPTION "The cumulative, running count of requests for a connection from this data source that had to wait before getting a connection, including those that eventually got a connection and those that did not get a connection. "
      ::= { jdbcOracleDataSourceRuntimeEntry 6  }
   
   
   jdbcOracleDataSourceRuntimeConnectionsTotalCount OBJECT-TYPE
      SYNTAX      Integer32
      MAX-ACCESS  read-only
      STATUS      current
      DESCRIPTION "The cumulative total number of database connections created in this data source since the data source was deployed. "
      ::= { jdbcOracleDataSourceRuntimeEntry 7  }
   
   
   jdbcOracleDataSourceRuntimeSuccessfulRCLBBasedBorrowCount OBJECT-TYPE
      SYNTAX      Counter64
      MAX-ACCESS  read-only
      STATUS      current
      DESCRIPTION "The number of reserve requests for which existing connections were found that satisfied the runtime connection load balancing policy. "
      ::= { jdbcOracleDataSourceRuntimeEntry 8  }
   
   
   jdbcOracleDataSourceRuntimeDriverVersion OBJECT-TYPE
      SYNTAX      OCTET STRING
      MAX-ACCESS  read-only
      STATUS      current
      DESCRIPTION " The version of the JDBC driver that this data source is configured to use.  "
      ::= { jdbcOracleDataSourceRuntimeEntry 9  }
   
   
   jdbcOracleDataSourceRuntimeWaitingForConnectionCurrentCount OBJECT-TYPE
      SYNTAX      Integer32
      MAX-ACCESS  read-only
      STATUS      current
      DESCRIPTION "The number of connection requests waiting for a database connection. "
      ::= { jdbcOracleDataSourceRuntimeEntry 10  }
   
   
   jdbcOracleDataSourceRuntimeLeakedConnectionCount OBJECT-TYPE
      SYNTAX      Integer32
      MAX-ACCESS  read-only
      STATUS      current
      DESCRIPTION "The number of leaked connections. A leaked connection is a connection that was reserved from the data source but was not returned to the data source by calling close(). "
      ::= { jdbcOracleDataSourceRuntimeEntry 11  }
   
   
   jdbcOracleDataSourceRuntimeHighestNumUnavailable OBJECT-TYPE
      SYNTAX      Integer32
      MAX-ACCESS  read-only
      STATUS      current
      DESCRIPTION "Highest number of database connections that were in use by applications or being tested by the system in this instance of the data source since the data source was deployed. "
      ::= { jdbcOracleDataSourceRuntimeEntry 12  }
   
   
   jdbcOracleDataSourceRuntimePrepStmtCacheAccessCount OBJECT-TYPE
      SYNTAX      Counter64
      MAX-ACCESS  read-only
      STATUS      current
      DESCRIPTION "The cumulative, running count of the number of times that the statement cache was accessed. "
      ::= { jdbcOracleDataSourceRuntimeEntry 13  }
   
   
   jdbcOracleDataSourceRuntimeWaitSecondsHighCount OBJECT-TYPE
      SYNTAX      Integer32
      MAX-ACCESS  read-only
      STATUS      current
      DESCRIPTION "The highest number of seconds that an application waited for a connection (the longest connection reserve wait time) from this instance of the connection pool since the connection pool was instantiated. This value is updated when a completed getConnection request takes longer to return a connection than any previous request. "
      ::= { jdbcOracleDataSourceRuntimeEntry 14  }
   
   
   jdbcOracleDataSourceRuntimeActiveConnectionsHighCount OBJECT-TYPE
      SYNTAX      Integer32
      MAX-ACCESS  read-only
      STATUS      current
      DESCRIPTION "Highest number of active database connections in this instance of the data source since the data source was instantiated.   Active connections are connections in use by an application. "
      ::= { jdbcOracleDataSourceRuntimeEntry 15  }
   
   
   jdbcOracleDataSourceRuntimeFailedAffinityBasedBorrowCount OBJECT-TYPE
      SYNTAX      Counter64
      MAX-ACCESS  read-only
      STATUS      current
      DESCRIPTION "The number of reserve requests for which an existing connection for the affinity policy was not found. "
      ::= { jdbcOracleDataSourceRuntimeEntry 16  }
   
   
   jdbcOracleDataSourceRuntimePrepStmtCacheHitCount OBJECT-TYPE
      SYNTAX      Integer32
      MAX-ACCESS  read-only
      STATUS      current
      DESCRIPTION "The cumulative, running count of the number of times that statements from the cache were used. "
      ::= { jdbcOracleDataSourceRuntimeEntry 17  }
   
   
   jdbcOracleDataSourceRuntimeActiveConnectionsAverageCount OBJECT-TYPE
      SYNTAX      Integer32
      MAX-ACCESS  read-only
      STATUS      current
      DESCRIPTION "Average number of active connections in this instance of the data source.  Active connections are connections in use by an application.  This value is only valid if the resource is configured to allow shrinking. "
      ::= { jdbcOracleDataSourceRuntimeEntry 18  }
   
   
   jdbcOracleDataSourceRuntimeVersionJDBCDriver OBJECT-TYPE
      SYNTAX      OCTET STRING
      MAX-ACCESS  read-only
      STATUS      current
      DESCRIPTION "The driver class name of the JDBC driver used to create database connections.  "
      ::= { jdbcOracleDataSourceRuntimeEntry 19  }
   
   
   jdbcOracleDataSourceRuntimeDatabaseProductVersion OBJECT-TYPE
      SYNTAX      OCTET STRING
      MAX-ACCESS  read-only
      STATUS      current
      DESCRIPTION " The product version of the database that this data source is connected to.  "
      ::= { jdbcOracleDataSourceRuntimeEntry 20  }
   
   
   jdbcOracleDataSourceRuntimeSuccessfulAffinityBasedBorrowCount OBJECT-TYPE
      SYNTAX      Counter64
      MAX-ACCESS  read-only
      STATUS      current
      DESCRIPTION "The number of reserve requests for which an existing connection was found that satisfied the affinity policy. "
      ::= { jdbcOracleDataSourceRuntimeEntry 21  }
   
   
   jdbcOracleDataSourceRuntimePrepStmtCacheDeleteCount OBJECT-TYPE
      SYNTAX      Counter64
      MAX-ACCESS  read-only
      STATUS      current
      DESCRIPTION "The cumulative, running count of statements discarded from the cache.  Each connection in the connection pool has its own cache of statements. This number is the sum of the number of statements that were discarded from the caches for all connections in the connection pool. "
      ::= { jdbcOracleDataSourceRuntimeEntry 22  }
   
   
   jdbcOracleDataSourceRuntimeReserveRequestCount OBJECT-TYPE
      SYNTAX      Counter64
      MAX-ACCESS  read-only
      STATUS      current
      DESCRIPTION "The cumulative, running count of requests for a connection from this data source. "
      ::= { jdbcOracleDataSourceRuntimeEntry 23  }
   
   
   jdbcOracleDataSourceRuntimeFailuresToReconnectCount OBJECT-TYPE
      SYNTAX      Integer32
      MAX-ACCESS  read-only
      STATUS      current
      DESCRIPTION "The number of times that the data source attempted to refresh a database connection and failed.  Failures may occur when the database is unavailable or when the network connection to the database is interrupted. "
      ::= { jdbcOracleDataSourceRuntimeEntry 24  }
   
   
   jdbcOracleDataSourceRuntimeWaitingForConnectionHighCount OBJECT-TYPE
      SYNTAX      Integer32
      MAX-ACCESS  read-only
      STATUS      current
      DESCRIPTION "Highest number of application requests concurrently waiting for a connection from this instance of the data source. "
      ::= { jdbcOracleDataSourceRuntimeEntry 25  }
   
   
   jdbcOracleDataSourceRuntimePrepStmtCacheMissCount OBJECT-TYPE
      SYNTAX      Integer32
      MAX-ACCESS  read-only
      STATUS      current
      DESCRIPTION "The number of times that a statement request could not be satisfied with a statement from the cache. "
      ::= { jdbcOracleDataSourceRuntimeEntry 26  }
   
   
   jdbcOracleDataSourceRuntimeEnabled OBJECT-TYPE
      SYNTAX      OCTET STRING
      MAX-ACCESS  read-only
      STATUS      current
      DESCRIPTION "Indicates whether the data source is enabled or disabled:   true if the data source is enabled. false if the data source is disabled.  "
      ::= { jdbcOracleDataSourceRuntimeEntry 27  }
   
   
   jdbcOracleDataSourceRuntimeFailedReserveRequestCount OBJECT-TYPE
      SYNTAX      Counter64
      MAX-ACCESS  read-only
      STATUS      current
      DESCRIPTION "The cumulative, running count of requests for a connection from this data source that could not be fulfilled. "
      ::= { jdbcOracleDataSourceRuntimeEntry 28  }
   
   
   jdbcOracleDataSourceRuntimeType OBJECT-TYPE
      SYNTAX      OCTET STRING
      MAX-ACCESS  read-only
      STATUS      current
      DESCRIPTION "Returns the type of the MBean. "
      ::= { jdbcOracleDataSourceRuntimeEntry 29  }
   
   
   jdbcOracleDataSourceRuntimeHighestNumAvailable OBJECT-TYPE
      SYNTAX      Integer32
      MAX-ACCESS  read-only
      STATUS      current
      DESCRIPTION "Highest number of database connections that were idle and available to be used by an application at any time in this instance of the data source since the data source was deployed. "
      ::= { jdbcOracleDataSourceRuntimeEntry 30  }
   
   
   jdbcOracleDataSourceRuntimeDatabaseProductName OBJECT-TYPE
      SYNTAX      OCTET STRING
      MAX-ACCESS  read-only
      STATUS      current
      DESCRIPTION " The product name of the database that this data source is connected to.  "
      ::= { jdbcOracleDataSourceRuntimeEntry 31  }
   
   
   jdbcOracleDataSourceRuntimeCurrCapacityHighCount OBJECT-TYPE
      SYNTAX      Integer32
      MAX-ACCESS  read-only
      STATUS      current
      DESCRIPTION "Highest number of database connections available or in use (current capacity) in this instance of the data source since the data source was deployed. "
      ::= { jdbcOracleDataSourceRuntimeEntry 32  }
   
   
   jdbcOracleDataSourceRuntimePrepStmtCacheCurrentSize OBJECT-TYPE
      SYNTAX      Integer32
      MAX-ACCESS  read-only
      STATUS      current
      DESCRIPTION "The number of prepared and callable statements currently cached in the statement cache.  Each connection in the connection pool has its own cache of statements. This number is the sum of the number of statements in the caches for all connections in the connection pool. "
      ::= { jdbcOracleDataSourceRuntimeEntry 33  }
   
   
   jdbcOracleDataSourceRuntimeServiceName OBJECT-TYPE
      SYNTAX      OCTET STRING
      MAX-ACCESS  read-only
      STATUS      current
      DESCRIPTION "The database service name for this RAC data source. "
      ::= { jdbcOracleDataSourceRuntimeEntry 34  }
   
   
   jdbcOracleDataSourceRuntimeWaitingForConnectionSuccessTotal OBJECT-TYPE
      SYNTAX      Counter64
      MAX-ACCESS  read-only
      STATUS      current
      DESCRIPTION "The cumulative, running count of requests for a connection from this data source that had to wait before getting a connection and eventually succeeded in getting a connection. "
      ::= { jdbcOracleDataSourceRuntimeEntry 35  }
   
   
   jdbcOracleDataSourceRuntimeNumUnavailable OBJECT-TYPE
      SYNTAX      Integer32
      MAX-ACCESS  read-only
      STATUS      current
      DESCRIPTION "The number of connections currently in use by applications or being tested in this instance of the data source. "
      ::= { jdbcOracleDataSourceRuntimeEntry 36  }
   
   
   jdbcOracleDataSourceRuntimePrepStmtCacheAddCount OBJECT-TYPE
      SYNTAX      Counter64
      MAX-ACCESS  read-only
      STATUS      current
      DESCRIPTION "The cumulative, running count of the number of statements added to the statement cache.  Each connection in the connection pool has its own cache of statements. This number is the sum of the number of statements added to the caches for all connections in the connection pool. "
      ::= { jdbcOracleDataSourceRuntimeEntry 37  }
   
   
   jdbcOracleDataSourceRuntimeDriverName OBJECT-TYPE
      SYNTAX      OCTET STRING
      MAX-ACCESS  read-only
      STATUS      current
      DESCRIPTION " The product name of the JDBC driver that this data source is configured to use.  "
      ::= { jdbcOracleDataSourceRuntimeEntry 38  }
   
   
   jdbcOracleDataSourceRuntimeNumAvailable OBJECT-TYPE
      SYNTAX      Integer32
      MAX-ACCESS  read-only
      STATUS      current
      DESCRIPTION "The number of database connections that are currently idle and  available to be used by applications in this instance of the data source. "
      ::= { jdbcOracleDataSourceRuntimeEntry 39  }
   
   
   jdbcOracleDataSourceRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { jdbcOracleDataSourceRuntimeEntry 40  }
   
   
   jdbcOracleDataSourceRuntimeName OBJECT-TYPE
      SYNTAX      OCTET STRING
      MAX-ACCESS  read-only
      STATUS      current
      DESCRIPTION "The name of this configuration. WebLogic Server uses an MBean to implement and persist the configuration. "
      ::= { jdbcOracleDataSourceRuntimeEntry 41  }
   
   
   jdbcOracleDataSourceRuntimeState OBJECT-TYPE
      SYNTAX      OCTET STRING
      MAX-ACCESS  read-only
      STATUS      current
      DESCRIPTION "The current state of the data source. Possible states are: Running - the data source is enabled (deployed and not Suspended). This is the normal state of the data source. This state includes conditions when the database server is not available and the data source is created (creation retry must be enabled) or when all connections have failed connection tests (on creation, on reserve, or periodic testing). Suspended - the data source has been disabled. Shutdown - the data source is shutdown and all database connections have been closed. Overloaded - all resources in pool are in use. Unknown - the data source state is unknown. "
      ::= { jdbcOracleDataSourceRuntimeEntry 42  }
   
   
   jdbcOracleDataSourceRuntimeConnectionDelayTime OBJECT-TYPE
      SYNTAX      Integer32
      MAX-ACCESS  read-only
      STATUS      current
      DESCRIPTION "The average amount of time, in milliseconds, that it takes to create a physical connection to the database.  The value is calculated as summary of all times to connect divided by the total number of connections. "
      ::= { jdbcOracleDataSourceRuntimeEntry 43  }
   
   
   jdbcOracleDataSourceRuntimeDeploymentState OBJECT-TYPE
      SYNTAX      Integer32
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jdbcOracleDataSourceRuntimeEntry 44  }
   
   
   jdbcOracleDataSourceRuntimeCurrCapacity OBJECT-TYPE
      SYNTAX      Integer32
      MAX-ACCESS  read-only
      STATUS      current
      DESCRIPTION "The current count of JDBC connections in the connection pool in the data source. "
      ::= { jdbcOracleDataSourceRuntimeEntry 45  }
   
   
   jdbcOracleDataSourceRuntimeRepurposeCount OBJECT-TYPE
      SYNTAX      Counter64
      MAX-ACCESS  read-only
      STATUS      current
      DESCRIPTION "The number of times connections have been repurposed since the datasource was deployed. "
      ::= { jdbcOracleDataSourceRuntimeEntry 46  }
   
   
   jdbcOracleDataSourceRuntimeUnresolvedTotalCount OBJECT-TYPE
      SYNTAX      Counter64
      MAX-ACCESS  read-only
      STATUS      current
      DESCRIPTION "The cumulative total number of commit outcomes unsuccessfully resolved in this data source since the data source was deployed. This does not refer to the number of outcome query retries used to resolve the outcomes. "
      ::= { jdbcOracleDataSourceRuntimeEntry 47  }
   
   
   jdbcOracleDataSourceRuntimeResolvedAsCommittedTotalCount OBJECT-TYPE
      SYNTAX      Counter64
      MAX-ACCESS  read-only
      STATUS      current
      DESCRIPTION "The cumulative total number of commit outcomes successfully resolved as committed in this data source since the data source was deployed. This does not refer to the number of outcome query retries used to resolve the outcomes. "
      ::= { jdbcOracleDataSourceRuntimeEntry 48  }
   
   
   jdbcOracleDataSourceRuntimeCommitOutcomeRetryTotalCount OBJECT-TYPE
      SYNTAX      Counter64
      MAX-ACCESS  read-only
      STATUS      current
      DESCRIPTION "The cumulative total number of commit outcome query retries conducted before resolving the outcome or exceeding the retry seconds in this data source since the data source was deployed. "
      ::= { jdbcOracleDataSourceRuntimeEntry 49  }
   
   
   jdbcOracleDataSourceRuntimeResolvedAsNotCommittedTotalCount OBJECT-TYPE
      SYNTAX      Counter64
      MAX-ACCESS  read-only
      STATUS      current
      DESCRIPTION "The cumulative total number of commit outcomes successfully resolved as not committed in this data source since the data source was deployed. This does not refer to the number of outcome query retries used to resolve the outcomes. "
      ::= { jdbcOracleDataSourceRuntimeEntry 50  }
   
   
   jdbcOracleDataSourceRuntimeFailedRepurposeCount OBJECT-TYPE
      SYNTAX      Counter64
      MAX-ACCESS  read-only
      STATUS      current
      DESCRIPTION "The number of repurpose errors that have occurred since the datasource was deployed. "
      ::= { jdbcOracleDataSourceRuntimeEntry 51  }
   
   
   onsClientRuntimeTable OBJECT-TYPE
      SYNTAX      SEQUENCE OF OnsClientRuntimeEntry
      MAX-ACCESS  not-accessible
      STATUS      current
      DESCRIPTION "Runtime MBean that represents an ONS client configuration that is associated with a RAC JDBC data source. "
      ::= { wls 1770  }
      
   
   onsClientRuntimeEntry OBJECT-TYPE
      SYNTAX      OnsClientRuntimeEntry
      MAX-ACCESS  not-accessible
      STATUS      current
      DESCRIPTION "Generated SNMP Table Entry."
      INDEX { onsClientRuntimeIndex}
      ::= { onsClientRuntimeTable 1 }
      
   OnsClientRuntimeEntry ::=
      SEQUENCE
      {
         onsClientRuntimeIndex OCTET STRING,
         onsClientRuntimeObjectName OCTET STRING,
         onsClientRuntimeType OCTET STRING,
         onsClientRuntimeName OCTET STRING
      }
      
   
   onsClientRuntimeIndex OBJECT-TYPE
      SYNTAX      OCTET STRING
      MAX-ACCESS  not-accessible
      STATUS      current
      DESCRIPTION "Index column"
      ::= { onsClientRuntimeEntry 1  }
   
   
   onsClientRuntimeObjectName OBJECT-TYPE
      SYNTAX      OCTET STRING
      MAX-ACCESS  read-only
      STATUS      current
      DESCRIPTION "ObjectName column"
      ::= { onsClientRuntimeEntry 2  }
   
   
   onsClientRuntimeType OBJECT-TYPE
      SYNTAX      OCTET STRING
      MAX-ACCESS  read-only
      STATUS      current
      DESCRIPTION "Returns the type of the MBean. "
      ::= { onsClientRuntimeEntry 3  }
   
   
   onsClientRuntimeName OBJECT-TYPE
      SYNTAX      OCTET STRING
      MAX-ACCESS  read-only
      STATUS      current
      DESCRIPTION "The name of this configuration. WebLogic Server uses an MBean to implement and persist the configuration. "
      ::= { onsClientRuntimeEntry 4  }
   
   
   onsDaemonRuntimeTable OBJECT-TYPE
      SYNTAX      SEQUENCE OF OnsDaemonRuntimeEntry
      MAX-ACCESS  not-accessible
      STATUS      current
      DESCRIPTION "Runtime MBean that represents an ONS client configuration that is associated with a RAC JDBC data source. "
      ::= { wls 1775  }
      
   
   onsDaemonRuntimeEntry OBJECT-TYPE
      SYNTAX      OnsDaemonRuntimeEntry
      MAX-ACCESS  not-accessible
      STATUS      current
      DESCRIPTION "Generated SNMP Table Entry."
      INDEX { onsDaemonRuntimeIndex}
      ::= { onsDaemonRuntimeTable 1 }
      
   OnsDaemonRuntimeEntry ::=
      SEQUENCE
      {
         onsDaemonRuntimeIndex OCTET STRING,
         onsDaemonRuntimeObjectName OCTET STRING,
         onsDaemonRuntimeHost OCTET STRING,
         onsDaemonRuntimeType OCTET STRING,
         onsDaemonRuntimeName OCTET STRING,
         onsDaemonRuntimeStatus OCTET STRING,
         onsDaemonRuntimePort Integer32
      }
      
   
   onsDaemonRuntimeIndex OBJECT-TYPE
      SYNTAX      OCTET STRING
      MAX-ACCESS  not-accessible
      STATUS      current
      DESCRIPTION "Index column"
      ::= { onsDaemonRuntimeEntry 1  }
   
   
   onsDaemonRuntimeObjectName OBJECT-TYPE
      SYNTAX      OCTET STRING
      MAX-ACCESS  read-only
      STATUS      current
      DESCRIPTION "ObjectName column"
      ::= { onsDaemonRuntimeEntry 2  }
   
   
   onsDaemonRuntimeHost OBJECT-TYPE
      SYNTAX      OCTET STRING
      MAX-ACCESS  read-only
      STATUS      current
      DESCRIPTION "The host address of the ONS daemon. "
      ::= { onsDaemonRuntimeEntry 3  }
   
   
   onsDaemonRuntimeType OBJECT-TYPE
      SYNTAX      OCTET STRING
      MAX-ACCESS  read-only
      STATUS      current
      DESCRIPTION "Returns the type of the MBean. "
      ::= { onsDaemonRuntimeEntry 4  }
   
   
   onsDaemonRuntimeName OBJECT-TYPE
      SYNTAX      OCTET STRING
      MAX-ACCESS  read-only
      STATUS      current
      DESCRIPTION "The name of this configuration. WebLogic Server uses an MBean to implement and persist the configuration. "
      ::= { onsDaemonRuntimeEntry 5  }
   
   
   onsDaemonRuntimeStatus OBJECT-TYPE
      SYNTAX      OCTET STRING
      MAX-ACCESS  read-only
      STATUS      current
      DESCRIPTION "The status of the ONS daemon. "
      ::= { onsDaemonRuntimeEntry 6  }
   
   
   onsDaemonRuntimePort OBJECT-TYPE
      SYNTAX      Integer32
      MAX-ACCESS  read-only
      STATUS      current
      DESCRIPTION "The port of the ONS daemon. "
      ::= { onsDaemonRuntimeEntry 7  }
   
   
   authModuleTable OBJECT-TYPE
      SYNTAX      SEQUENCE OF AuthModuleEntry
      MAX-ACCESS  not-accessible
      STATUS      current
      DESCRIPTION " "
      ::= { wls 1780  }
      
   
   authModuleEntry OBJECT-TYPE
      SYNTAX      AuthModuleEntry
      MAX-ACCESS  not-accessible
      STATUS      current
      DESCRIPTION "Generated SNMP Table Entry."
      INDEX { authModuleIndex}
      ::= { authModuleTable 1 }
      
   AuthModuleEntry ::=
      SEQUENCE
      {
         authModuleIndex      OCTET STRING,
         authModuleObjectName OCTET STRING,
         authModuleType       OCTET STRING,
         authModuleModuleType OCTET STRING,
         authModuleName       OCTET STRING,
         authModuleClassName  OCTET STRING,
         authModuleTags       OCTET STRING
      }
      
   
   authModuleIndex OBJECT-TYPE
      SYNTAX      OCTET STRING
      MAX-ACCESS  not-accessible
      STATUS      current
      DESCRIPTION "Index column"
      ::= { authModuleEntry 1  }
   
   
   authModuleObjectName OBJECT-TYPE
      SYNTAX      OCTET STRING
      MAX-ACCESS  read-only
      STATUS      current
      DESCRIPTION "ObjectName column"
      ::= { authModuleEntry 2  }
   
   
   authModuleType OBJECT-TYPE
      SYNTAX      OCTET STRING
      MAX-ACCESS  read-only
      STATUS      current
      DESCRIPTION "Returns the type of the MBean. "
      ::= { authModuleEntry 3  }
   
   
   authModuleModuleType OBJECT-TYPE
      SYNTAX      OCTET STRING
      MAX-ACCESS  read-only
      STATUS      current
      DESCRIPTION "get the module type - that is: Client or Server "
      ::= { authModuleEntry 4  }
   
   
   authModuleName OBJECT-TYPE
      SYNTAX      OCTET STRING
      MAX-ACCESS  read-only
      STATUS      current
      DESCRIPTION "The user-specified name of this MBean instance.  This name is included as one of the key properties in the MBean's javax.management.ObjectName:  Name=user-specified-name "
      ::= { authModuleEntry 5  }
   
   
   authModuleClassName OBJECT-TYPE
      SYNTAX      OCTET STRING
      MAX-ACCESS  read-only
      STATUS      current
      DESCRIPTION "get the classname for the authentication module "
      ::= { authModuleEntry 6  }
   
   
   authModuleTags OBJECT-TYPE
      SYNTAX      OCTET STRING
      MAX-ACCESS  read-only
      STATUS      current
      DESCRIPTION "Return all tags on this Configuration MBean "
      ::= { authModuleEntry 7  }
   
   
   certRevocCaTable OBJECT-TYPE
      SYNTAX      SEQUENCE OF CertRevocCaEntry
      MAX-ACCESS  not-accessible
      STATUS      current
      DESCRIPTION "This MBean represents the configuration of certificate revocation checking for a specific certificate authority. Default values for attributes in this MBean are derived from CertRevocMBean. "
      ::= { wls 1785  }
      
   
   certRevocCaEntry OBJECT-TYPE
      SYNTAX      CertRevocCaEntry
      MAX-ACCESS  not-accessible
      STATUS      current
      DESCRIPTION "Generated SNMP Table Entry."
      INDEX { certRevocCaIndex}
      ::= { certRevocCaTable 1 }
      
   CertRevocCaEntry ::=
      SEQUENCE
      {
         certRevocCaIndex     OCTET STRING,
         certRevocCaObjectName OCTET STRING,
         certRevocCaOcspResponderCertSubjectName OCTET STRING,
         certRevocCaType      OCTET STRING,
         certRevocCaOcspResponderExplicitTrustMethod OCTET STRING,
         certRevocCaCrlDpEnabled OCTET STRING,
         certRevocCaCrlDpDownloadTimeout Counter64,
         certRevocCaCrlDpUrlUsage OCTET STRING,
         certRevocCaMethodOrder OCTET STRING,
         certRevocCaOcspResponderUrl OCTET STRING,
         certRevocCaOcspResponderCertSerialNumber OCTET STRING,
         certRevocCaOcspTimeTolerance Integer32,
         certRevocCaFailOnUnknownRevocStatus OCTET STRING,
         certRevocCaCrlDpBackgroundDownloadEnabled OCTET STRING,
         certRevocCaDistinguishedName OCTET STRING,
         certRevocCaOcspResponseCacheEnabled OCTET STRING,
         certRevocCaOcspResponderUrlUsage OCTET STRING,
         certRevocCaCheckingDisabled OCTET STRING,
         certRevocCaName      OCTET STRING,
         certRevocCaOcspResponderCertIssuerName OCTET STRING,
         certRevocCaCrlDpUrl  OCTET STRING,
         certRevocCaOcspNonceEnabled OCTET STRING,
         certRevocCaOcspResponseTimeout Counter64,
         certRevocCaTags      OCTET STRING
      }
      
   
   certRevocCaIndex OBJECT-TYPE
      SYNTAX      OCTET STRING
      MAX-ACCESS  not-accessible
      STATUS      current
      DESCRIPTION "Index column"
      ::= { certRevocCaEntry 1  }
   
   
   certRevocCaObjectName OBJECT-TYPE
      SYNTAX      OCTET STRING
      MAX-ACCESS  read-only
      STATUS      current
      DESCRIPTION "ObjectName column"
      ::= { certRevocCaEntry 2  }
   
   
   certRevocCaOcspResponderCertSubjectName OBJECT-TYPE
      SYNTAX      OCTET STRING
      MAX-ACCESS  read-only
      STATUS      current
      DESCRIPTION "For this CA, determines the explicitly trusted OCSP responder certificate subject name, when the attribute returned by getOcspResponderExplicitTrustMethod is 'USE_SUBJECT'.  The subject name is formatted as a distinguished name per RFC 2253, for example 'CN=CertGenCAB, OU=FOR TESTING ONLY, O=MyOrganization, L=MyTown, ST=MyState, C=US'.  In cases where the subject name alone is not sufficient to uniquely identify the certificate, then both the {@link #getOcspResponderCertIssuerName} and {@link #getOcspResponderCertSerialNumber} may be used instead. "
      ::= { certRevocCaEntry 3  }
   
   
   certRevocCaType OBJECT-TYPE
      SYNTAX      OCTET STRING
      MAX-ACCESS  read-only
      STATUS      current
      DESCRIPTION "Returns the type of the MBean. "
      ::= { certRevocCaEntry 4  }
   
   
   certRevocCaOcspResponderExplicitTrustMethod OBJECT-TYPE
      SYNTAX      OCTET STRING
      MAX-ACCESS  read-only
      STATUS      current
      DESCRIPTION "For this CA, determines whether the OCSP Explicit Trust model is enabled and how the trusted certificate is specified.  The valid values:  'NONE' Explicit Trust is disabled 'USE_SUBJECT' Identify the trusted certificate using the subject DN specified in the attribute {@link #getOcspResponderCertSubjectName}. 'USE_ISSUER_SERIAL_NUMBER' Identify the trusted certificate using the issuer DN and certificate serial number specified in the attributes {@link #getOcspResponderCertIssuerName} and {@link #getOcspResponderCertSerialNumber}, respectively.  "
      ::= { certRevocCaEntry 5  }
   
   
   certRevocCaCrlDpEnabled OBJECT-TYPE
      SYNTAX      OCTET STRING
      MAX-ACCESS  read-only
      STATUS      current
      DESCRIPTION "For this CA, determines whether the CRL Distribution Point processing to update the local CRL cache is enabled. "
      ::= { certRevocCaEntry 6  }
   
   
   certRevocCaCrlDpDownloadTimeout OBJECT-TYPE
      SYNTAX      Counter64
      MAX-ACCESS  read-only
      STATUS      current
      DESCRIPTION "For this CA, determines the overall timeout for the Distribution Point CRL download, expressed in seconds.  The valid range is 1 thru 300 seconds. "
      ::= { certRevocCaEntry 7  }
   
   
   certRevocCaCrlDpUrlUsage OBJECT-TYPE
      SYNTAX      OCTET STRING
      MAX-ACCESS  read-only
      STATUS      current
      DESCRIPTION "For this CA, determines how getCrlDpUrl is used: as failover in case the URL in the certificate CRLDistributionPoints extension is invalid or not found, or as a value overriding the URL found in the certificate CRLDistributionPoints extension. "
      ::= { certRevocCaEntry 8  }
   
   
   certRevocCaMethodOrder OBJECT-TYPE
      SYNTAX      OCTET STRING
      MAX-ACCESS  read-only
      STATUS      current
      DESCRIPTION "For this CA, determines the certificate revocation checking method order.  NOTE THAT omission of a specific method disables that method. "
      ::= { certRevocCaEntry 9  }
   
   
   certRevocCaOcspResponderUrl OBJECT-TYPE
      SYNTAX      OCTET STRING
      MAX-ACCESS  read-only
      STATUS      current
      DESCRIPTION "For this CA, determines the OCSP responder URL to use as failover or override for the URL found in the certificate AIA. The usage is determined by getOcspResponderUrlUsage. "
      ::= { certRevocCaEntry 10  }
   
   
   certRevocCaOcspResponderCertSerialNumber OBJECT-TYPE
      SYNTAX      OCTET STRING
      MAX-ACCESS  read-only
      STATUS      current
      DESCRIPTION "For this CA, determines the explicitly trusted OCSP responder certificate serial number, when the attribute returned by getOcspResponderExplicitTrustMethod is 'USE_ISSUER_SERIAL_NUMBER'.  The serial number is formatted as a hexidecimal string, with optional colon or space separators, for example '2A:FF:00'.  When {@link #getOcspResponderCertSerialNumber} returns a non-null value then the {@link #getOcspResponderCertIssuerName} must also be set. "
      ::= { certRevocCaEntry 11  }
   
   
   certRevocCaOcspTimeTolerance OBJECT-TYPE
      SYNTAX      Integer32
      MAX-ACCESS  read-only
      STATUS      current
      DESCRIPTION "For this CA, determines the time tolerance value for handling clock-skew differences between clients and responders, expressed in seconds.  The validity period of the response is extended both into the future and into the past by the specified amount of time, effectively widening the validity interval.  The value is &gt;=0 and &lt;=900. The maximum allowed tolerance is 15 minutes. "
      ::= { certRevocCaEntry 12  }
   
   
   certRevocCaFailOnUnknownRevocStatus OBJECT-TYPE
      SYNTAX      OCTET STRING
      MAX-ACCESS  read-only
      STATUS      current
      DESCRIPTION "For this CA, determines whether certificate path checking should fail, if revocation status could not be determined. "
      ::= { certRevocCaEntry 13  }
   
   
   certRevocCaCrlDpBackgroundDownloadEnabled OBJECT-TYPE
      SYNTAX      OCTET STRING
      MAX-ACCESS  read-only
      STATUS      current
      DESCRIPTION "For this CA, determines whether the CRL Distribution Point background downloading, to automatically update the local CRL cache, is enabled. "
      ::= { certRevocCaEntry 14  }
   
   
   certRevocCaDistinguishedName OBJECT-TYPE
      SYNTAX      OCTET STRING
      MAX-ACCESS  read-only
      STATUS      current
      DESCRIPTION "Determines the identity of this per-CA configuration using the distinguished name (defined in RFC 2253), which is used in certificates issued by the represented certificate authority.  For example:  &quot;CN=CertGenCAB, OU=FOR TESTING ONLY, O=MyOrganization, L=MyTown, ST=MyState, C=US&quot;  This will be used to match this configuration to issued certificates requiring revocation checking. "
      ::= { certRevocCaEntry 15  }
   
   
   certRevocCaOcspResponseCacheEnabled OBJECT-TYPE
      SYNTAX      OCTET STRING
      MAX-ACCESS  read-only
      STATUS      current
      DESCRIPTION "For this CA, determines whether the OCSP response local cache is enabled. "
      ::= { certRevocCaEntry 16  }
   
   
   certRevocCaOcspResponderUrlUsage OBJECT-TYPE
      SYNTAX      OCTET STRING
      MAX-ACCESS  read-only
      STATUS      current
      DESCRIPTION "For this CA, determines how getOcspResponderUrl is used: as failover in case the URL in the certificate AIA is invalid or not found, or as a value overriding the URL found in the certificate AIA. "
      ::= { certRevocCaEntry 17  }
   
   
   certRevocCaCheckingDisabled OBJECT-TYPE
      SYNTAX      OCTET STRING
      MAX-ACCESS  read-only
      STATUS      current
      DESCRIPTION "For this CA, determines whether certificate revocation checking is disabled. "
      ::= { certRevocCaEntry 18  }
   
   
   certRevocCaName OBJECT-TYPE
      SYNTAX      OCTET STRING
      MAX-ACCESS  read-only
      STATUS      current
      DESCRIPTION "The user-specified name of this MBean instance.  This name is included as one of the key properties in the MBean's javax.management.ObjectName:  Name=user-specified-name "
      ::= { certRevocCaEntry 19  }
   
   
   certRevocCaOcspResponderCertIssuerName OBJECT-TYPE
      SYNTAX      OCTET STRING
      MAX-ACCESS  read-only
      STATUS      current
      DESCRIPTION "For this CA, determines the explicitly trusted OCSP responder certificate issuer name, when the attribute returned by getOcspResponderExplicitTrustMethod is 'USE_ISSUER_SERIAL_NUMBER'.  The issuer name is formatted as a distinguished name per RFC 2253, for example 'CN=CertGenCAB, OU=FOR TESTING ONLY, O=MyOrganization, L=MyTown, ST=MyState, C=US'.  When {@link #getOcspResponderCertIssuerName} returns a non-null value then the {@link #getOcspResponderCertSerialNumber} must also be set. "
      ::= { certRevocCaEntry 20  }
   
   
   certRevocCaCrlDpUrl OBJECT-TYPE
      SYNTAX      OCTET STRING
      MAX-ACCESS  read-only
      STATUS      current
      DESCRIPTION "For this CA, determines the CRL Distribution Point URL to use as failover or override for the URL found in the CRLDistributionPoints extension in the certificate. "
      ::= { certRevocCaEntry 21  }
   
   
   certRevocCaOcspNonceEnabled OBJECT-TYPE
      SYNTAX      OCTET STRING
      MAX-ACCESS  read-only
      STATUS      current
      DESCRIPTION "For this CA, determines whether a nonce is sent with OCSP requests, to force a fresh (not pre-signed) response. "
      ::= { certRevocCaEntry 22  }
   
   
   certRevocCaOcspResponseTimeout OBJECT-TYPE
      SYNTAX      Counter64
      MAX-ACCESS  read-only
      STATUS      current
      DESCRIPTION "For this CA, determines the timeout for the OCSP response, expressed in seconds.  The valid range is 1 thru 300 seconds. "
      ::= { certRevocCaEntry 23  }
   
   
   certRevocCaTags OBJECT-TYPE
      SYNTAX      OCTET STRING
      MAX-ACCESS  read-only
      STATUS      current
      DESCRIPTION "Return all tags on this Configuration MBean "
      ::= { certRevocCaEntry 24  }
   
   
   certRevocTable OBJECT-TYPE
      SYNTAX      SEQUENCE OF CertRevocEntry
      MAX-ACCESS  not-accessible
      STATUS      current
      DESCRIPTION "This MBean represents the configuration of the certificate revocation checking across all certificate authorities. Many of the attributes in this MBean may be overridden per certificate authority using the specific CertRevocCaMBean. "
      ::= { wls 1790  }
      
   
   certRevocEntry OBJECT-TYPE
      SYNTAX      CertRevocEntry
      MAX-ACCESS  not-accessible
      STATUS      current
      DESCRIPTION "Generated SNMP Table Entry."
      INDEX { certRevocIndex}
      ::= { certRevocTable 1 }
      
   CertRevocEntry ::=
      SEQUENCE
      {
         certRevocIndex       OCTET STRING,
         certRevocObjectName  OCTET STRING,
         certRevocType        OCTET STRING,
         certRevocCrlDpEnabled OCTET STRING,
         certRevocCrlDpDownloadTimeout Counter64,
         certRevocOcspResponseCacheCapacity Integer32,
         certRevocMethodOrder OCTET STRING,
         certRevocOcspTimeTolerance Integer32,
         certRevocCheckingEnabled OCTET STRING,
         certRevocFailOnUnknownRevocStatus OCTET STRING,
         certRevocCrlDpBackgroundDownloadEnabled OCTET STRING,
         certRevocOcspResponseCacheEnabled OCTET STRING,
         certRevocName        OCTET STRING,
         certRevocCrlCacheRefreshPeriodPercent Integer32,
         certRevocCrlCacheType OCTET STRING,
         certRevocOcspNonceEnabled OCTET STRING,
         certRevocOcspResponseTimeout Counter64,
         certRevocOcspResponseCacheRefreshPeriodPercent Integer32,
         certRevocTags        OCTET STRING
      }
      
   
   certRevocIndex OBJECT-TYPE
      SYNTAX      OCTET STRING
      MAX-ACCESS  not-accessible
      STATUS      current
      DESCRIPTION "Index column"
      ::= { certRevocEntry 1  }
   
   
   certRevocObjectName OBJECT-TYPE
      SYNTAX      OCTET STRING
      MAX-ACCESS  read-only
      STATUS      current
      DESCRIPTION "ObjectName column"
      ::= { certRevocEntry 2  }
   
   
   certRevocType OBJECT-TYPE
      SYNTAX      OCTET STRING
      MAX-ACCESS  read-only
      STATUS      current
      DESCRIPTION "Returns the type of the MBean. "
      ::= { certRevocEntry 3  }
   
   
   certRevocCrlDpEnabled OBJECT-TYPE
      SYNTAX      OCTET STRING
      MAX-ACCESS  read-only
      STATUS      current
      DESCRIPTION "Determines whether the CRL Distribution Point processing to update the local CRL cache is enabled. "
      ::= { certRevocEntry 4  }
   
   
   certRevocCrlDpDownloadTimeout OBJECT-TYPE
      SYNTAX      Counter64
      MAX-ACCESS  read-only
      STATUS      current
      DESCRIPTION "Determines the overall timeout for the Distribution Point CRL download, expressed in seconds.  The valid range is 1 thru 300 seconds. "
      ::= { certRevocEntry 5  }
   
   
   certRevocOcspResponseCacheCapacity OBJECT-TYPE
      SYNTAX      Integer32
      MAX-ACCESS  read-only
      STATUS      current
      DESCRIPTION "Determines the maximum number of entries supported by the OCSP response local cache. The minimum value is 1. "
      ::= { certRevocEntry 6  }
   
   
   certRevocMethodOrder OBJECT-TYPE
      SYNTAX      OCTET STRING
      MAX-ACCESS  read-only
      STATUS      current
      DESCRIPTION "Determines the certificate revocation checking method order.  NOTE that omission of a specific method disables that method. "
      ::= { certRevocEntry 9  }
   
   
   certRevocOcspTimeTolerance OBJECT-TYPE
      SYNTAX      Integer32
      MAX-ACCESS  read-only
      STATUS      current
      DESCRIPTION "Determines the time tolerance value for handling clock-skew differences between clients and responders, expressed in seconds.  The validity period of the response is extended both into the future and into the past by the specified amount of time, effectively widening the validity interval.  The value is &gt;=0 and &lt;=900. The maximum allowed tolerance is 15 minutes. "
      ::= { certRevocEntry 11  }
   
   
   certRevocCheckingEnabled OBJECT-TYPE
      SYNTAX      OCTET STRING
      MAX-ACCESS  read-only
      STATUS      current
      DESCRIPTION "Determines whether certificate revocation checking is enabled. "
      ::= { certRevocEntry 12  }
   
   
   certRevocFailOnUnknownRevocStatus OBJECT-TYPE
      SYNTAX      OCTET STRING
      MAX-ACCESS  read-only
      STATUS      current
      DESCRIPTION "Determines whether certificate path checking should fail, if revocation status could not be determined. "
      ::= { certRevocEntry 13  }
   
   
   certRevocCrlDpBackgroundDownloadEnabled OBJECT-TYPE
      SYNTAX      OCTET STRING
      MAX-ACCESS  read-only
      STATUS      current
      DESCRIPTION "Determines whether the CRL Distribution Point background downloading, to automatically update the local CRL cache, is enabled. "
      ::= { certRevocEntry 14  }
   
   
   certRevocOcspResponseCacheEnabled OBJECT-TYPE
      SYNTAX      OCTET STRING
      MAX-ACCESS  read-only
      STATUS      current
      DESCRIPTION "Determines whether the OCSP response local cache is enabled. "
      ::= { certRevocEntry 15  }
   
   
   certRevocName OBJECT-TYPE
      SYNTAX      OCTET STRING
      MAX-ACCESS  read-only
      STATUS      current
      DESCRIPTION "The user-specified name of this MBean instance.  This name is included as one of the key properties in the MBean's javax.management.ObjectName:  Name=user-specified-name "
      ::= { certRevocEntry 16  }
   
   
   certRevocCrlCacheRefreshPeriodPercent OBJECT-TYPE
      SYNTAX      Integer32
      MAX-ACCESS  read-only
      STATUS      current
      DESCRIPTION "Determines the refresh period for the CRL local cache, expressed as a percentage of the validity period of the CRL.  For example, for a validity period of 10 hours, a value of 10% specifies a refresh every 1 hour.  The validity period is determined by the CRL, and is calculated as the (next reported update time) - (this update time).  The valid range is 1 through 100. "
      ::= { certRevocEntry 17  }
   
   
   certRevocCrlCacheType OBJECT-TYPE
      SYNTAX      OCTET STRING
      MAX-ACCESS  read-only
      STATUS      current
      DESCRIPTION "Determines the type of CRL cache, related to the physical storage of the CRLs. The ldap CRL cache type can be specified, but is not currently supported.  The value specified in this attribute determines which related CrlCacheType* attributes apply. "
      ::= { certRevocEntry 18  }
   
   
   certRevocOcspNonceEnabled OBJECT-TYPE
      SYNTAX      OCTET STRING
      MAX-ACCESS  read-only
      STATUS      current
      DESCRIPTION "Determines whether a nonce is sent with OCSP requests, to force a fresh (not pre-signed) response. "
      ::= { certRevocEntry 19  }
   
   
   certRevocOcspResponseTimeout OBJECT-TYPE
      SYNTAX      Counter64
      MAX-ACCESS  read-only
      STATUS      current
      DESCRIPTION "Determines the timeout for the OCSP response, expressed in seconds.  The valid range is 1 thru 300 seconds. "
      ::= { certRevocEntry 20  }
   
   
   certRevocOcspResponseCacheRefreshPeriodPercent OBJECT-TYPE
      SYNTAX      Integer32
      MAX-ACCESS  read-only
      STATUS      current
      DESCRIPTION "Determines the refresh period for the OCSP response local cache, expressed as a percentage of the validity period of the response.  For example, for a validity period of 10 hours, a value of 10% specifies a refresh every 1 hour.  The validity period is determined by the OCSP response, and is calculated as the (next reported update time) - (this update time).  The valid range is 1 through 100. "
      ::= { certRevocEntry 21  }
   
   
   certRevocTags OBJECT-TYPE
      SYNTAX      OCTET STRING
      MAX-ACCESS  read-only
      STATUS      current
      DESCRIPTION "Return all tags on this Configuration MBean "
      ::= { certRevocEntry 22  }
   
   
   coherenceCacheConfigTable OBJECT-TYPE
      SYNTAX      SEQUENCE OF CoherenceCacheConfigEntry
      MAX-ACCESS  not-accessible
      STATUS      current
      DESCRIPTION "Information that represents a Coherence cache configuration. "
      ::= { wls 1795  }
      
   
   coherenceCacheConfigEntry OBJECT-TYPE
      SYNTAX      CoherenceCacheConfigEntry
      MAX-ACCESS  not-accessible
      STATUS      current
      DESCRIPTION "Generated SNMP Table Entry."
      INDEX { coherenceCacheConfigIndex}
      ::= { coherenceCacheConfigTable 1 }
      
   CoherenceCacheConfigEntry ::=
      SEQUENCE
      {
         coherenceCacheConfigIndex OCTET STRING,
         coherenceCacheConfigObjectName OCTET STRING,
         coherenceCacheConfigType OCTET STRING,
         coherenceCacheConfigCompatibilityName OCTET STRING,
         coherenceCacheConfigModuleType OCTET STRING,
         coherenceCacheConfigName OCTET STRING,
         coherenceCacheConfigCacheConfigurationFile OCTET STRING,
         coherenceCacheConfigJNDIName OCTET STRING,
         coherenceCacheConfigTags OCTET STRING
      }
      
   
   coherenceCacheConfigIndex OBJECT-TYPE
      SYNTAX      OCTET STRING
      MAX-ACCESS  not-accessible
      STATUS      current
      DESCRIPTION "Index column"
      ::= { coherenceCacheConfigEntry 1  }
   
   
   coherenceCacheConfigObjectName OBJECT-TYPE
      SYNTAX      OCTET STRING
      MAX-ACCESS  read-only
      STATUS      current
      DESCRIPTION "ObjectName column"
      ::= { coherenceCacheConfigEntry 2  }
   
   
   coherenceCacheConfigType OBJECT-TYPE
      SYNTAX      OCTET STRING
      MAX-ACCESS  read-only
      STATUS      current
      DESCRIPTION "Returns the type of the MBean. "
      ::= { coherenceCacheConfigEntry 3  }
   
   
   coherenceCacheConfigCompatibilityName OBJECT-TYPE
      SYNTAX      OCTET STRING
      MAX-ACCESS  read-only
      STATUS      current
      DESCRIPTION " This is only set for beans created as a result of conversion from an 8.1 application configured using ApplicationMBean and ComponentMBean.  Standalone modules in 8.1 have both an ApplicationMBean name and ComponentMBean name. This attribute stores the name of the latter, to be used when the server creates the transient ComponentMBean for backward compatibility. "
      ::= { coherenceCacheConfigEntry 4  }
   
   
   coherenceCacheConfigModuleType OBJECT-TYPE
      SYNTAX      OCTET STRING
      MAX-ACCESS  read-only
      STATUS      current
      DESCRIPTION "The values match those defined by jsr88. This attribute may move to another MBean. "
      ::= { coherenceCacheConfigEntry 5  }
   
   
   coherenceCacheConfigName OBJECT-TYPE
      SYNTAX      OCTET STRING
      MAX-ACCESS  read-only
      STATUS      current
      DESCRIPTION "Unique identifier for this bean instance. "
      ::= { coherenceCacheConfigEntry 6  }
   
   
   coherenceCacheConfigCacheConfigurationFile OBJECT-TYPE
      SYNTAX      OCTET STRING
      MAX-ACCESS  read-only
      STATUS      current
      DESCRIPTION "Return the cache configuration file being used by this CoherenceCacheConfigMBean. "
      ::= { coherenceCacheConfigEntry 7  }
   
   
   coherenceCacheConfigJNDIName OBJECT-TYPE
      SYNTAX      OCTET STRING
      MAX-ACCESS  read-only
      STATUS      current
      DESCRIPTION "The JNDI name this resource will be bound to. "
      ::= { coherenceCacheConfigEntry 8  }
   
   
   coherenceCacheConfigTags OBJECT-TYPE
      SYNTAX      OCTET STRING
      MAX-ACCESS  read-only
      STATUS      current
      DESCRIPTION "Return all tags on this Configuration MBean "
      ::= { coherenceCacheConfigEntry 9  }
   
   
   coherenceMemberConfigTable OBJECT-TYPE
      SYNTAX      SEQUENCE OF CoherenceMemberConfigEntry
      MAX-ACCESS  not-accessible
      STATUS      current
      DESCRIPTION "This class represents Coherence Operational Configuration for a WLS Server that is part of a Coherence Cluster. "
      ::= { wls 1800  }
      
   
   coherenceMemberConfigEntry OBJECT-TYPE
      SYNTAX      CoherenceMemberConfigEntry
      MAX-ACCESS  not-accessible
      STATUS      current
      DESCRIPTION "Generated SNMP Table Entry."
      INDEX { coherenceMemberConfigIndex}
      ::= { coherenceMemberConfigTable 1 }
      
   CoherenceMemberConfigEntry ::=
      SEQUENCE
      {
         coherenceMemberConfigIndex OCTET STRING,
         coherenceMemberConfigObjectName OCTET STRING,
         coherenceMemberConfigType OCTET STRING,
         coherenceMemberConfigCoherenceWebLocalStorageEnabled OCTET STRING,
         coherenceMemberConfigSiteName OCTET STRING,
         coherenceMemberConfigUnicastListenPort Integer32,
         coherenceMemberConfigUnicastPortAutoAdjust OCTET STRING,
         coherenceMemberConfigName OCTET STRING,
         coherenceMemberConfigRoleName OCTET STRING,
         coherenceMemberConfigUnicastListenAddress OCTET STRING,
         coherenceMemberConfigLocalStorageEnabled OCTET STRING,
         coherenceMemberConfigRackName OCTET STRING,
         coherenceMemberConfigManagementProxy OCTET STRING,
         coherenceMemberConfigUnicastPortAutoAdjustAttempts INTEGER,
         coherenceMemberConfigTags OCTET STRING,
         coherenceMemberConfigCoherenceWebFederatedStorageEnabled OCTET STRING
      }
      
   
   coherenceMemberConfigIndex OBJECT-TYPE
      SYNTAX      OCTET STRING
      MAX-ACCESS  not-accessible
      STATUS      current
      DESCRIPTION "Index column"
      ::= { coherenceMemberConfigEntry 1  }
   
   
   coherenceMemberConfigObjectName OBJECT-TYPE
      SYNTAX      OCTET STRING
      MAX-ACCESS  read-only
      STATUS      current
      DESCRIPTION "ObjectName column"
      ::= { coherenceMemberConfigEntry 2  }
   
   
   coherenceMemberConfigType OBJECT-TYPE
      SYNTAX      OCTET STRING
      MAX-ACCESS  read-only
      STATUS      current
      DESCRIPTION "Returns the type of the MBean. "
      ::= { coherenceMemberConfigEntry 3  }
   
   
   coherenceMemberConfigCoherenceWebLocalStorageEnabled OBJECT-TYPE
      SYNTAX      OCTET STRING
      MAX-ACCESS  read-only
      STATUS      current
      DESCRIPTION "Specifies whether Local Storage is enabled for the Coherence Web cluster member  "
      ::= { coherenceMemberConfigEntry 4  }
   
   
   coherenceMemberConfigSiteName OBJECT-TYPE
      SYNTAX      OCTET STRING
      MAX-ACCESS  read-only
      STATUS      current
      DESCRIPTION "Specifies the name of the geographic site where this member is hosted. "
      ::= { coherenceMemberConfigEntry 5  }
   
   
   coherenceMemberConfigUnicastListenPort OBJECT-TYPE
      SYNTAX      Integer32
      MAX-ACCESS  read-only
      STATUS      current
      DESCRIPTION "The port for the Coherence unicast listener. A value of 0 indicates that the unicast listen port value will be assigned automatically to an ephemeral port. "
      ::= { coherenceMemberConfigEntry 6  }
   
   
   coherenceMemberConfigUnicastPortAutoAdjust OBJECT-TYPE
      SYNTAX      OCTET STRING
      MAX-ACCESS  read-only
      STATUS      current
      DESCRIPTION " Specifies whether the unicast port will be automatically incremented if the port cannot be bound because it is already in use.  "
      ::= { coherenceMemberConfigEntry 7  }
   
   
   coherenceMemberConfigName OBJECT-TYPE
      SYNTAX      OCTET STRING
      MAX-ACCESS  read-only
      STATUS      current
      DESCRIPTION "The user-specified name of this MBean instance.  This name is included as one of the key properties in the MBean's javax.management.ObjectName:  Name=user-specified-name "
      ::= { coherenceMemberConfigEntry 8  }
   
   
   coherenceMemberConfigRoleName OBJECT-TYPE
      SYNTAX      OCTET STRING
      MAX-ACCESS  read-only
      STATUS      current
      DESCRIPTION "Specifies a name used to logically group similar members. "
      ::= { coherenceMemberConfigEntry 9  }
   
   
   coherenceMemberConfigUnicastListenAddress OBJECT-TYPE
      SYNTAX      OCTET STRING
      MAX-ACCESS  read-only
      STATUS      current
      DESCRIPTION "The IP address for the Coherence unicast listener. "
      ::= { coherenceMemberConfigEntry 10  }
   
   
   coherenceMemberConfigLocalStorageEnabled OBJECT-TYPE
      SYNTAX      OCTET STRING
      MAX-ACCESS  read-only
      STATUS      current
      DESCRIPTION "Specifies whether or not this member will contribute storage to the Coherence cluster i.e. maintain partitions. This attribute is used only when the WebLogic Server is not part of a WLS Cluster. "
      ::= { coherenceMemberConfigEntry 11  }
   
   
   coherenceMemberConfigRackName OBJECT-TYPE
      SYNTAX      OCTET STRING
      MAX-ACCESS  read-only
      STATUS      current
      DESCRIPTION "Specifies the location within a geographic site where this member is hosted. "
      ::= { coherenceMemberConfigEntry 12  }
   
   
   coherenceMemberConfigManagementProxy OBJECT-TYPE
      SYNTAX      OCTET STRING
      MAX-ACCESS  read-only
      STATUS      current
      DESCRIPTION "Specifies whether or not this server can act as a Coherence Management node. "
      ::= { coherenceMemberConfigEntry 13  }
   
   
   coherenceMemberConfigUnicastPortAutoAdjustAttempts OBJECT-TYPE
      SYNTAX      INTEGER
      MAX-ACCESS  read-only
      STATUS      current
      DESCRIPTION " Get the upper bound of the unicast port. A positive value indicates the unicast port is automatically incremented if the specified port cannot be bound because it is already in use.  "
      ::= { coherenceMemberConfigEntry 14  }
   
   
   coherenceMemberConfigTags OBJECT-TYPE
      SYNTAX      OCTET STRING
      MAX-ACCESS  read-only
      STATUS      current
      DESCRIPTION "Return all tags on this Configuration MBean "
      ::= { coherenceMemberConfigEntry 15  }
   
   
   coherenceMemberConfigCoherenceWebFederatedStorageEnabled OBJECT-TYPE
      SYNTAX      OCTET STRING
      MAX-ACCESS  read-only
      STATUS      current
      DESCRIPTION "Specifies whether Federated Cache Storage is enabled for the Coherence Web cluster member  "
      ::= { coherenceMemberConfigEntry 16  }
   
   
   coherenceTierTable OBJECT-TYPE
      SYNTAX      SEQUENCE OF CoherenceTierEntry
      MAX-ACCESS  not-accessible
      STATUS      current
      DESCRIPTION "This class represents Coherence Tier. A Coherence Tier is formed by one WLS Cluster. "
      ::= { wls 1805  }
      
   
   coherenceTierEntry OBJECT-TYPE
      SYNTAX      CoherenceTierEntry
      MAX-ACCESS  not-accessible
      STATUS      current
      DESCRIPTION "Generated SNMP Table Entry."
      INDEX { coherenceTierIndex}
      ::= { coherenceTierTable 1 }
      
   CoherenceTierEntry ::=
      SEQUENCE
      {
         coherenceTierIndex   OCTET STRING,
         coherenceTierObjectName OCTET STRING,
         coherenceTierType    OCTET STRING,
         coherenceTierCoherenceWebLocalStorageEnabled OCTET STRING,
         coherenceTierName    OCTET STRING,
         coherenceTierLocalStorageEnabled OCTET STRING,
         coherenceTierTags    OCTET STRING,
         coherenceTierCoherenceWebFederatedStorageEnabled OCTET STRING
      }
      
   
   coherenceTierIndex OBJECT-TYPE
      SYNTAX      OCTET STRING
      MAX-ACCESS  not-accessible
      STATUS      current
      DESCRIPTION "Index column"
      ::= { coherenceTierEntry 1  }
   
   
   coherenceTierObjectName OBJECT-TYPE
      SYNTAX      OCTET STRING
      MAX-ACCESS  read-only
      STATUS      current
      DESCRIPTION "ObjectName column"
      ::= { coherenceTierEntry 2  }
   
   
   coherenceTierType OBJECT-TYPE
      SYNTAX      OCTET STRING
      MAX-ACCESS  read-only
      STATUS      current
      DESCRIPTION "Returns the type of the MBean. "
      ::= { coherenceTierEntry 3  }
   
   
   coherenceTierCoherenceWebLocalStorageEnabled OBJECT-TYPE
      SYNTAX      OCTET STRING
      MAX-ACCESS  read-only
      STATUS      current
      DESCRIPTION "Specifies whether Local Storage is enabled for the Coherence*Web cluster tier  "
      ::= { coherenceTierEntry 4  }
   
   
   coherenceTierName OBJECT-TYPE
      SYNTAX      OCTET STRING
      MAX-ACCESS  read-only
      STATUS      current
      DESCRIPTION "The user-specified name of this MBean instance.  This name is included as one of the key properties in the MBean's javax.management.ObjectName:  Name=user-specified-name "
      ::= { coherenceTierEntry 5  }
   
   
   coherenceTierLocalStorageEnabled OBJECT-TYPE
      SYNTAX      OCTET STRING
      MAX-ACCESS  read-only
      STATUS      current
      DESCRIPTION "Specifies whether Local Storage is enabled   "
      ::= { coherenceTierEntry 6  }
   
   
   coherenceTierTags OBJECT-TYPE
      SYNTAX      OCTET STRING
      MAX-ACCESS  read-only
      STATUS      current
      DESCRIPTION "Return all tags on this Configuration MBean "
      ::= { coherenceTierEntry 7  }
   
   
   coherenceTierCoherenceWebFederatedStorageEnabled OBJECT-TYPE
      SYNTAX      OCTET STRING
      MAX-ACCESS  read-only
      STATUS      current
      DESCRIPTION "Specifies whether Federated Cache Storage is enabled for the Coherence Web cluster member  "
      ::= { coherenceTierEntry 8  }
   
   
   customAuthConfigProviderTable OBJECT-TYPE
      SYNTAX      SEQUENCE OF CustomAuthConfigProviderEntry
      MAX-ACCESS  not-accessible
      STATUS      current
      DESCRIPTION " "
      ::= { wls 1810  }
      
   
   customAuthConfigProviderEntry OBJECT-TYPE
      SYNTAX      CustomAuthConfigProviderEntry
      MAX-ACCESS  not-accessible
      STATUS      current
      DESCRIPTION "Generated SNMP Table Entry."
      INDEX { customAuthConfigProviderIndex}
      ::= { customAuthConfigProviderTable 1 }
      
   CustomAuthConfigProviderEntry ::=
      SEQUENCE
      {
         customAuthConfigProviderIndex OCTET STRING,
         customAuthConfigProviderObjectName OCTET STRING,
         customAuthConfigProviderType OCTET STRING,
         customAuthConfigProviderName OCTET STRING,
         customAuthConfigProviderClassName OCTET STRING,
         customAuthConfigProviderTags OCTET STRING
      }
      
   
   customAuthConfigProviderIndex OBJECT-TYPE
      SYNTAX      OCTET STRING
      MAX-ACCESS  not-accessible
      STATUS      current
      DESCRIPTION "Index column"
      ::= { customAuthConfigProviderEntry 1  }
   
   
   customAuthConfigProviderObjectName OBJECT-TYPE
      SYNTAX      OCTET STRING
      MAX-ACCESS  read-only
      STATUS      current
      DESCRIPTION "ObjectName column"
      ::= { customAuthConfigProviderEntry 2  }
   
   
   customAuthConfigProviderType OBJECT-TYPE
      SYNTAX      OCTET STRING
      MAX-ACCESS  read-only
      STATUS      current
      DESCRIPTION "Returns the type of the MBean. "
      ::= { customAuthConfigProviderEntry 3  }
   
   
   customAuthConfigProviderName OBJECT-TYPE
      SYNTAX      OCTET STRING
      MAX-ACCESS  read-only
      STATUS      current
      DESCRIPTION "The user-specified name of this MBean instance.  This name is included as one of the key properties in the MBean's javax.management.ObjectName:  Name=user-specified-name "
      ::= { customAuthConfigProviderEntry 4  }
   
   
   customAuthConfigProviderClassName OBJECT-TYPE
      SYNTAX      OCTET STRING
      MAX-ACCESS  read-only
      STATUS      current
      DESCRIPTION "get the classname for the custom authentication config provider "
      ::= { customAuthConfigProviderEntry 5  }
   
   
   customAuthConfigProviderTags OBJECT-TYPE
      SYNTAX      OCTET STRING
      MAX-ACCESS  read-only
      STATUS      current
      DESCRIPTION "Return all tags on this Configuration MBean "
      ::= { customAuthConfigProviderEntry 6  }
   
   
   dataSourceLogFileTable OBJECT-TYPE
      SYNTAX      SEQUENCE OF DataSourceLogFileEntry
      MAX-ACCESS  not-accessible
      STATUS      current
      DESCRIPTION "Defines the logging configuration for a DataSource. "
      ::= { wls 1815  }
      
   
   dataSourceLogFileEntry OBJECT-TYPE
      SYNTAX      DataSourceLogFileEntry
      MAX-ACCESS  not-accessible
      STATUS      current
      DESCRIPTION "Generated SNMP Table Entry."
      INDEX { dataSourceLogFileIndex}
      ::= { dataSourceLogFileTable 1 }
      
   DataSourceLogFileEntry ::=
      SEQUENCE
      {
         dataSourceLogFileIndex OCTET STRING,
         dataSourceLogFileObjectName OCTET STRING,
         dataSourceLogFileRotateLogOnStartup OCTET STRING,
         dataSourceLogFileFileTimeSpan Integer32,
         dataSourceLogFileLogFileRotationDir OCTET STRING,
         dataSourceLogFileRotationTime OCTET STRING,
         dataSourceLogFileType OCTET STRING,
         dataSourceLogFileNumberOfFilesLimited OCTET STRING,
         dataSourceLogFileBufferSizeKB Integer32,
         dataSourceLogFileFileCount Integer32,
         dataSourceLogFileRotationType OCTET STRING,
         dataSourceLogFileName OCTET STRING,
         dataSourceLogFileFileMinSize Integer32,
         dataSourceLogFileFileName OCTET STRING,
         dataSourceLogFileDateFormatPattern OCTET STRING,
         dataSourceLogFileTags OCTET STRING
      }
      
   
   dataSourceLogFileIndex OBJECT-TYPE
      SYNTAX      OCTET STRING
      MAX-ACCESS  not-accessible
      STATUS      current
      DESCRIPTION "Index column"
      ::= { dataSourceLogFileEntry 1  }
   
   
   dataSourceLogFileObjectName OBJECT-TYPE
      SYNTAX      OCTET STRING
      MAX-ACCESS  read-only
      STATUS      current
      DESCRIPTION "ObjectName column"
      ::= { dataSourceLogFileEntry 2  }
   
   
   dataSourceLogFileRotateLogOnStartup OBJECT-TYPE
      SYNTAX      OCTET STRING
      MAX-ACCESS  read-only
      STATUS      current
      DESCRIPTION "Specifies whether a server rotates its log file during its startup cycle. The default value in production mode is false. "
      ::= { dataSourceLogFileEntry 3  }
   
   
   dataSourceLogFileFileTimeSpan OBJECT-TYPE
      SYNTAX      Integer32
      MAX-ACCESS  read-only
      STATUS      current
      DESCRIPTION "The interval (in hours) at which the server saves old log messages to another file. (Requires that you specify a file rotation type of TIME.) "
      ::= { dataSourceLogFileEntry 4  }
   
   
   dataSourceLogFileLogFileRotationDir OBJECT-TYPE
      SYNTAX      OCTET STRING
      MAX-ACCESS  read-only
      STATUS      current
      DESCRIPTION "The directory where the rotated log files will be stored. By default the rotated files are stored in the same directory where the log file is stored. "
      ::= { dataSourceLogFileEntry 5  }
   
   
   dataSourceLogFileRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  Note that WebLogic Server sets a threshold size limit of 500 MB before it forces a hard rotation to prevent excessive log file growth.  Use the following format: H:mm, where  H is Hour in day (0-23) mm is the minute in hour  "
      ::= { dataSourceLogFileEntry 6  }
   
   
   dataSourceLogFileType OBJECT-TYPE
      SYNTAX      OCTET STRING
      MAX-ACCESS  read-only
      STATUS      current
      DESCRIPTION "Returns the type of the MBean. "
      ::= { dataSourceLogFileEntry 7  }
   
   
   dataSourceLogFileNumberOfFilesLimited OBJECT-TYPE
      SYNTAX      OCTET STRING
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require. "
      ::= { dataSourceLogFileEntry 8  }
   
   
   dataSourceLogFileBufferSizeKB OBJECT-TYPE
      SYNTAX      Integer32
      MAX-ACCESS  read-only
      STATUS      current
      DESCRIPTION "Gets the underlying log buffer size in kilobytes "
      ::= { dataSourceLogFileEntry 9  }
   
   
   dataSourceLogFileFileCount OBJECT-TYPE
      SYNTAX      Integer32
      MAX-ACCESS  read-only
      STATUS      current
      DESCRIPTION "The maximum number of log files that the server creates when it rotates the log. This number does not include the file that the server uses to store current messages. (Requires that you enable Number of Files Limited.) "
      ::= { dataSourceLogFileEntry 10  }
   
   
   dataSourceLogFileRotationType OBJECT-TYPE
      SYNTAX      OCTET STRING
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as SERVER_NAME.lognnnnn.  TIME At each time interval that you specify in TimeSpan, the server renames the file as SERVER_NAME.lognnnnn.   After the server renames a file, subsequent messages accumulate in a new file with the name that you specified as the log file name. "
      ::= { dataSourceLogFileEntry 11  }
   
   
   dataSourceLogFileName OBJECT-TYPE
      SYNTAX      OCTET STRING
      MAX-ACCESS  read-only
      STATUS      current
      DESCRIPTION "The user-specified name of this MBean instance.  This name is included as one of the key properties in the MBean's javax.management.ObjectName:  Name=user-specified-name "
      ::= { dataSourceLogFileEntry 12  }
   
   
   dataSourceLogFileFileMinSize OBJECT-TYPE
      SYNTAX      Integer32
      MAX-ACCESS  read-only
      STATUS      current
      DESCRIPTION "The size (1 - 2097150 kilobytes) that triggers the server to move log messages to a separate file. The default is 500 kilobytes. After the log file reaches the specified minimum size, the next time the server checks the file size, it will rename the current log file as SERVER_NAME.lognnnnn and create a new one to store subsequent messages. (Requires that you specify a file rotation type of Size.) "
      ::= { dataSourceLogFileEntry 13  }
   
   
   dataSourceLogFileFileName OBJECT-TYPE
      SYNTAX      OCTET STRING
      MAX-ACCESS  read-only
      STATUS      current
      DESCRIPTION "The name of the file that stores datasource profile records. Usually it is a computed value based on the name of the parent of this MBean. For example, for a datasource profile log, it is serverName.log.  However, if the name of the parent cannot be obtained, the file name is weblogic.log. If you specify a relative pathname, it is interpreted as relative to the server's root directory.  To include a time and date stamp in the file name when the log file is rotated, add java.text.SimpleDateFormat variables to the file name. Surround each variable with percentage (%) characters.  For example, if the file name is defined to be myjmsserver_%yyyy%_%MM%_%dd%_%hh%_%mm%.log, the log file will be named myserver_yyyy_mm_dd_hh_mm.log.  When the log file is rotated, the rotated file name contains the date stamp. For example, if the log file is rotated on 2 April, 2005 at 10:05 AM, the log file that contains the old messages will be named myserver_2005_04_02_10_05.log.  If you do not include a time and date stamp, the rotated log files are numbered in order of creation. For example, myjmsserver.log00007. "
      ::= { dataSourceLogFileEntry 14  }
   
   
   dataSourceLogFileDateFormatPattern OBJECT-TYPE
      SYNTAX      OCTET STRING
      MAX-ACCESS  read-only
      STATUS      current
      DESCRIPTION "The date format pattern used for rendering dates in the  log. The DateFormatPattern string conforms to the specification of the java.text.SimpleDateFormat class. "
      ::= { dataSourceLogFileEntry 15  }
   
   
   dataSourceLogFileTags OBJECT-TYPE
      SYNTAX      OCTET STRING
      MAX-ACCESS  read-only
      STATUS      current
      DESCRIPTION "Return all tags on this Configuration MBean "
      ::= { dataSourceLogFileEntry 16  }
   
   
   dataSourceTable OBJECT-TYPE
      SYNTAX      SEQUENCE OF DataSourceEntry
      MAX-ACCESS  not-accessible
      STATUS      current
      DESCRIPTION "This bean represents a DataSource within a Weblogic Server instance. "
      ::= { wls 1820  }
      
   
   dataSourceEntry OBJECT-TYPE
      SYNTAX      DataSourceEntry
      MAX-ACCESS  not-accessible
      STATUS      current
      DESCRIPTION "Generated SNMP Table Entry."
      INDEX { dataSourceIndex}
      ::= { dataSourceTable 1 }
      
   DataSourceEntry ::=
      SEQUENCE
      {
         dataSourceIndex      OCTET STRING,
         dataSourceObjectName OCTET STRING,
         dataSourceType       OCTET STRING,
         dataSourceName       OCTET STRING,
         dataSourceRmiJDBCSecurity OCTET STRING,
         dataSourceDeploymentOrder Integer32,
         dataSourceDefaultDatasource OCTET STRING,
         dataSourceTags       OCTET STRING
      }
      
   
   dataSourceIndex OBJECT-TYPE
      SYNTAX      OCTET STRING
      MAX-ACCESS  not-accessible
      STATUS      current
      DESCRIPTION "Index column"
      ::= { dataSourceEntry 1  }
   
   
   dataSourceObjectName OBJECT-TYPE
      SYNTAX      OCTET STRING
      MAX-ACCESS  read-only
      STATUS      current
      DESCRIPTION "ObjectName column"
      ::= { dataSourceEntry 2  }
   
   
   dataSourceType OBJECT-TYPE
      SYNTAX      OCTET STRING
      MAX-ACCESS  read-only
      STATUS      current
      DESCRIPTION "Returns the type of the MBean. "
      ::= { dataSourceEntry 3  }
   
   
   dataSourceName OBJECT-TYPE
      SYNTAX      OCTET STRING
      MAX-ACCESS  read-only
      STATUS      current
      DESCRIPTION "The user-specified name of this MBean instance.  This name is included as one of the key properties in the MBean's javax.management.ObjectName:  Name=user-specified-name "
      ::= { dataSourceEntry 4  }
   
   
   dataSourceRmiJDBCSecurity OBJECT-TYPE
      SYNTAX      OCTET STRING
      MAX-ACCESS  read-only
      STATUS      current
      DESCRIPTION "The security protocol used by an RMI client to access a data source. Values are:  Secure: All incoming JDBC calls require administrator authentication. All other subjects, including anonymous, are rejected. Requires a configured SSL listen port. Compatibility: Use an unsecure channel with the application's subject and no check for inbound administrator authentication when using RMI to access a data source. This setting reflects the legacy implementation behavior for RMI access to a data source and is a potential security vulnerability as it provides a client uncontrolled access to a database. The default value is Compatibility.  "
      ::= { dataSourceEntry 5  }
   
   
   dataSourceDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { dataSourceEntry 6  }
   
   
   dataSourceDefaultDatasource OBJECT-TYPE
      SYNTAX      OCTET STRING
      MAX-ACCESS  read-only
      STATUS      current
      DESCRIPTION "The JNDI name of a system resource data source used to override the default datasource. "
      ::= { dataSourceEntry 7  }
   
   
   dataSourceTags OBJECT-TYPE
      SYNTAX      OCTET STRING
      MAX-ACCESS  read-only
      STATUS      current
      DESCRIPTION "Return all tags on this Configuration MBean "
      ::= { dataSourceEntry 8  }
   
   
   dynamicServersTable OBJECT-TYPE
      SYNTAX      SEQUENCE OF DynamicServersEntry
      MAX-ACCESS  not-accessible
      STATUS      current
      DESCRIPTION "Contains the properties used to control how dynamic servers are created. These properties allow you to control if listens ports are calculated, how servers are assigned to machines, and the number of dynamic servers to create. "
      ::= { wls 1825  }
      
   
   dynamicServersEntry OBJECT-TYPE
      SYNTAX      DynamicServersEntry
      MAX-ACCESS  not-accessible
      STATUS      current
      DESCRIPTION "Generated SNMP Table Entry."
      INDEX { dynamicServersIndex}
      ::= { dynamicServersTable 1 }
      
   DynamicServersEntry ::=
      SEQUENCE
      {
         dynamicServersIndex  OCTET STRING,
         dynamicServersObjectName OCTET STRING,
         dynamicServersType   OCTET STRING,
         dynamicServersCalculatedListenPorts OCTET STRING,
         dynamicServersCalculatedMachineNames OCTET STRING,
         dynamicServersMachineNameMatchExpression OCTET STRING,
         dynamicServersName   OCTET STRING,
         dynamicServersServerNamePrefix OCTET STRING,
         dynamicServersMaximumDynamicServerCount Integer32,
         dynamicServersMaxDynamicClusterSize INTEGER,
         dynamicServersIgnoreSessionsDuringShutdown OCTET STRING,
         dynamicServersMachineMatchType OCTET STRING,
         dynamicServersDynamicClusterShutdownTimeoutSeconds INTEGER,
         dynamicServersTags   OCTET STRING,
         dynamicServersMinDynamicClusterSize INTEGER,
         dynamicServersDynamicClusterSize INTEGER,
         dynamicServersDynamicClusterCooloffPeriodSeconds INTEGER,
         dynamicServersWaitForAllSessionsDuringShutdown OCTET STRING,
         dynamicServersMachineMatchExpression OCTET STRING,
         dynamicServersDynamicServerNames OCTET STRING
      }
      
   
   dynamicServersIndex OBJECT-TYPE
      SYNTAX      OCTET STRING
      MAX-ACCESS  not-accessible
      STATUS      current
      DESCRIPTION "Index column"
      ::= { dynamicServersEntry 1  }
   
   
   dynamicServersObjectName OBJECT-TYPE
      SYNTAX      OCTET STRING
      MAX-ACCESS  read-only
      STATUS      current
      DESCRIPTION "ObjectName column"
      ::= { dynamicServersEntry 2  }
   
   
   dynamicServersType OBJECT-TYPE
      SYNTAX      OCTET STRING
      MAX-ACCESS  read-only
      STATUS      current
      DESCRIPTION "Returns the type of the MBean. "
      ::= { dynamicServersEntry 3  }
   
   
   dynamicServersCalculatedListenPorts OBJECT-TYPE
      SYNTAX      OCTET STRING
      MAX-ACCESS  read-only
      STATUS      current
      DESCRIPTION "Specifies whether listen ports are calculated. "
      ::= { dynamicServersEntry 4  }
   
   
   dynamicServersCalculatedMachineNames OBJECT-TYPE
      SYNTAX      OCTET STRING
      MAX-ACCESS  read-only
      STATUS      current
      DESCRIPTION "The CalculatedMachineNames attribute controls how server instances in a dynamic cluster are assigned to a machine. If the attribute is not set, then the dynamic servers will not be assigned to a machine. If the attribute is set, then the MachineNameMatchExpression attribute is used to select the set of machines to use for the dynamic servers. "
      ::= { dynamicServersEntry 5  }
   
   
   dynamicServersMachineNameMatchExpression OBJECT-TYPE
      SYNTAX      OCTET STRING
      MAX-ACCESS  read-only
      STATUS      current
      DESCRIPTION "The expression is used when determining machines to use for server assignments. If null, then all machines in the domain are used. If a expression is provided, then only the machines in the domain that match the expression will be used when assigning machine names to dynamic servers.  The expression is a comma separated set of values that specify the machines to match. Each value will either match a machine name exactly or if specified with a trailing '*' suffix, the value will match multiple machine names. "
      ::= { dynamicServersEntry 6  }
   
   
   dynamicServersName OBJECT-TYPE
      SYNTAX      OCTET STRING
      MAX-ACCESS  read-only
      STATUS      current
      DESCRIPTION "The user-specified name of this MBean instance.  This name is included as one of the key properties in the MBean's javax.management.ObjectName:  Name=user-specified-name "
      ::= { dynamicServersEntry 7  }
   
   
   dynamicServersServerNamePrefix OBJECT-TYPE
      SYNTAX      OCTET STRING
      MAX-ACCESS  read-only
      STATUS      current
      DESCRIPTION "The server name prefix is used to specify the naming convention when creating server names. When the server name prefix is defined, server names are calculated with the specified prefix followed by the index starting with 1. "
      ::= { dynamicServersEntry 8  }
   
   
   dynamicServersMaximumDynamicServerCount OBJECT-TYPE
      SYNTAX      Integer32
      MAX-ACCESS  read-only
      STATUS      current
      DESCRIPTION "The maximum number of server instances allowed to be created. This value should be set to the number of servers expected to be in the cluster. The specified number of servers are dynamically added to the configuration at runtime and associated ServerLifeCycleRuntimeMBeans are created. "
      ::= { dynamicServersEntry 9  }
   
   
   dynamicServersMaxDynamicClusterSize OBJECT-TYPE
      SYNTAX      INTEGER
      MAX-ACCESS  read-only
      STATUS      current
      DESCRIPTION "Get the upper bound on the DynamicClusterSize that the Elasticity Framework is allowed to assign to DynamicClusterSize. "
      ::= { dynamicServersEntry 10  }
   
   
   dynamicServersIgnoreSessionsDuringShutdown OBJECT-TYPE
      SYNTAX      OCTET STRING
      MAX-ACCESS  read-only
      STATUS      current
      DESCRIPTION "Indicates if the Elasticity Framework should ignore inflight HTTP sessions while shutting down servers. "
      ::= { dynamicServersEntry 11  }
   
   
   dynamicServersMachineMatchType OBJECT-TYPE
      SYNTAX      OCTET STRING
      MAX-ACCESS  read-only
      STATUS      current
      DESCRIPTION "Get the machine tag expression to use when selecting machine names.  If the MachineMatchType is 'name', each value will either match a machine name exactly or, if specified with a trailing '*' suffix, will match multiple machine names. If the MachineMatchType is 'tag', the values will match all of the machines that have all of the tag values. "
      ::= { dynamicServersEntry 12  }
   
   
   dynamicServersDynamicClusterShutdownTimeoutSeconds OBJECT-TYPE
      SYNTAX      INTEGER
      MAX-ACCESS  read-only
      STATUS      current
      DESCRIPTION "Get the timeout period (in seconds) used by the Elasticity Framework while gracefully shutting down a server. If the server does not shut down before the specified timeout period, the server will be forcibly shut down. With a negative time value, no timeout will be applied. "
      ::= { dynamicServersEntry 13  }
   
   
   dynamicServersTags OBJECT-TYPE
      SYNTAX      OCTET STRING
      MAX-ACCESS  read-only
      STATUS      current
      DESCRIPTION "Return all tags on this Configuration MBean "
      ::= { dynamicServersEntry 14  }
   
   
   dynamicServersMinDynamicClusterSize OBJECT-TYPE
      SYNTAX      INTEGER
      MAX-ACCESS  read-only
      STATUS      current
      DESCRIPTION "Get the minimum number of running server instances that the Elasticity Framework will attempt to keep in the dynamic cluster. "
      ::= { dynamicServersEntry 15  }
   
   
   dynamicServersDynamicClusterSize OBJECT-TYPE
      SYNTAX      INTEGER
      MAX-ACCESS  read-only
      STATUS      current
      DESCRIPTION "Get the current size of the dynamic cluster (the number of dynamic server instances allowed to be created). The specified number of server instances are dynamically added to the configuration at runtime and associated ServerLifeCycleRuntimeMBeans are created. "
      ::= { dynamicServersEntry 16  }
   
   
   dynamicServersDynamicClusterCooloffPeriodSeconds OBJECT-TYPE
      SYNTAX      INTEGER
      MAX-ACCESS  read-only
      STATUS      current
      DESCRIPTION "Get the cool-off period (in seconds) used by the Elasticity Framework while performing scale up or scale down operations. If a scale up or scale down operation was performed, subsequent requests for scale up or down operations will be ignored by the Elasticity Framework during this period. "
      ::= { dynamicServersEntry 17  }
   
   
   dynamicServersWaitForAllSessionsDuringShutdown OBJECT-TYPE
      SYNTAX      OCTET STRING
      MAX-ACCESS  read-only
      STATUS      current
      DESCRIPTION "Indicates if the Elasticity Framework should wait for all (persisted and non-persisted) HTTP sessions during inflight work handling while shutting down servers. "
      ::= { dynamicServersEntry 18  }
   
   
   dynamicServersMachineMatchExpression OBJECT-TYPE
      SYNTAX      OCTET STRING
      MAX-ACCESS  read-only
      STATUS      current
      DESCRIPTION "Get the machine tag expression to use when selecting machine names.  If the MachineMatchType is 'name', each value will either match a machine name exactly or, if specified with a trailing '*' suffix, will match multiple machine names. If the MachineMatchType is 'tag', the values will match all of the machines that have all of the tag values. "
      ::= { dynamicServersEntry 19  }
   
   
   dynamicServersDynamicServerNames OBJECT-TYPE
      SYNTAX      OCTET STRING
      MAX-ACCESS  read-only
      STATUS      current
      DESCRIPTION "Return an array of all the dynamic server names "
      ::= { dynamicServersEntry 20  }
   
   
   jASPICTable OBJECT-TYPE
      SYNTAX      SEQUENCE OF JASPICEntry
      MAX-ACCESS  not-accessible
      STATUS      current
      DESCRIPTION "Provides configuration for JASPIC (JSR-196) Auth Config Providers on the domain. "
      ::= { wls 1830  }
      
   
   jASPICEntry OBJECT-TYPE
      SYNTAX      JASPICEntry
      MAX-ACCESS  not-accessible
      STATUS      current
      DESCRIPTION "Generated SNMP Table Entry."
      INDEX { jASPICIndex}
      ::= { jASPICTable 1 }
      
   JASPICEntry ::=
      SEQUENCE
      {
         jASPICIndex          OCTET STRING,
         jASPICObjectName     OCTET STRING,
         jASPICEnabled        OCTET STRING,
         jASPICType           OCTET STRING,
         jASPICName           OCTET STRING,
         jASPICTags           OCTET STRING
      }
      
   
   jASPICIndex OBJECT-TYPE
      SYNTAX      OCTET STRING
      MAX-ACCESS  not-accessible
      STATUS      current
      DESCRIPTION "Index column"
      ::= { jASPICEntry 1  }
   
   
   jASPICObjectName OBJECT-TYPE
      SYNTAX      OCTET STRING
      MAX-ACCESS  read-only
      STATUS      current
      DESCRIPTION "ObjectName column"
      ::= { jASPICEntry 2  }
   
   
   jASPICEnabled OBJECT-TYPE
      SYNTAX      OCTET STRING
      MAX-ACCESS  read-only
      STATUS      current
      DESCRIPTION "Returns true if JASPIC is enabled, false otherwise. "
      ::= { jASPICEntry 3  }
   
   
   jASPICType OBJECT-TYPE
      SYNTAX      OCTET STRING
      MAX-ACCESS  read-only
      STATUS      current
      DESCRIPTION "Returns the type of the MBean. "
      ::= { jASPICEntry 4  }
   
   
   jASPICName OBJECT-TYPE
      SYNTAX      OCTET STRING
      MAX-ACCESS  read-only
      STATUS      current
      DESCRIPTION "The user-specified name of this MBean instance.  This name is included as one of the key properties in the MBean's javax.management.ObjectName:  Name=user-specified-name "
      ::= { jASPICEntry 5  }
   
   
   jASPICTags OBJECT-TYPE
      SYNTAX      OCTET STRING
      MAX-ACCESS  read-only
      STATUS      current
      DESCRIPTION "Return all tags on this Configuration MBean "
      ::= { jASPICEntry 6  }
   
   
   jtaClusterTable OBJECT-TYPE
      SYNTAX      SEQUENCE OF JtaClusterEntry
      MAX-ACCESS  not-accessible
      STATUS      current
      DESCRIPTION "This interface provides access to the JTA configuration attributes.  The methods defined herein are applicable for JTA configuration at the clluster level. "
      ::= { wls 1835  }
      
   
   jtaClusterEntry OBJECT-TYPE
      SYNTAX      JtaClusterEntry
      MAX-ACCESS  not-accessible
      STATUS      current
      DESCRIPTION "Generated SNMP Table Entry."
      INDEX { jtaClusterIndex}
      ::= { jtaClusterTable 1 }
      
   JtaClusterEntry ::=
      SEQUENCE
      {
         jtaClusterIndex      OCTET STRING,
         jtaClusterObjectName OCTET STRING,
         jtaClusterTightlyCoupledTransactionsEnabled OCTET STRING,
         jtaClusterBeforeCompletionIterationLimit Integer32,
         jtaClusterMigrationCheckpointIntervalSeconds Integer32,
         jtaClusterType       OCTET STRING,
         jtaClusterUnregisterResourceGracePeriod Integer32,
         jtaClusterMaxUniqueNameStatistics Integer32,
         jtaClusterParallelXAEnabled OCTET STRING,
         jtaClusterForgetHeuristics OCTET STRING,
         jtaClusterSecurityInteropMode OCTET STRING,
         jtaClusterWSATIssuedTokenEnabled OCTET STRING,
         jtaClusterAbandonTimeoutSeconds Integer32,
         jtaClusterSerializeEnlistmentsGCIntervalMillis Counter64,
         jtaClusterMaxResourceRequestsOnServer Integer32,
         jtaClusterMaxTransactionsHealthIntervalMillis Counter64,
         jtaClusterParallelXADispatchPolicy OCTET STRING,
         jtaClusterMaxXACallMillis Counter64,
         jtaClusterCheckpointIntervalSeconds Integer32,
         jtaClusterTimeoutSeconds Integer32,
         jtaClusterName       OCTET STRING,
         jtaClusterMaxTransactions Integer32,
         jtaClusterClusterwideRecoveryEnabled OCTET STRING,
         jtaClusterCompletionTimeoutSeconds Integer32,
         jtaClusterMaxResourceUnavailableMillis Counter64,
         jtaClusterPurgeResourceFromCheckpointIntervalSeconds Integer32,
         jtaClusterWSATTransportSecurityMode OCTET STRING,
         jtaClusterTwoPhaseEnabled OCTET STRING,
         jtaClusterRecoveryThresholdMillis Counter64,
         jtaClusterDeterminers OCTET STRING,
         jtaClusterTLOGWriteWhenDeterminerExistsEnabled OCTET STRING,
         jtaClusterMaxRetrySecondsBeforeDeterminerFail INTEGER,
         jtaClusterShutdownGracePeriod INTEGER,
         jtaClusterRecoverySiteName OCTET STRING,
         jtaClusterTags       OCTET STRING,
         jtaClusterCrossDomainRecoveryRetryInterval INTEGER,
         jtaClusterCrossSiteRecoveryRetryInterval INTEGER,
         jtaClusterCrossSiteRecoveryLeaseUpdate INTEGER,
         jtaClusterCrossSiteRecoveryLeaseExpiration INTEGER,
         jtaClusterUsePublicAddressesForRemoteDomains OCTET STRING,
         jtaClusterUseNonSecureAddressesForDomains OCTET STRING
      }
      
   
   jtaClusterIndex OBJECT-TYPE
      SYNTAX      OCTET STRING
      MAX-ACCESS  not-accessible
      STATUS      current
      DESCRIPTION "Index column"
      ::= { jtaClusterEntry 1  }
   
   
   jtaClusterObjectName OBJECT-TYPE
      SYNTAX      OCTET STRING
      MAX-ACCESS  read-only
      STATUS      current
      DESCRIPTION "ObjectName column"
      ::= { jtaClusterEntry 2  }
   
   
   jtaClusterTightlyCoupledTransactionsEnabled OBJECT-TYPE
      SYNTAX      OCTET STRING
      MAX-ACCESS  read-only
      STATUS      current
      DESCRIPTION "Indicates tight coupling of transaction branches that span different transaction manager systems.   When enabled, WebLogic uses the transaction identifier of a transaction imported by the InterposedTransactionManager for XA calls rather than an internally mapped Xid. This applies to inter-domain WebLogic transactions and transactions imported from Tuxedo. This allows for tight coupling of transaction branches for transactions that span across different transaction manager systems.  If a transaction between WebLogic and Tuxedo resources uses a GridLink Data Source with GridLink Affinity enabled, the XA Affinity context is automatically used for the transaction. "
      ::= { jtaClusterEntry 3  }
   
   
   jtaClusterBeforeCompletionIterationLimit OBJECT-TYPE
      SYNTAX      Integer32
      MAX-ACCESS  read-only
      STATUS      current
      DESCRIPTION "The maximum number of cycles that the transaction manager performs the beforeCompletion synchronization callback for this cluster.  Nothing prevents a Synchronization object from registering another during beforeCompletion, even those whose beforeCompletions have already been called. For example, an EJB can call another in its ejbStore() method. To accommodate this, the transaction manager calls all Synchronization objects, then repeats the cycle if new ones have been registered. This count sets a limit to the number of cycles that synchronization occurs. "
      ::= { jtaClusterEntry 4  }
   
   
   jtaClusterMigrationCheckpointIntervalSeconds OBJECT-TYPE
      SYNTAX      Integer32
      MAX-ACCESS  read-only
      STATUS      current
      DESCRIPTION "The time interval, in seconds,  that the checkpoint is done for the migrated transaction logs (TLOGs). "
      ::= { jtaClusterEntry 5  }
   
   
   jtaClusterType OBJECT-TYPE
      SYNTAX      OCTET STRING
      MAX-ACCESS  read-only
      STATUS      current
      DESCRIPTION "Returns the type of the MBean. "
      ::= { jtaClusterEntry 6  }
   
   
   jtaClusterUnregisterResourceGracePeriod OBJECT-TYPE
      SYNTAX      Integer32
      MAX-ACCESS  read-only
      STATUS      current
      DESCRIPTION "The amount of time, in seconds, a  transaction manager waits for transactions involving the resource to complete before unregistering a resource. This grace period helps minimize the risk of abandoned transactions because of an unregistered resource, such as a JDBC data source module packaged with an application.  During the specified grace period, the unregisterResource call blocks until the call returns and no new transactions are started for the associated resource. If the number of outstanding transactions for the resource goes to 0, the unregisterResource call returns immediately.  At the end of the grace period, if outstanding transactions are associated with the resource, the unregisterResource call returns and a log message is written to the server on which the resource was previously registered.  "
      ::= { jtaClusterEntry 7  }
   
   
   jtaClusterMaxUniqueNameStatistics OBJECT-TYPE
      SYNTAX      Integer32
      MAX-ACCESS  read-only
      STATUS      current
      DESCRIPTION "The maximum number of unique transaction names for which statistics are maintained.  The first 1001 unique transaction names are maintained as their own transaction name and stored in each statistic. After the 1001st transaction name is reached, the transaction name is stored as weblogic.transaction.statistics.namedOverflow, and the transaction statistic is also merged and maintained in weblogic.transaction.statistics.namedOverflow.  A transaction name typically represents a category of business transactions, such as 'funds-transfer.' "
      ::= { jtaClusterEntry 8  }
   
   
   jtaClusterParallelXAEnabled OBJECT-TYPE
      SYNTAX      OCTET STRING
      MAX-ACCESS  read-only
      STATUS      current
      DESCRIPTION "Indicates that XA calls are executed in parallel if there are available threads. "
      ::= { jtaClusterEntry 9  }
   
   
   jtaClusterForgetHeuristics OBJECT-TYPE
      SYNTAX      OCTET STRING
      MAX-ACCESS  read-only
      STATUS      current
      DESCRIPTION "Specifies whether the transaction manager automatically performs an XA Resource forget operation for heuristic transaction completions.  When enabled, the transaction manager automatically performs an XA Resource forget() operation for all resources as soon as the transaction learns of a heuristic outcome. Disable this feature only if you know what to do with the resource when it reports a heuristic decision. "
      ::= { jtaClusterEntry 10  }
   
   
   jtaClusterSecurityInteropMode OBJECT-TYPE
      SYNTAX      OCTET STRING
      MAX-ACCESS  read-only
      STATUS      current
      DESCRIPTION "Specifies the security mode of the communication channel used for XA calls between servers that participate in a global transaction. All server instances in a domain must have the same security mode setting.  Security Interoperability Mode options:  default  The transaction coordinator makes calls using the kernel identity over an admin channel if it is enabled, and anonymous otherwise. Man-in-the-middle attacks are possible if the admin channel is not enabled.  performance  The transaction coordinator makes calls using anonymous at all times. This implies a security risk since a malicious third party could then try to affect the outcome of transactions using a man-in-the-middle attack.  compatibility  The transaction coordinator makes calls as the kernel identity over an insecure channel. This is a high security risk because a successful man-in-the-middle attack would allow the attacker to gain administrative control over both domains. This setting should only be used when strong network security is in place.   "
      ::= { jtaClusterEntry 11  }
   
   
   jtaClusterWSATIssuedTokenEnabled OBJECT-TYPE
      SYNTAX      OCTET STRING
      MAX-ACCESS  read-only
      STATUS      current
      DESCRIPTION "Specifies whether to use issuedtoken to enable authentication between the WS-AT coordinator and participant. "
      ::= { jtaClusterEntry 12  }
   
   
   jtaClusterAbandonTimeoutSeconds OBJECT-TYPE
      SYNTAX      Integer32
      MAX-ACCESS  read-only
      STATUS      current
      DESCRIPTION "Specifies the maximum amount of time, in seconds, a transaction manager persists in attempting to complete the second phase of a two-phase commit transaction.   During the second phase of a two-phase commit transaction, the transaction manager continues to try to complete the transaction until all resource managers indicate that the transaction is completed. After the abandon transaction timer expires, no further attempt is made to resolve the transaction. If the transaction is in a prepared state before being abandoned, the transaction manager rolls back the transaction to release any locks held on behalf of the abandoned transaction. "
      ::= { jtaClusterEntry 13  }
   
   
   jtaClusterSerializeEnlistmentsGCIntervalMillis OBJECT-TYPE
      SYNTAX      Counter64
      MAX-ACCESS  read-only
      STATUS      current
      DESCRIPTION "The time interval, in milliseconds, at which internal objects used to serialize resource enlistment are cleaned up. "
      ::= { jtaClusterEntry 14  }
   
   
   jtaClusterMaxResourceRequestsOnServer OBJECT-TYPE
      SYNTAX      Integer32
      MAX-ACCESS  read-only
      STATUS      current
      DESCRIPTION "Maximum number of concurrent requests to resources allowed for each server. "
      ::= { jtaClusterEntry 15  }
   
   
   jtaClusterMaxTransactionsHealthIntervalMillis OBJECT-TYPE
      SYNTAX      Counter64
      MAX-ACCESS  read-only
      STATUS      current
      DESCRIPTION "The interval for which the transaction map must be full for the JTA subsystem to declare its health as CRITICAL. "
      ::= { jtaClusterEntry 16  }
   
   
   jtaClusterParallelXADispatchPolicy OBJECT-TYPE
      SYNTAX      OCTET STRING
      MAX-ACCESS  read-only
      STATUS      current
      DESCRIPTION "The dispatch policy to use when performing XA operations in parallel.  "
      ::= { jtaClusterEntry 17  }
   
   
   jtaClusterMaxXACallMillis OBJECT-TYPE
      SYNTAX      Counter64
      MAX-ACCESS  read-only
      STATUS      current
      DESCRIPTION "Maximum allowed time duration, in milliseconds,  for XA calls to resources. If a particular XA call to a resource exceeds the limit, the resource is declared unavailable. "
      ::= { jtaClusterEntry 18  }
   
   
   jtaClusterCheckpointIntervalSeconds OBJECT-TYPE
      SYNTAX      Integer32
      MAX-ACCESS  read-only
      STATUS      current
      DESCRIPTION "The interval at which the transaction manager creates a new transaction log file and checks all old transaction log files to see if they are ready to be deleted. "
      ::= { jtaClusterEntry 19  }
   
   
   jtaClusterTimeoutSeconds OBJECT-TYPE
      SYNTAX      Integer32
      MAX-ACCESS  read-only
      STATUS      current
      DESCRIPTION "Specifies the maximum amount of time, in seconds, an active transaction is allowed to be in the first phase of a two-phase commit transaction. If the specified amount of time expires, the transaction is automatically rolled back. "
      ::= { jtaClusterEntry 20  }
   
   
   jtaClusterName OBJECT-TYPE
      SYNTAX      OCTET STRING
      MAX-ACCESS  read-only
      STATUS      current
      DESCRIPTION "The user-specified name of this MBean instance.  This name is included as one of the key properties in the MBean's javax.management.ObjectName:  Name=user-specified-name "
      ::= { jtaClusterEntry 21  }
   
   
   jtaClusterMaxTransactions OBJECT-TYPE
      SYNTAX      Integer32
      MAX-ACCESS  read-only
      STATUS      current
      DESCRIPTION "The maximum number of simultaneous in-progress transactions allowed on a server in this cluster. "
      ::= { jtaClusterEntry 22  }
   
   
   jtaClusterClusterwideRecoveryEnabled OBJECT-TYPE
      SYNTAX      OCTET STRING
      MAX-ACCESS  read-only
      STATUS      current
      DESCRIPTION "Indicates that cluster-wide recovery is used for distributed transactions.  When enabled, recovery operations for a distributed transaction are applied to all the servers of the cluster hosting a InterposedTransactionManager rather than just the server hosting the InterposedTransactionManager. "
      ::= { jtaClusterEntry 23  }
   
   
   jtaClusterCompletionTimeoutSeconds OBJECT-TYPE
      SYNTAX      Integer32
      MAX-ACCESS  read-only
      STATUS      current
      DESCRIPTION "Specifies the maximum amount of time, in seconds, a transaction manager waits for all resource managers to respond and indicate if the transaction can be committed or rolled back.   The default value is 0, which sets the value to approximately twice the default transaction-timeout value with a maximum value of 120 seconds. This value provides backward compatibility for prior releases without this setting. If the specified value is -1, the maximum value supported by this attribute is used.  If the specified value exceeds the value set for abandon-timeout-seconds, the value of abandon-timeout-seconds is used.   "
      ::= { jtaClusterEntry 24  }
   
   
   jtaClusterMaxResourceUnavailableMillis OBJECT-TYPE
      SYNTAX      Counter64
      MAX-ACCESS  read-only
      STATUS      current
      DESCRIPTION "Maximum duration time, in milliseconds, that a resource is declared dead. After the duration, the resource is declared available again, even if the resource provider does not explicitly re-register the resource. "
      ::= { jtaClusterEntry 25  }
   
   
   jtaClusterPurgeResourceFromCheckpointIntervalSeconds OBJECT-TYPE
      SYNTAX      Integer32
      MAX-ACCESS  read-only
      STATUS      current
      DESCRIPTION "The interval that a particular resource must be accessed within for it to be included in the checkpoint record. "
      ::= { jtaClusterEntry 26  }
   
   
   jtaClusterWSATTransportSecurityMode OBJECT-TYPE
      SYNTAX      OCTET STRING
      MAX-ACCESS  read-only
      STATUS      current
      DESCRIPTION " Specifies transport security mode required by WebService Transaction endpoints. Transport Security options:  SSLNotRequired All WebService Transaction protocol messages are exchanged over the HTTP channel.  SSLRequired All WebService Transaction protocol messages are and can only be exchanged over the HTTPS.  ClientCertRequired All WebService Transaction protocol messages are and can only be exchanged over the HTTPS, and WLS enforces the presence of client certificate   "
      ::= { jtaClusterEntry 27  }
   
   
   jtaClusterTwoPhaseEnabled OBJECT-TYPE
      SYNTAX      OCTET STRING
      MAX-ACCESS  read-only
      STATUS      current
      DESCRIPTION "Indicates that the two-phase commit protocol is used to coordinate transactions across two or more resource managers.  If not selected:   Two-phase commit is disabled and any attempt to use two-phase commit results in a RollbackException being thrown.  All transaction logging is disabled, including checkpoint records.  "
      ::= { jtaClusterEntry 28  }
   
   
   jtaClusterRecoveryThresholdMillis OBJECT-TYPE
      SYNTAX      Counter64
      MAX-ACCESS  read-only
      STATUS      current
      DESCRIPTION "The interval that recovery is attempted until the resource becomes available. "
      ::= { jtaClusterEntry 29  }
   
   
   jtaClusterDeterminers OBJECT-TYPE
      SYNTAX      OCTET STRING
      MAX-ACCESS  read-only
      STATUS      current
      DESCRIPTION "Specifies a list of one or more transaction resources (determiners) separated by line breaks. A determiner's in-doubt transaction records are used during transaction recovery when a TLog is not present. "
      ::= { jtaClusterEntry 30  }
   
   
   jtaClusterTLOGWriteWhenDeterminerExistsEnabled OBJECT-TYPE
      SYNTAX      OCTET STRING
      MAX-ACCESS  read-only
      STATUS      current
      DESCRIPTION "Indicates two-phase transaction recovery logs are written even if one or more determiners are configured. "
      ::= { jtaClusterEntry 31  }
   
   
   jtaClusterMaxRetrySecondsBeforeDeterminerFail OBJECT-TYPE
      SYNTAX      INTEGER
      MAX-ACCESS  read-only
      STATUS      current
      DESCRIPTION "The maximum amount of time, in seconds, WebLogic Server waits for the determiner to recover from a failure. If the determiner does not recover after this period, WebLogic Server sets the TLog health state to HEALTH_FAILED. "
      ::= { jtaClusterEntry 32  }
   
   
   jtaClusterShutdownGracePeriod OBJECT-TYPE
      SYNTAX      INTEGER
      MAX-ACCESS  read-only
      STATUS      current
      DESCRIPTION "Indicates how long the server should wait for active transactions to complete before allowing shutdown. "
      ::= { jtaClusterEntry 33  }
   
   
   jtaClusterRecoverySiteName OBJECT-TYPE
      SYNTAX      OCTET STRING
      MAX-ACCESS  read-only
      STATUS      current
      DESCRIPTION "The name of the site whose transactions this site/domain will recover in the event that intra-cluster transaction service migration is not successful or efficient. "
      ::= { jtaClusterEntry 34  }
   
   
   jtaClusterTags OBJECT-TYPE
      SYNTAX      OCTET STRING
      MAX-ACCESS  read-only
      STATUS      current
      DESCRIPTION "Return all tags on this Configuration MBean "
      ::= { jtaClusterEntry 35  }
   
   
   jtaClusterCrossDomainRecoveryRetryInterval OBJECT-TYPE
      SYNTAX      INTEGER
      MAX-ACCESS  read-only
      STATUS      current
      DESCRIPTION "The interval at which a store lock for a given server in a recovery domain will be checked for takeover eligibility. "
      ::= { jtaClusterEntry 36  }
   
   
   jtaClusterCrossSiteRecoveryRetryInterval OBJECT-TYPE
      SYNTAX      INTEGER
      MAX-ACCESS  read-only
      STATUS      current
      DESCRIPTION "The interval at which a lease for a given server in a recovery domain will be checked for takeover eligibility. "
      ::= { jtaClusterEntry 37  }
   
   
   jtaClusterCrossSiteRecoveryLeaseUpdate OBJECT-TYPE
      SYNTAX      INTEGER
      MAX-ACCESS  read-only
      STATUS      current
      DESCRIPTION "The time in seconds in which to update at lease timestamp. "
      ::= { jtaClusterEntry 38  }
   
   
   jtaClusterCrossSiteRecoveryLeaseExpiration OBJECT-TYPE
      SYNTAX      INTEGER
      MAX-ACCESS  read-only
      STATUS      current
      DESCRIPTION "The time after which a lease expires making it eligible for recovery by another site. "
      ::= { jtaClusterEntry 39  }
   
   
   jtaClusterUsePublicAddressesForRemoteDomains OBJECT-TYPE
      SYNTAX      OCTET STRING
      MAX-ACCESS  read-only
      STATUS      current
      DESCRIPTION "Returns the remote domains for which public addresses should be used if the servers in the domains are configured to use network channels for internal JTA communication. "
      ::= { jtaClusterEntry 40  }
   
   
   jtaClusterUseNonSecureAddressesForDomains OBJECT-TYPE
      SYNTAX      OCTET STRING
      MAX-ACCESS  read-only
      STATUS      current
      DESCRIPTION "Returns the domains for which non-secure protocols should be used for internal JTA communication if the servers in the domains are configured to use network channels. "
      ::= { jtaClusterEntry 41  }
   
   
   osgiFrameworkTable OBJECT-TYPE
      SYNTAX      SEQUENCE OF OsgiFrameworkEntry
      MAX-ACCESS  not-accessible
      STATUS      current
      DESCRIPTION "An MBean representing an OSGi framework. "
      ::= { wls 1840  }
      
   
   osgiFrameworkEntry OBJECT-TYPE
      SYNTAX      OsgiFrameworkEntry
      MAX-ACCESS  not-accessible
      STATUS      current
      DESCRIPTION "Generated SNMP Table Entry."
      INDEX { osgiFrameworkIndex}
      ::= { osgiFrameworkTable 1 }
      
   OsgiFrameworkEntry ::=
      SEQUENCE
      {
         osgiFrameworkIndex   OCTET STRING,
         osgiFrameworkObjectName OCTET STRING,
         osgiFrameworkType    OCTET STRING,
         osgiFrameworkRegisterGlobalDataSources OCTET STRING,
         osgiFrameworkOsgiImplementationLocation OCTET STRING,
         osgiFrameworkName    OCTET STRING,
         osgiFrameworkRegisterGlobalWorkManagers OCTET STRING,
         osgiFrameworkDeployInstallationBundles OCTET STRING,
         osgiFrameworkOrgOsgiFrameworkSystemPackagesExtra OCTET STRING,
         osgiFrameworkFactoryImplementationClass OCTET STRING,
         osgiFrameworkOrgOsgiFrameworkBootdelegation OCTET STRING,
         osgiFrameworkDeploymentOrder Integer32,
         osgiFrameworkTags    OCTET STRING
      }
      
   
   osgiFrameworkIndex OBJECT-TYPE
      SYNTAX      OCTET STRING
      MAX-ACCESS  not-accessible
      STATUS      current
      DESCRIPTION "Index column"
      ::= { osgiFrameworkEntry 1  }
   
   
   osgiFrameworkObjectName OBJECT-TYPE
      SYNTAX      OCTET STRING
      MAX-ACCESS  read-only
      STATUS      current
      DESCRIPTION "ObjectName column"
      ::= { osgiFrameworkEntry 2  }
   
   
   osgiFrameworkType OBJECT-TYPE
      SYNTAX      OCTET STRING
      MAX-ACCESS  read-only
      STATUS      current
      DESCRIPTION "Returns the type of the MBean. "
      ::= { osgiFrameworkEntry 3  }
   
   
   osgiFrameworkRegisterGlobalDataSources OBJECT-TYPE
      SYNTAX      OCTET STRING
      MAX-ACCESS  read-only
      STATUS      current
      DESCRIPTION "Returns true if global data sources should be added to the OSGi service registry. "
      ::= { osgiFrameworkEntry 4  }
   
   
   osgiFrameworkOsgiImplementationLocation OBJECT-TYPE
      SYNTAX      OCTET STRING
      MAX-ACCESS  read-only
      STATUS      current
      DESCRIPTION "The location of the OSGi implementation JAR file which contains the org.osgi.framework.launch.FrameworkFactory implementation.  If this field is not set then an appropriate default implementation that is shipped with the product will be used.  If this field is relative it must be relative to the start directory of the server and the file must exist everywhere this framework is deployed.  If this field is not relative then the given filename must exist at the same location everywhere this framework is deployed. "
      ::= { osgiFrameworkEntry 5  }
   
   
   osgiFrameworkName OBJECT-TYPE
      SYNTAX      OCTET STRING
      MAX-ACCESS  read-only
      STATUS      current
      DESCRIPTION "The user-specified name of this MBean instance.  This name is included as one of the key properties in the MBean's javax.management.ObjectName:  Name=user-specified-name "
      ::= { osgiFrameworkEntry 6  }
   
   
   osgiFrameworkRegisterGlobalWorkManagers OBJECT-TYPE
      SYNTAX      OCTET STRING
      MAX-ACCESS  read-only
      STATUS      current
      DESCRIPTION "Returns true if global work managers should be added to the OSGi service registry. "
      ::= { osgiFrameworkEntry 7  }
   
   
   osgiFrameworkDeployInstallationBundles OBJECT-TYPE
      SYNTAX      OCTET STRING
      MAX-ACCESS  read-only
      STATUS      current
      DESCRIPTION "Determines if some WebLogic helper bundles will be installed into the framework  If this is set to 'populate' then the bundles found in the WebLogic installation directory under wlserver/server/osgi-lib will be installed into this OSGi framework.  Futhermore a few extra packages will be added to the bootdelegation classpath parameters in order to enable the bundles in the osgi-lib directory if they are not already there.  If this is set to 'ignore' then the bundles found in the WebLogic installation directory will not be installed into the framework. "
      ::= { osgiFrameworkEntry 8  }
   
   
   osgiFrameworkOrgOsgiFrameworkSystemPackagesExtra OBJECT-TYPE
      SYNTAX      OCTET STRING
      MAX-ACCESS  read-only
      STATUS      current
      DESCRIPTION "The name of the org.osgi.framework.system.packages.extra property.  Note that this value, if set, will take precedence over anything specified in the init-properties. "
      ::= { osgiFrameworkEntry 9  }
   
   
   osgiFrameworkFactoryImplementationClass OBJECT-TYPE
      SYNTAX      OCTET STRING
      MAX-ACCESS  read-only
      STATUS      current
      DESCRIPTION "The name of the frameworks implementation class for the org.osgi.framework.launch.FrameworkFactory class. "
      ::= { osgiFrameworkEntry 10  }
   
   
   osgiFrameworkOrgOsgiFrameworkBootdelegation OBJECT-TYPE
      SYNTAX      OCTET STRING
      MAX-ACCESS  read-only
      STATUS      current
      DESCRIPTION "The name of the org.osgi.framework.bootdelegation property.  Note that this value, if set, will take precedence over anything specified in the init-properties. "
      ::= { osgiFrameworkEntry 11  }
   
   
   osgiFrameworkDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { osgiFrameworkEntry 12  }
   
   
   osgiFrameworkTags OBJECT-TYPE
      SYNTAX      OCTET STRING
      MAX-ACCESS  read-only
      STATUS      current
      DESCRIPTION "Return all tags on this Configuration MBean "
      ::= { osgiFrameworkEntry 13  }
   
   
   restfulManagementServicesTable OBJECT-TYPE
      SYNTAX      SEQUENCE OF RestfulManagementServicesEntry
      MAX-ACCESS  not-accessible
      STATUS      current
      DESCRIPTION "Controls the configuration of the RESTful Management Services interfaces to WebLogic Server. "
      ::= { wls 1845  }
      
   
   restfulManagementServicesEntry OBJECT-TYPE
      SYNTAX      RestfulManagementServicesEntry
      MAX-ACCESS  not-accessible
      STATUS      current
      DESCRIPTION "Generated SNMP Table Entry."
      INDEX { restfulManagementServicesIndex}
      ::= { restfulManagementServicesTable 1 }
      
   RestfulManagementServicesEntry ::=
      SEQUENCE
      {
         restfulManagementServicesIndex OCTET STRING,
         restfulManagementServicesObjectName OCTET STRING,
         restfulManagementServicesEnabled OCTET STRING,
         restfulManagementServicesType OCTET STRING,
         restfulManagementServicesJavaServiceResourcesEnabled OCTET STRING,
         restfulManagementServicesName OCTET STRING,
         restfulManagementServicesTags OCTET STRING,
         restfulManagementServicesDelegatedRequestReadTimeoutMillis INTEGER,
         restfulManagementServicesDelegatedRequestConnectTimeoutMillis INTEGER,
         restfulManagementServicesDelegatedRequestMinThreads INTEGER,
         restfulManagementServicesDelegatedRequestMaxWaitMillis INTEGER,
         restfulManagementServicesFannedOutRequestMaxWaitMillis INTEGER
      }
      
   
   restfulManagementServicesIndex OBJECT-TYPE
      SYNTAX      OCTET STRING
      MAX-ACCESS  not-accessible
      STATUS      current
      DESCRIPTION "Index column"
      ::= { restfulManagementServicesEntry 1  }
   
   
   restfulManagementServicesObjectName OBJECT-TYPE
      SYNTAX      OCTET STRING
      MAX-ACCESS  read-only
      STATUS      current
      DESCRIPTION "ObjectName column"
      ::= { restfulManagementServicesEntry 2  }
   
   
   restfulManagementServicesEnabled OBJECT-TYPE
      SYNTAX      OCTET STRING
      MAX-ACCESS  read-only
      STATUS      current
      DESCRIPTION "Enables the monitoring of this WebLogic Server domain through the RESTful Management Services Web application. "
      ::= { restfulManagementServicesEntry 3  }
   
   
   restfulManagementServicesType OBJECT-TYPE
      SYNTAX      OCTET STRING
      MAX-ACCESS  read-only
      STATUS      current
      DESCRIPTION "Returns the type of the MBean. "
      ::= { restfulManagementServicesEntry 4  }
   
   
   restfulManagementServicesJavaServiceResourcesEnabled OBJECT-TYPE
      SYNTAX      OCTET STRING
      MAX-ACCESS  read-only
      STATUS      current
      DESCRIPTION "Specifies whether the REST resource features for administering WebLogic Server as a Java Service within a cloud environment should be enabled in this domain. "
      ::= { restfulManagementServicesEntry 5  }
   
   
   restfulManagementServicesName OBJECT-TYPE
      SYNTAX      OCTET STRING
      MAX-ACCESS  read-only
      STATUS      current
      DESCRIPTION "The user-specified name of this MBean instance.  This name is included as one of the key properties in the MBean's javax.management.ObjectName:  Name=user-specified-name "
      ::= { restfulManagementServicesEntry 6  }
   
   
   restfulManagementServicesTags OBJECT-TYPE
      SYNTAX      OCTET STRING
      MAX-ACCESS  read-only
      STATUS      current
      DESCRIPTION "Return all tags on this Configuration MBean "
      ::= { restfulManagementServicesEntry 7  }
   
   
   restfulManagementServicesDelegatedRequestReadTimeoutMillis OBJECT-TYPE
      SYNTAX      INTEGER
      MAX-ACCESS  read-only
      STATUS      current
      DESCRIPTION "Determines the read timeout, in milliseconds, when the Management Services Web application propagates an idempotent REST request from the admin server to a managed server.  If DelegatedRequestReadTimeoutMillis is zero, then the default underlying JAXRS client api read timeout will be used. "
      ::= { restfulManagementServicesEntry 8  }
   
   
   restfulManagementServicesDelegatedRequestConnectTimeoutMillis OBJECT-TYPE
      SYNTAX      INTEGER
      MAX-ACCESS  read-only
      STATUS      current
      DESCRIPTION "Determines the connection timeout, in milliseconds, when the Management Services Web application propagates an idempotent REST request from the admin server to a managed server.  If DelegatedRequestConnectTimeouttMillis is zero, then the default underlying JAXRS client api connection timeout will be used. "
      ::= { restfulManagementServicesEntry 9  }
   
   
   restfulManagementServicesDelegatedRequestMinThreads OBJECT-TYPE
      SYNTAX      INTEGER
      MAX-ACCESS  read-only
      STATUS      current
      DESCRIPTION "Specifies the minimum number of threads that should be dedicated to the Management Services Web application when interacting with managed servers in parallel for improved responsiveness in large domains. "
      ::= { restfulManagementServicesEntry 10  }
   
   
   restfulManagementServicesDelegatedRequestMaxWaitMillis OBJECT-TYPE
      SYNTAX      INTEGER
      MAX-ACCESS  read-only
      STATUS      current
      DESCRIPTION "Determines how long the Management Services Web application will wait, in milliseconds, when it propagates an idempotent REST request from the admin server to a managed server.  If zero, then it will try to propagate the request once. If greater than zero, then it will retry the request until it finishes or until it detects that the time limit has been exceeded.. A request can override this value by specifying the requestMaxWaitMillis query parameter. "
      ::= { restfulManagementServicesEntry 11  }
   
   
   restfulManagementServicesFannedOutRequestMaxWaitMillis OBJECT-TYPE
      SYNTAX      INTEGER
      MAX-ACCESS  read-only
      STATUS      current
      DESCRIPTION "Determines how long the Management Services Web application will wait, in milliseconds, when it fans out an idempotent REST request from the admin server to all the managed servers.  If zero, then it will choose an appropriate timeout. . A request can override this value by specifying the requestMaxWaitMillis query parameter. "
      ::= { restfulManagementServicesEntry 12  }
   
   
   systemComponentTable OBJECT-TYPE
      SYNTAX      SEQUENCE OF SystemComponentEntry
      MAX-ACCESS  not-accessible
      STATUS      current
      DESCRIPTION " "
      ::= { wls 1850  }
      
   
   systemComponentEntry OBJECT-TYPE
      SYNTAX      SystemComponentEntry
      MAX-ACCESS  not-accessible
      STATUS      current
      DESCRIPTION "Generated SNMP Table Entry."
      INDEX { systemComponentIndex}
      ::= { systemComponentTable 1 }
      
   SystemComponentEntry ::=
      SEQUENCE
      {
         systemComponentIndex OCTET STRING,
         systemComponentObjectName OCTET STRING,
         systemComponentRestartDelaySeconds Integer32,
         systemComponentType  OCTET STRING,
         systemComponentNMSocketCreateTimeoutInMillis Integer32,
         systemComponentComponentType OCTET STRING,
         systemComponentName  OCTET STRING,
         systemComponentRestartIntervalSeconds Integer32,
         systemComponentRestartMax Integer32,
         systemComponentAutoRestart OCTET STRING,
         systemComponentTags  OCTET STRING
      }
      
   
   systemComponentIndex OBJECT-TYPE
      SYNTAX      OCTET STRING
      MAX-ACCESS  not-accessible
      STATUS      current
      DESCRIPTION "Index column"
      ::= { systemComponentEntry 1  }
   
   
   systemComponentObjectName OBJECT-TYPE
      SYNTAX      OCTET STRING
      MAX-ACCESS  read-only
      STATUS      current
      DESCRIPTION "ObjectName column"
      ::= { systemComponentEntry 2  }
   
   
   systemComponentRestartDelaySeconds OBJECT-TYPE
      SYNTAX      Integer32
      MAX-ACCESS  read-only
      STATUS      current
      DESCRIPTION " The number of seconds the Node Manager should wait before restarting this server.    After killing a server process, the system might need several seconds to release the TCP port(s) the server was using. If Node Manager attempts to restart the Managed Server while its ports are still active, the startup attempt fails.    If AutoMigration is enabled and RestartDelaySeconds is 0, the RestartDelaySeconds is automatically set to the lease time. This prevents the server from failing to restart after migration when the previous lease is still valid.  "
      ::= { systemComponentEntry 3  }
   
   
   systemComponentType OBJECT-TYPE
      SYNTAX      OCTET STRING
      MAX-ACCESS  read-only
      STATUS      current
      DESCRIPTION "Returns the type of the MBean. "
      ::= { systemComponentEntry 4  }
   
   
   systemComponentNMSocketCreateTimeoutInMillis OBJECT-TYPE
      SYNTAX      Integer32
      MAX-ACCESS  read-only
      STATUS      current
      DESCRIPTION "Returns the timeout value to be used by NodeManagerRuntime when creating a socket connection to the agent. Default set high as SSH agent may require a high connection establishment time. "
      ::= { systemComponentEntry 5  }
   
   
   systemComponentComponentType OBJECT-TYPE
      SYNTAX      OCTET STRING
      MAX-ACCESS  read-only
      STATUS      current
      DESCRIPTION "Get the system component type Examples of types may include 'OHS', 'Coherence'. New System Components may be added in the future so the list of types is not static. "
      ::= { systemComponentEntry 6  }
   
   
   systemComponentName OBJECT-TYPE
      SYNTAX      OCTET STRING
      MAX-ACCESS  read-only
      STATUS      current
      DESCRIPTION "An alphanumeric name for this server instance. (Spaces are not valid.)  The name must be unique for all configuration objects in the domain. Within a domain, each server, machine, cluster, JDBC connection pool, virtual host, and any other resource type must be named uniquely and must not use the same name as the domain.  The server name is not used as part of the URL for applications that are deployed on the server. It is for your identification purposes only. The server name displays in the Administration Console, and if you use WebLogic Server command-line utilities or APIs, you use this name to identify the server.  After you have created a server, you cannot change its name. Instead, clone the server and provide a new name for the clone. "
      ::= { systemComponentEntry 7  }
   
   
   systemComponentRestartIntervalSeconds OBJECT-TYPE
      SYNTAX      Integer32
      MAX-ACCESS  read-only
      STATUS      current
      DESCRIPTION " The number of seconds during which this server can be restarted, up to the number of times specified in RestartMax.  "
      ::= { systemComponentEntry 8  }
   
   
   systemComponentRestartMax OBJECT-TYPE
      SYNTAX      Integer32
      MAX-ACCESS  read-only
      STATUS      current
      DESCRIPTION " The number of times that the Node Manager can restart this server within the interval specified in RestartIntervalSeconds.  "
      ::= { systemComponentEntry 9  }
   
   
   systemComponentAutoRestart OBJECT-TYPE
      SYNTAX      OCTET STRING
      MAX-ACCESS  read-only
      STATUS      current
      DESCRIPTION " Specifies whether the Node Manager can automatically restart this server if it crashes or otherwise goes down unexpectedly.  "
      ::= { systemComponentEntry 10  }
   
   
   systemComponentTags OBJECT-TYPE
      SYNTAX      OCTET STRING
      MAX-ACCESS  read-only
      STATUS      current
      DESCRIPTION "Return all tags on this Configuration MBean "
      ::= { systemComponentEntry 11  }
   
   
   systemComponentStartTable OBJECT-TYPE
      SYNTAX      SEQUENCE OF SystemComponentStartEntry
      MAX-ACCESS  not-accessible
      STATUS      current
      DESCRIPTION "The NodeManager does not directly create the command to start a SystemComponent.  This is done through a plugin architecture.  So the following properties are not used when starting a SystemComponent from the NodeManager: #getJavaVendor #getJavaHome #getClassPath #getMWHome #getArguments "
      ::= { wls 1855  }
      
   
   systemComponentStartEntry OBJECT-TYPE
      SYNTAX      SystemComponentStartEntry
      MAX-ACCESS  not-accessible
      STATUS      current
      DESCRIPTION "Generated SNMP Table Entry."
      INDEX { systemComponentStartIndex}
      ::= { systemComponentStartTable 1 }
      
   SystemComponentStartEntry ::=
      SEQUENCE
      {
         systemComponentStartIndex OCTET STRING,
         systemComponentStartObjectName OCTET STRING,
         systemComponentStartJavaHome OCTET STRING,
         systemComponentStartBeaHome OCTET STRING,
         systemComponentStartArguments OCTET STRING,
         systemComponentStartType OCTET STRING,
         systemComponentStartJavaVendor OCTET STRING,
         systemComponentStartName OCTET STRING,
         systemComponentStartRootDirectory OCTET STRING,
         systemComponentStartClassPath OCTET STRING,
         systemComponentStartMWHome OCTET STRING,
         systemComponentStartTags OCTET STRING
      }
      
   
   systemComponentStartIndex OBJECT-TYPE
      SYNTAX      OCTET STRING
      MAX-ACCESS  not-accessible
      STATUS      current
      DESCRIPTION "Index column"
      ::= { systemComponentStartEntry 1  }
   
   
   systemComponentStartObjectName OBJECT-TYPE
      SYNTAX      OCTET STRING
      MAX-ACCESS  read-only
      STATUS      current
      DESCRIPTION "ObjectName column"
      ::= { systemComponentStartEntry 2  }
   
   
   systemComponentStartJavaHome OBJECT-TYPE
      SYNTAX      OCTET STRING
      MAX-ACCESS  read-only
      STATUS      current
      DESCRIPTION "The Java home directory (path on the machine running Node Manager) to use when starting this server.  Specify the parent directory of the JDK's bin directory. For example, c:&#92;bea&#92;jdk141. "
      ::= { systemComponentStartEntry 3  }
   
   
   systemComponentStartBeaHome OBJECT-TYPE
      SYNTAX      OCTET STRING
      MAX-ACCESS  read-only
      STATUS      current
      DESCRIPTION "The BEA home directory (path on the machine running Node Manager) to use when starting this server.  Specify the directory on the Node Manager machine under which all of Oracle's BEA products were installed. For example, c:&#92Oracle&#92Middleware&#92. "
      ::= { systemComponentStartEntry 4  }
   
   
   systemComponentStartArguments OBJECT-TYPE
      SYNTAX      OCTET STRING
      MAX-ACCESS  read-only
      STATUS      current
      DESCRIPTION "The arguments to use when starting this server.  These are the first arguments appended immediately after java portion of the startup command. For example, you can set Java heap memory or specify any weblogic.nodemanager.server.provider.WeblogicCacheServer option.  Separate arguments with a space. "
      ::= { systemComponentStartEntry 5  }
   
   
   systemComponentStartType OBJECT-TYPE
      SYNTAX      OCTET STRING
      MAX-ACCESS  read-only
      STATUS      current
      DESCRIPTION "Returns the type of the MBean. "
      ::= { systemComponentStartEntry 6  }
   
   
   systemComponentStartJavaVendor OBJECT-TYPE
      SYNTAX      OCTET STRING
      MAX-ACCESS  read-only
      STATUS      current
      DESCRIPTION "The Java Vendor value to use when starting this server.   If the server is part of a cluster and configured for automatic migration across possibly different platforms with different vendors providing the JDKs, then, both JavaVendor and JavaHome should be set in the generated configuration file instead. "
      ::= { systemComponentStartEntry 7  }
   
   
   systemComponentStartName OBJECT-TYPE
      SYNTAX      OCTET STRING
      MAX-ACCESS  read-only
      STATUS      current
      DESCRIPTION "The user-specified name of this MBean instance.  This name is included as one of the key properties in the MBean's javax.management.ObjectName:  Name=user-specified-name "
      ::= { systemComponentStartEntry 8  }
   
   
   systemComponentStartRootDirectory OBJECT-TYPE
      SYNTAX      OCTET STRING
      MAX-ACCESS  read-only
      STATUS      current
      DESCRIPTION "The directory that this server uses as its root directory. This directory must be on the computer that hosts the Node Manager. If you do not specify a Root Directory value, the domain directory is used by default.  "
      ::= { systemComponentStartEntry 9  }
   
   
   systemComponentStartClassPath OBJECT-TYPE
      SYNTAX      OCTET STRING
      MAX-ACCESS  read-only
      STATUS      current
      DESCRIPTION "The classpath (path on the machine running Node Manager) to use when starting this server.  If you need to add user classes to the classpath, in addition you will need to add the following: FEATURES_HOME/weblogic.server.modules.coherence.integration.jar:COHERENCE_HOME/lib/coherence.jar  where FEATURES_HOME is the features directory (typically $WL_HOME/modules/features) and COHERENCE_HOME the coherence directory (typically $ORACLE_HOME/coherence) on the Node Manager machine. If you do not specify a classpath the above will be used automatically.   The operating system determines which character separates path elements. On Windows, use a semicolon (;). On UNIX a colon (:). "
      ::= { systemComponentStartEntry 10  }
   
   
   systemComponentStartMWHome OBJECT-TYPE
      SYNTAX      OCTET STRING
      MAX-ACCESS  read-only
      STATUS      current
      DESCRIPTION "The MWHome directory (path on the machine running Node Manager) to use when starting this server.  Specify the directory on the Node Manager machine under which all of Oracle's MW products were installed. For example, c:&#92;Oracle&#92;Middleware&#92;. "
      ::= { systemComponentStartEntry 11  }
   
   
   systemComponentStartTags OBJECT-TYPE
      SYNTAX      OCTET STRING
      MAX-ACCESS  read-only
      STATUS      current
      DESCRIPTION "Return all tags on this Configuration MBean "
      ::= { systemComponentStartEntry 12  }
   
   
   transactionLogJDBCStoreTable OBJECT-TYPE
      SYNTAX      SEQUENCE OF TransactionLogJDBCStoreEntry
      MAX-ACCESS  not-accessible
      STATUS      current
      DESCRIPTION "This class represents a Transaction Log JDBC Store configuration. "
      ::= { wls 1860  }
      
   
   transactionLogJDBCStoreEntry OBJECT-TYPE
      SYNTAX      TransactionLogJDBCStoreEntry
      MAX-ACCESS  not-accessible
      STATUS      current
      DESCRIPTION "Generated SNMP Table Entry."
      INDEX { transactionLogJDBCStoreIndex}
      ::= { transactionLogJDBCStoreTable 1 }
      
   TransactionLogJDBCStoreEntry ::=
      SEQUENCE
      {
         transactionLogJDBCStoreIndex OCTET STRING,
         transactionLogJDBCStoreObjectName OCTET STRING,
         transactionLogJDBCStoreEnabled OCTET STRING,
         transactionLogJDBCStoreLogicalName OCTET STRING,
         transactionLogJDBCStoreRetryIntervalSeconds Integer32,
         transactionLogJDBCStoreType OCTET STRING,
         transactionLogJDBCStoreCreateTableDDLFile OCTET STRING,
         transactionLogJDBCStorePrefixName OCTET STRING,
         transactionLogJDBCStoreInsertsPerBatchMaximum Integer32,
         transactionLogJDBCStoreThreeStepThreshold Integer32,
         transactionLogJDBCStoreXAResourceName OCTET STRING,
         transactionLogJDBCStoreDeletesPerBatchMaximum Integer32,
         transactionLogJDBCStoreName OCTET STRING,
         transactionLogJDBCStoreDeletesPerStatementMaximum Integer32,
         transactionLogJDBCStoreMaxRetrySecondsBeforeTLOGFail Integer32,
         transactionLogJDBCStoreWorkerPreferredBatchSize Integer32,
         transactionLogJDBCStoreWorkerCount Integer32,
         transactionLogJDBCStoreMaxRetrySecondsBeforeTXException Integer32,
         transactionLogJDBCStoreDeploymentOrder Integer32,
         transactionLogJDBCStoreOraclePiggybackCommitEnabled OCTET STRING,
         transactionLogJDBCStorePartialClusterStabilityDelaySeconds Counter64,
         transactionLogJDBCStoreRestartInPlace OCTET STRING,
         transactionLogJDBCStoreNumberOfRestartAttempts INTEGER,
         transactionLogJDBCStoreSecondsBetweenRestarts INTEGER,
         transactionLogJDBCStoreDistributionPolicy OCTET STRING,
         transactionLogJDBCStoreTags OCTET STRING,
         transactionLogJDBCStoreMigrationPolicy OCTET STRING,
         transactionLogJDBCStoreReconnectRetryPeriodMillis INTEGER,
         transactionLogJDBCStoreFailbackDelaySeconds Counter64,
         transactionLogJDBCStoreInitialBootDelaySeconds Counter64,
         transactionLogJDBCStoreReconnectRetryIntervalMillis INTEGER,
         transactionLogJDBCStoreConnectionCachingPolicy OCTET STRING,
         transactionLogJDBCStoreFailOverLimit INTEGER
      }
      
   
   transactionLogJDBCStoreIndex OBJECT-TYPE
      SYNTAX      OCTET STRING
      MAX-ACCESS  not-accessible
      STATUS      current
      DESCRIPTION "Index column"
      ::= { transactionLogJDBCStoreEntry 1  }
   
   
   transactionLogJDBCStoreObjectName OBJECT-TYPE
      SYNTAX      OCTET STRING
      MAX-ACCESS  read-only
      STATUS      current
      DESCRIPTION "ObjectName column"
      ::= { transactionLogJDBCStoreEntry 2  }
   
   
   transactionLogJDBCStoreEnabled OBJECT-TYPE
      SYNTAX      OCTET STRING
      MAX-ACCESS  read-only
      STATUS      current
      DESCRIPTION "When true, TLOGs are logged to a TLOG JDBC Store; otherwise, TLOGs are logged to the server's default store. When using the Administration Console, select JDBC to enable logging of TLOGs to a JDBC store; select Default Store to enable logging of TLOGs to the server's default store.  "
      ::= { transactionLogJDBCStoreEntry 3  }
   
   
   transactionLogJDBCStoreLogicalName OBJECT-TYPE
      SYNTAX      OCTET STRING
      MAX-ACCESS  read-only
      STATUS      current
      DESCRIPTION "The name used by subsystems to refer to different stores on different servers using the same name.  For example, an EJB that uses the timer service may refer to its store using the logical name, and this name may be valid on multiple servers in the same cluster, even if each server has a store with a different physical name.  Multiple stores in the same domain or the same cluster may share the same logical name. However, a given logical name may not be assigned to more than one store on the same server. "
      ::= { transactionLogJDBCStoreEntry 4  }
   
   
   transactionLogJDBCStoreRetryIntervalSeconds OBJECT-TYPE
      SYNTAX      Integer32
      MAX-ACCESS  read-only
      STATUS      current
      DESCRIPTION "The amount of time, in seconds, WebLogic Server waits before attempting to verify the health of the TLOG store after a store failure has occurred.  "
      ::= { transactionLogJDBCStoreEntry 5  }
   
   
   transactionLogJDBCStoreType OBJECT-TYPE
      SYNTAX      OCTET STRING
      MAX-ACCESS  read-only
      STATUS      current
      DESCRIPTION "Returns the type of the MBean. "
      ::= { transactionLogJDBCStoreEntry 6  }
   
   
   transactionLogJDBCStoreCreateTableDDLFile OBJECT-TYPE
      SYNTAX      OCTET STRING
      MAX-ACCESS  read-only
      STATUS      current
      DESCRIPTION "Specifies the DDL (Data Definition Language) file to use for creating the JDBC store's backing table.    This field is ignored when the JDBC store's backing table, WLStore, already exists.    If a DDL file is not specified and the JDBC store detects that a backing table doesn't already exist, the JDBC store automatically creates the table by executing a preconfigured DDL file that is specific to the database vendor. These preconfigured files are located in the  weblogic\store\io\jdbc\ddl directory of the MIDDLEWARE_HOME\modules\com.bea.core.store.jdbc_x.x.x.x.jar file.    If a DDL file is specified and the JDBC store detects that a backing table doesn't already exist, then the JDBC store searches for the DDL file in the file path first, and then if the file is not found, it searches for it in the CLASSPATH. Once found, the SQL within the DDL file is executed to create the JDBC store's database table. If the DDL file is not found and the backing table doesn't already exist, the JDBC store will fail to boot.   "
      ::= { transactionLogJDBCStoreEntry 7  }
   
   
   transactionLogJDBCStorePrefixName OBJECT-TYPE
      SYNTAX      OCTET STRING
      MAX-ACCESS  read-only
      STATUS      current
      DESCRIPTION "When using multiple TLOG JDBC stores, use this attribute to create a label ending in '_'  that is prepended to the name of the server hosting the JDBC TLOG store and ends in '_' to form a unique JDBC TLOG store name for each configured JDBC TLOG store.  The default prefix name is 'TLOG_' . For example, a valid JDBC TLOG store name using the default Prefix Name is TLOG_MyServer_  where TLOG_ is the Prefix Name and MyServer is the name of the server hosting the JDBC TLOG store. "
      ::= { transactionLogJDBCStoreEntry 8  }
   
   
   transactionLogJDBCStoreInsertsPerBatchMaximum OBJECT-TYPE
      SYNTAX      Integer32
      MAX-ACCESS  read-only
      STATUS      current
      DESCRIPTION "The maximum number of table rows that are inserted per database call.    When possible, a JDBC store uses JDBC 3.0 batching to batch concurrent client requests.    Both the maximum batch size for concurrent inserts and for concurrent writes are configurable.    To disable JDBC 3.0 batching, set the maximum batch size to 1.    The maximum batch size has no effect on the maximum number of concurrent client requests.   "
      ::= { transactionLogJDBCStoreEntry 9  }
   
   
   transactionLogJDBCStoreThreeStepThreshold OBJECT-TYPE
      SYNTAX      Integer32
      MAX-ACCESS  read-only
      STATUS      current
      DESCRIPTION "Specifies the threshold, in bytes, when the JDBC store uses 3 steps (insert, select, populate) instead of 1 step (insert) to populate an Oracle Blob data type.  Applies only to Oracle databases where a Blob data type is used instead of the default Long Raw data type for record data.  The default value is 200000. "
      ::= { transactionLogJDBCStoreEntry 10  }
   
   
   transactionLogJDBCStoreXAResourceName OBJECT-TYPE
      SYNTAX      OCTET STRING
      MAX-ACCESS  read-only
      STATUS      current
      DESCRIPTION "Overrides the name of the XAResource that this store registers with JTA.  You should not normally set this attribute. Its purpose is to allow the name of the XAResource to be overridden when a store has been upgraded from an older release and the store contained prepared transactions. The generated name should be used in all other cases. "
      ::= { transactionLogJDBCStoreEntry 11  }
   
   
   transactionLogJDBCStoreDeletesPerBatchMaximum OBJECT-TYPE
      SYNTAX      Integer32
      MAX-ACCESS  read-only
      STATUS      current
      DESCRIPTION "The maximum number of table rows that are deleted per database call.    When possible, a JDBC store uses JDBC 3.0 batching to batch concurrent client requests.    Both the maximum batch size for concurrent inserts and for concurrent writes are configurable.    To disable JDBC 3.0 batching, set the maximum batch size to 1.    The maximum batch size has no effect on the maximum number of concurrent client requests.   "
      ::= { transactionLogJDBCStoreEntry 12  }
   
   
   transactionLogJDBCStoreName OBJECT-TYPE
      SYNTAX      OCTET STRING
      MAX-ACCESS  read-only
      STATUS      current
      DESCRIPTION "The user-specified name of this MBean instance.  This name is included as one of the key properties in the MBean's javax.management.ObjectName:  Name=user-specified-name "
      ::= { transactionLogJDBCStoreEntry 13  }
   
   
   transactionLogJDBCStoreDeletesPerStatementMaximum OBJECT-TYPE
      SYNTAX      Integer32
      MAX-ACCESS  read-only
      STATUS      current
      DESCRIPTION "The maximum number of table rows that are deleted per database call.    Applies only when a JDBC store does not use JDBC 3.0 batching to batch concurrent client requests.    The maximum deletes per statement has no effect on the maximum number of concurrent client requests.    For some databases, the JDBC store may choose a lower value than the one configured.   "
      ::= { transactionLogJDBCStoreEntry 14  }
   
   
   transactionLogJDBCStoreMaxRetrySecondsBeforeTLOGFail OBJECT-TYPE
      SYNTAX      Integer32
      MAX-ACCESS  read-only
      STATUS      current
      DESCRIPTION "The maximum amount of time, in seconds, WebLogic Server tries to recover from a JDBC TLog store failure. If store remains unusable after this period, WebLogic Server set the health state to HEALTH_FAILED. A value of 0 indicates WebLogic Server does not conduct a retry and and immediately sets the health state as HEALTH_FAILED.  "
      ::= { transactionLogJDBCStoreEntry 15  }
   
   
   transactionLogJDBCStoreWorkerPreferredBatchSize OBJECT-TYPE
      SYNTAX      Integer32
      MAX-ACCESS  read-only
      STATUS      current
      DESCRIPTION "Specifies the batch size when the Worker Count attribute is configured to a value greater than 1. Used to configure the workload the JDBC store incrementally puts on each worker thread. The workload consists of IO requests which are grouped and pushed to each JDBC worker thread for processing. If the IO request is very large (for example 1M), then tune this attribute to a smaller value. "
      ::= { transactionLogJDBCStoreEntry 16  }
   
   
   transactionLogJDBCStoreWorkerCount OBJECT-TYPE
      SYNTAX      Integer32
      MAX-ACCESS  read-only
      STATUS      current
      DESCRIPTION "The number of JDBC store worker threads to process the workerload.  A value of 1 indicates a single thread is used (the default). A value greater than 1 indicates that multiple threads are used. For Oracle databases, Oracle recommends users rebuild the primary key index into a reverse index for the JDBC Store table when the worker count is greater than 1. For non-Oracle databases, refer to the database provider's documentation for help with indexing.  "
      ::= { transactionLogJDBCStoreEntry 17  }
   
   
   transactionLogJDBCStoreMaxRetrySecondsBeforeTXException OBJECT-TYPE
      SYNTAX      Integer32
      MAX-ACCESS  read-only
      STATUS      current
      DESCRIPTION "The maximum amount of time, in seconds, WebLogic Server waits before trying to recover from a JDBC TLog store failure while processing a transaction. If store remains unusable after this amount of time, WebLogic Server throws an exception the affected transaction. A value of 0 indicates WebLogic Server does not conduct a retry and an exception will thrown immediately. The practical maximum value is a value less than the current value of MaxRetrySecondsBeforeTLogFail. "
      ::= { transactionLogJDBCStoreEntry 18  }
   
   
   transactionLogJDBCStoreDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { transactionLogJDBCStoreEntry 19  }
   
   
   transactionLogJDBCStoreOraclePiggybackCommitEnabled OBJECT-TYPE
      SYNTAX      OCTET STRING
      MAX-ACCESS  read-only
      STATUS      current
      DESCRIPTION "Enables committing a batch of INSERT or DELETE operations with the last operation of the transaction instead of issuing a separate commit call to database server which saves a server round trip. This feature benefits applications that have many transactions of a small number of operations or small messages. "
      ::= { transactionLogJDBCStoreEntry 20  }
   
   
   transactionLogJDBCStorePartialClusterStabilityDelaySeconds OBJECT-TYPE
      SYNTAX      Counter64
      MAX-ACCESS  read-only
      STATUS      current
      DESCRIPTION "Specifies the amount of time, in seconds, to delay before a partially started cluster starts all cluster-targeted JMS artifact instances that are configured with a Migration Policy of Always or On-Failure.   Before this timeout expires or all servers are running, a cluster starts a subset of such instances based on the total number of servers running and the configured cluster size. Once the timeout expires or all servers have started, the system considers the cluster stable and starts any remaining services.  This delay ensures that services are balanced across a cluster even if the servers are started sequentially. It is ignored after a cluster is fully started (stable) or when individual servers are started.   A value > 0 specifies the time, in seconds, to delay before a partially started cluster starts dynamically configured services. A value of 0 specifies no delay.  "
      ::= { transactionLogJDBCStoreEntry 21  }
   
   
   transactionLogJDBCStoreRestartInPlace OBJECT-TYPE
      SYNTAX      OCTET STRING
      MAX-ACCESS  read-only
      STATUS      current
      DESCRIPTION " Enables a periodic automatic in-place restart of failed cluster-targeted or standalone-server-targeted JMS artifact instance(s) running on healthy WebLogic Server instances. See the migratable target settings for in-place restarts of migratable-targeted JMS artifacts. When the Restart In Place setting is configured on a store, it applies to all JMS artifacts that reference the store.    If the Migration Policy of the JMS artifact is set to Off, Restart In Place is disabled by default.  If the Migration Policy of the JMS artifact is set to On-Failure or Always, Restart In Place is enabled by default.  This attribute is not used by WebLogic messaging bridges which automatically restart internal connections as needed.  For a JMS artifact that is cluster-targeted and the Migration Policy is set to On-Failure or Always, if restart fails after the configured maximum retry attempts, it will migrate to a different server within the cluster.    "
      ::= { transactionLogJDBCStoreEntry 22  }
   
   
   transactionLogJDBCStoreNumberOfRestartAttempts OBJECT-TYPE
      SYNTAX      INTEGER
      MAX-ACCESS  read-only
      STATUS      current
      DESCRIPTION "Specifies the maximum number of restart attempts.   A value > 0 specifies the maximum number of restart attempts. A value of 0 specifies the same behavior as setting {@link #getRestartInPlace} to false. A value of -1 means infinite retry restart until it either starts or the server instance shuts down.  "
      ::= { transactionLogJDBCStoreEntry 23  }
   
   
   transactionLogJDBCStoreSecondsBetweenRestarts OBJECT-TYPE
      SYNTAX      INTEGER
      MAX-ACCESS  read-only
      STATUS      current
      DESCRIPTION "Specifies the amount of time, in seconds, to wait in between attempts to restart a failed service instance. "
      ::= { transactionLogJDBCStoreEntry 24  }
   
   
   transactionLogJDBCStoreDistributionPolicy OBJECT-TYPE
      SYNTAX      OCTET STRING
      MAX-ACCESS  read-only
      STATUS      current
      DESCRIPTION "Specifies how the instances of a configured JMS artifact are named and distributed when cluster-targeted.  A JMS artifact is cluster-targeted when its target is directly set to a cluster, or when it is scoped to a resource group and the resource group is in turn targeted to a cluster.  When this setting is configured on a store, it applies to all JMS artifacts that reference the store.  Valid options:   Distributed Creates an instance on each server JVM in a cluster. Required for all SAF agents and for cluster-targeted or resource-group-scoped JMS servers that host distributed destinations.    Singleton Creates a single instance on a single server JVM within a cluster. Required for cluster-targeted or resource-group-scoped JMS servers that host standalone (non-distributed) destinations and for cluster-targeted or resource-group-scoped path services.  The Migration Policy must be On-Failure or Always when using this option with a JMS server, On-Failure when using this option with a messaging bridge, and Always when using this option with a path service.    Instance Naming Note:   The DistributionPolicy determines the instance name suffix for cluster-targeted JMS artifacts.  The suffix for a cluster-targeted Singleton is -01 and for a cluster-targeted Distributed is @ClusterMemberName.    Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   If you cannot cluster-target a bridge and still need singleton behavior in a configured cluster, you can target the bridge to a migratable target and configure the Migration Policy on the migratable target to Exactly-Once.   "
      ::= { transactionLogJDBCStoreEntry 25  }
   
   
   transactionLogJDBCStoreTags OBJECT-TYPE
      SYNTAX      OCTET STRING
      MAX-ACCESS  read-only
      STATUS      current
      DESCRIPTION "Return all tags on this Configuration MBean "
      ::= { transactionLogJDBCStoreEntry 26  }
   
   
   transactionLogJDBCStoreMigrationPolicy OBJECT-TYPE
      SYNTAX      OCTET STRING
      MAX-ACCESS  read-only
      STATUS      current
      DESCRIPTION "Controls migration and restart behavior of cluster-targeted JMS service artifact instances. When this setting is configured on a cluster-targeted store, it applies to all JMS artifacts that reference the store. See the migratable target settings for enabling migration and restart on migratable-targeted JMS artifacts.  Off Disables migration support for cluster-targeted JMS service objects, and changes the default for Restart In Place to false. If you want a restart to be enabled when the Migration Policy is Off, then Restart In Place must be explicitly configured to true. This policy cannot be combined with the Singleton Migration Policy.  On-Failure Enables automatic migration and restart of instances on the failure of a subsystem Service or WebLogic Server instance, including automatic fail-back and load balancing of instances.   Always Provides the same behavior as On-Failure and automatically migrates instances even in the event of a graceful shutdown or a partial cluster start.   Note: Cluster leasing must be configured for On-Failure and Always.  Messaging Bridge Notes:   When an instance per server is desired for a cluster-targeted messaging bridge, Oracle recommends setting the bridge Distributed Policy and Migration Policy to Distributed/Off, respectively; these are the defaults.   When a single instance per cluster is desired for a cluster-targeted bridge, Oracle recommends setting the bridge Distributed Policy and Migration Policy to Singleton/On-Failure, respectively.   A Migration Policy of Always is not recommended for bridges.   If you cannot cluster-target a bridge and still need singleton behavior in a configured cluster, you can target the bridge to a migratable target and configure the Migration Policy on the migratable target to Exactly-Once.   "
      ::= { transactionLogJDBCStoreEntry 27  }
   
   
   transactionLogJDBCStoreReconnectRetryPeriodMillis OBJECT-TYPE
      SYNTAX      INTEGER
      MAX-ACCESS  read-only
      STATUS      current
      DESCRIPTION "Returns the length of time in milliseconds during which the persistent store will attempt to re-establish a connection to the database.  Successive reconnection attempts will be attempted after a fixed delay that is specified by the reconnection retry interval.  The reconnection period applies to JDBC connections regardless of the database that is used for the JDBC store.  The default value is 1000 "
      ::= { transactionLogJDBCStoreEntry 28  }
   
   
   transactionLogJDBCStoreFailbackDelaySeconds OBJECT-TYPE
      SYNTAX      Counter64
      MAX-ACCESS  read-only
      STATUS      current
      DESCRIPTION "Specifies the amount of time, in seconds, to delay before failing a cluster-targeted JMS artifact instance back to its preferred server after the preferred server failed and was restarted.  This delay allows time for the system to stabilize and dependent services to be restarted, preventing a system failure during a reboot.   A value > 0 specifies the time, in seconds, to delay before failing a JMS artifact back to its user preferred server. A value of 0 indicates that the instance would never failback. A value of -1 indicates that there is no delay and the instance would failback immediately.   Note: This setting only applies when the JMS artifact is cluster-targeted and the Migration Policy is set to On-Failure or Always. "
      ::= { transactionLogJDBCStoreEntry 29  }
   
   
   transactionLogJDBCStoreInitialBootDelaySeconds OBJECT-TYPE
      SYNTAX      Counter64
      MAX-ACCESS  read-only
      STATUS      current
      DESCRIPTION "Specifies the amount of time, in seconds, to delay before starting a cluster-targeted JMS instance on a newly booted WebLogic Server instance. When this setting is configured on a store, it applies to all JMS artifacts that reference the store.  This allows time for the system to stabilize and dependent services to be restarted, preventing a system failure during a reboot.   A value > 0 is the time, in seconds, to delay before before loading resources after a failure and restart. A value of 0 specifies no delay.  Note: This setting only applies when the JMS artifact is cluster-targeted and the Migration Policy is set to On-Failure or Always. "
      ::= { transactionLogJDBCStoreEntry 30  }
   
   
   transactionLogJDBCStoreReconnectRetryIntervalMillis OBJECT-TYPE
      SYNTAX      INTEGER
      MAX-ACCESS  read-only
      STATUS      current
      DESCRIPTION "The length of time in milliseconds between reconnection attempts during the reconnection retry period.  The reconnection interval applies to JDBC connections regardless of the database that is used for the JDBC store.  The default value is 200 milliseconds "
      ::= { transactionLogJDBCStoreEntry 31  }
   
   
   transactionLogJDBCStoreConnectionCachingPolicy OBJECT-TYPE
      SYNTAX      OCTET STRING
      MAX-ACCESS  read-only
      STATUS      current
      DESCRIPTION "Advanced use only: gets the connection caching policy for the JDBC store.  The return values will be one of:  JMSConstants.JDBCSTORE_CONNECTION_CACHING_POLICY_DEFAULT (&quot;DEFAULT&quot;) JMSConstants.JDBCSTORE_CONNECTION_CACHING_POLICY_MINIMAL (&quot;MINIMAL&quot;) JMSConstants.JDBCSTORE_CONNECTION_CACHING_POLICY_NONE (&quot;NONE&quot;)   IMPORTANT: See the below for additional usage information, particularly regarding NONE  DEFAULT The default mode of operation for the JDBC store.  The JDBC store will open two connections to the database and it will keep these connections open for the life of the store. In addition, if the worker count for the store is two or more, then it will open one connection for each of the workers and those connections will also stay open for the life of the JDBC store.  If the worker count is 3 then the JDBC store will use 5 database connections.  If the worker count is the default of 1 then the JDBC store will use just 2 connections.The DEFAULT setting is the recommended setting to be used when the database backing the JDBC store is not constrained with respect to the number of open connections.  MINIMAL The JDBC store will open one connection to the database and it will keep that connection open for the life of the store. In addition, if the worker count for the store is two or more, then it will open one connection for each of the workers and those connections will also stay open for the life of the JDBC store. If the worker count is 3 then the JDBC store will use 4 database connections. If the worker count is the default of 1 then the JDBC store will use just 1 connection. The MINIMAL setting may result in a slight reduction of through-put for low concurrency messaging scenarios in comparison to DEFAULT.  NONE The NONE connection caching policy is for 'advanced usage only'. The JDBC store will open one connection to the database on an as-needed basis to perform I/O and it will release that connection when the operation is complete. The NONE value is not compatible with a configured worker count of 2 or more and will result in a configuration validation exception. The NONE setting may result in a slight reduction of through-put for low concurrency messaging scenarios in comparison to DEFAULT or MINIMAL.  NOTE: It is strongly recommended that a JDBC store be configured with a dedicated data source when the store is configured with the NONE connection caching policy.  A store that shares a data source with other non-store components or applications runs the risk of failing due to dead-locks.  Please note that a JDBC store will require more than one connection when first started. As such, a data source should be configured to grow and shrink so that the JDBC store can initialize. "
      ::= { transactionLogJDBCStoreEntry 32  }
   
   
   transactionLogJDBCStoreFailOverLimit OBJECT-TYPE
      SYNTAX      INTEGER
      MAX-ACCESS  read-only
      STATUS      current
      DESCRIPTION "Specify a limit for the number of cluster-targeted JMS artifact instances that can fail over to a particular JVM.  This can be used to prevent too many instances from starting on a server, avoiding a system failure when starting too few servers of a formerly large cluster.  A typical limit value should allow all instances to run in the smallest desired cluster size, which means (smallest-cluster-size * (limit + 1)) should equal or exceed the total number of instances.    A value of -1 means there is no fail over limit (unlimited). A value of 0 prevents any fail overs of cluster-targeted JMS artifact instances, so no more than 1 instance will run per server (this is an instance that has not failed over). A value of 1 allows one fail-over instance on each server, so no more than two instances will run per server (one failed over instance plus an instance that has not failed over).   Note: This setting only applies when the JMS artifact is cluster-targeted and the Migration Policy is set to On-Failure or Always. "
      ::= { transactionLogJDBCStoreEntry 33  }
   
   
   wLSAuthConfigProviderTable OBJECT-TYPE
      SYNTAX      SEQUENCE OF WLSAuthConfigProviderEntry
      MAX-ACCESS  not-accessible
      STATUS      current
      DESCRIPTION " "
      ::= { wls 1865  }
      
   
   wLSAuthConfigProviderEntry OBJECT-TYPE
      SYNTAX      WLSAuthConfigProviderEntry
      MAX-ACCESS  not-accessible
      STATUS      current
      DESCRIPTION "Generated SNMP Table Entry."
      INDEX { wLSAuthConfigProviderIndex}
      ::= { wLSAuthConfigProviderTable 1 }
      
   WLSAuthConfigProviderEntry ::=
      SEQUENCE
      {
         wLSAuthConfigProviderIndex OCTET STRING,
         wLSAuthConfigProviderObjectName OCTET STRING,
         wLSAuthConfigProviderType OCTET STRING,
         wLSAuthConfigProviderName OCTET STRING,
         wLSAuthConfigProviderTags OCTET STRING
      }
      
   
   wLSAuthConfigProviderIndex OBJECT-TYPE
      SYNTAX      OCTET STRING
      MAX-ACCESS  not-accessible
      STATUS      current
      DESCRIPTION "Index column"
      ::= { wLSAuthConfigProviderEntry 1  }
   
   
   wLSAuthConfigProviderObjectName OBJECT-TYPE
      SYNTAX      OCTET STRING
      MAX-ACCESS  read-only
      STATUS      current
      DESCRIPTION "ObjectName column"
      ::= { wLSAuthConfigProviderEntry 2  }
   
   
   wLSAuthConfigProviderType OBJECT-TYPE
      SYNTAX      OCTET STRING
      MAX-ACCESS  read-only
      STATUS      current
      DESCRIPTION "Returns the type of the MBean. "
      ::= { wLSAuthConfigProviderEntry 3  }
   
   
   wLSAuthConfigProviderName OBJECT-TYPE
      SYNTAX      OCTET STRING
      MAX-ACCESS  read-only
      STATUS      current
      DESCRIPTION "The user-specified name of this MBean instance.  This name is included as one of the key properties in the MBean's javax.management.ObjectName:  Name=user-specified-name "
      ::= { wLSAuthConfigProviderEntry 4  }
   
   
   wLSAuthConfigProviderTags OBJECT-TYPE
      SYNTAX      OCTET STRING
      MAX-ACCESS  read-only
      STATUS      current
      DESCRIPTION "Return all tags on this Configuration MBean "
      ::= { wLSAuthConfigProviderEntry 5  }
   
   
   webserviceTestpageTable OBJECT-TYPE
      SYNTAX      SEQUENCE OF WebserviceTestpageEntry
      MAX-ACCESS  not-accessible
      STATUS      current
      DESCRIPTION "Controls the configuration of the Web Service Test Page. "
      ::= { wls 1870  }
      
   
   webserviceTestpageEntry OBJECT-TYPE
      SYNTAX      WebserviceTestpageEntry
      MAX-ACCESS  not-accessible
      STATUS      current
      DESCRIPTION "Generated SNMP Table Entry."
      INDEX { webserviceTestpageIndex}
      ::= { webserviceTestpageTable 1 }
      
   WebserviceTestpageEntry ::=
      SEQUENCE
      {
         webserviceTestpageIndex OCTET STRING,
         webserviceTestpageObjectName OCTET STRING,
         webserviceTestpageEnabled OCTET STRING,
         webserviceTestpageType OCTET STRING,
         webserviceTestpageName OCTET STRING,
         webserviceTestpageBasicAuthEnabled OCTET STRING,
         webserviceTestpageTags OCTET STRING
      }
      
   
   webserviceTestpageIndex OBJECT-TYPE
      SYNTAX      OCTET STRING
      MAX-ACCESS  not-accessible
      STATUS      current
      DESCRIPTION "Index column"
      ::= { webserviceTestpageEntry 1  }
   
   
   webserviceTestpageObjectName OBJECT-TYPE
      SYNTAX      OCTET STRING
      MAX-ACCESS  read-only
      STATUS      current
      DESCRIPTION "ObjectName column"
      ::= { webserviceTestpageEntry 2  }
   
   
   webserviceTestpageEnabled OBJECT-TYPE
      SYNTAX      OCTET STRING
      MAX-ACCESS  read-only
      STATUS      current
      DESCRIPTION "Specifies whether the WebLogic Server automatically deploys Web Service Test Page in the current domain. "
      ::= { webserviceTestpageEntry 3  }
   
   
   webserviceTestpageType OBJECT-TYPE
      SYNTAX      OCTET STRING
      MAX-ACCESS  read-only
      STATUS      current
      DESCRIPTION "Returns the type of the MBean. "
      ::= { webserviceTestpageEntry 4  }
   
   
   webserviceTestpageName OBJECT-TYPE
      SYNTAX      OCTET STRING
      MAX-ACCESS  read-only
      STATUS      current
      DESCRIPTION "The user-specified name of this MBean instance.  This name is included as one of the key properties in the MBean's javax.management.ObjectName:  Name=user-specified-name "
      ::= { webserviceTestpageEntry 5  }
   
   
   webserviceTestpageBasicAuthEnabled OBJECT-TYPE
      SYNTAX      OCTET STRING
      MAX-ACCESS  read-only
      STATUS      current
      DESCRIPTION "Specifies whether the basic authentication is automatically used by Web Service Test Page in the current domain. "
      ::= { webserviceTestpageEntry 6  }
   
   
   webserviceTestpageTags OBJECT-TYPE
      SYNTAX      OCTET STRING
      MAX-ACCESS  read-only
      STATUS      current
      DESCRIPTION "Return all tags on this Configuration MBean "
      ::= { webserviceTestpageEntry 7  }
   
   
   connectorWorkManagerRuntimeTable OBJECT-TYPE
      SYNTAX      SEQUENCE OF ConnectorWorkManagerRuntimeEntry
      MAX-ACCESS  not-accessible
      STATUS      current
      DESCRIPTION "This class is used for monitoring Connector Work Manager of resource adapters. "
      ::= { wls 1875  }
      
   
   connectorWorkManagerRuntimeEntry OBJECT-TYPE
      SYNTAX      ConnectorWorkManagerRuntimeEntry
      MAX-ACCESS  not-accessible
      STATUS      current
      DESCRIPTION "Generated SNMP Table Entry."
      INDEX { connectorWorkManagerRuntimeIndex}
      ::= { connectorWorkManagerRuntimeTable 1 }
      
   ConnectorWorkManagerRuntimeEntry ::=
      SEQUENCE
      {
         connectorWorkManagerRuntimeIndex OCTET STRING,
         connectorWorkManagerRuntimeObjectName OCTET STRING,
         connectorWorkManagerRuntimeCompletedLongRunningRequests Integer32,
         connectorWorkManagerRuntimeType OCTET STRING,
         connectorWorkManagerRuntimeActiveLongRunningRequests Integer32,
         connectorWorkManagerRuntimeMaxConcurrentLongRunningRequests Integer32,
         connectorWorkManagerRuntimeName OCTET STRING
      }
      
   
   connectorWorkManagerRuntimeIndex OBJECT-TYPE
      SYNTAX      OCTET STRING
      MAX-ACCESS  not-accessible
      STATUS      current
      DESCRIPTION "Index column"
      ::= { connectorWorkManagerRuntimeEntry 1  }
   
   
   connectorWorkManagerRuntimeObjectName OBJECT-TYPE
      SYNTAX      OCTET STRING
      MAX-ACCESS  read-only
      STATUS      current
      DESCRIPTION "ObjectName column"
      ::= { connectorWorkManagerRuntimeEntry 2  }
   
   
   connectorWorkManagerRuntimeCompletedLongRunningRequests OBJECT-TYPE
      SYNTAX      Integer32
      MAX-ACCESS  read-only
      STATUS      current
      DESCRIPTION "The number of completed long-running work requests. "
      ::= { connectorWorkManagerRuntimeEntry 3  }
   
   
   connectorWorkManagerRuntimeType OBJECT-TYPE
      SYNTAX      OCTET STRING
      MAX-ACCESS  read-only
      STATUS      current
      DESCRIPTION "Returns the type of the MBean. "
      ::= { connectorWorkManagerRuntimeEntry 4  }
   
   
   connectorWorkManagerRuntimeActiveLongRunningRequests OBJECT-TYPE
      SYNTAX      Integer32
      MAX-ACCESS  read-only
      STATUS      current
      DESCRIPTION "Return The number of current active long-running work requests. "
      ::= { connectorWorkManagerRuntimeEntry 5  }
   
   
   connectorWorkManagerRuntimeMaxConcurrentLongRunningRequests OBJECT-TYPE
      SYNTAX      Integer32
      MAX-ACCESS  read-only
      STATUS      current
      DESCRIPTION "The maximum number of allowed concurrent long-running work requests. New work submission will be rejected if current running long-running work requests exceed the limit. "
      ::= { connectorWorkManagerRuntimeEntry 6  }
   
   
   connectorWorkManagerRuntimeName OBJECT-TYPE
      SYNTAX      OCTET STRING
      MAX-ACCESS  read-only
      STATUS      current
      DESCRIPTION "The name of this configuration. WebLogic Server uses an MBean to implement and persist the configuration. "
      ::= { connectorWorkManagerRuntimeEntry 7  }
   
   
   jdbcMultiDataSourceRuntimeTable OBJECT-TYPE
      SYNTAX      SEQUENCE OF JdbcMultiDataSourceRuntimeEntry
      MAX-ACCESS  not-accessible
      STATUS      current
      DESCRIPTION "This class is used for monitoring a WebLogic JDBC Multi Data Source and its associated data sources. "
      ::= { wls 1880  }
      
   
   jdbcMultiDataSourceRuntimeEntry OBJECT-TYPE
      SYNTAX      JdbcMultiDataSourceRuntimeEntry
      MAX-ACCESS  not-accessible
      STATUS      current
      DESCRIPTION "Generated SNMP Table Entry."
      INDEX { jdbcMultiDataSourceRuntimeIndex}
      ::= { jdbcMultiDataSourceRuntimeTable 1 }
      
   JdbcMultiDataSourceRuntimeEntry ::=
      SEQUENCE
      {
         jdbcMultiDataSourceRuntimeIndex OCTET STRING,
         jdbcMultiDataSourceRuntimeObjectName OCTET STRING,
         jdbcMultiDataSourceRuntimeType OCTET STRING,
         jdbcMultiDataSourceRuntimeModuleId OCTET STRING,
         jdbcMultiDataSourceRuntimeName OCTET STRING,
         jdbcMultiDataSourceRuntimeMaxCapacity Integer32,
         jdbcMultiDataSourceRuntimeDeploymentState Integer32
      }
      
   
   jdbcMultiDataSourceRuntimeIndex OBJECT-TYPE
      SYNTAX      OCTET STRING
      MAX-ACCESS  not-accessible
      STATUS      current
      DESCRIPTION "Index column"
      ::= { jdbcMultiDataSourceRuntimeEntry 1  }
   
   
   jdbcMultiDataSourceRuntimeObjectName OBJECT-TYPE
      SYNTAX      OCTET STRING
      MAX-ACCESS  read-only
      STATUS      current
      DESCRIPTION "ObjectName column"
      ::= { jdbcMultiDataSourceRuntimeEntry 2  }
   
   
   jdbcMultiDataSourceRuntimeType OBJECT-TYPE
      SYNTAX      OCTET STRING
      MAX-ACCESS  read-only
      STATUS      current
      DESCRIPTION "Returns the type of the MBean. "
      ::= { jdbcMultiDataSourceRuntimeEntry 3  }
   
   
   jdbcMultiDataSourceRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { jdbcMultiDataSourceRuntimeEntry 4  }
   
   
   jdbcMultiDataSourceRuntimeName OBJECT-TYPE
      SYNTAX      OCTET STRING
      MAX-ACCESS  read-only
      STATUS      current
      DESCRIPTION "The name of this configuration. WebLogic Server uses an MBean to implement and persist the configuration. "
      ::= { jdbcMultiDataSourceRuntimeEntry 5  }
   
   
   jdbcMultiDataSourceRuntimeMaxCapacity OBJECT-TYPE
      SYNTAX      Integer32
      MAX-ACCESS  read-only
      STATUS      current
      DESCRIPTION "The maximum capacity of this multi data source.  The maximum capacity is:  - Maximum capacity of first available (not suspended) data source in the list, if the multi data source is using the FAILOVER algorithm (the FailoverRequestIfBusy flag is not set).  - Sum of maximum capacities of all available (not suspended) data sources, if the  multi data source is using other algorithms. "
      ::= { jdbcMultiDataSourceRuntimeEntry 6  }
   
   
   jdbcMultiDataSourceRuntimeDeploymentState OBJECT-TYPE
      SYNTAX      Integer32
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jdbcMultiDataSourceRuntimeEntry 7  }
   
   
   jaxRsApplicationRuntimeTable OBJECT-TYPE
      SYNTAX      SEQUENCE OF JaxRsApplicationRuntimeEntry
      MAX-ACCESS  not-accessible
      STATUS      current
      DESCRIPTION "This the runtime server MBean for a JAX-RS application. There can be more than one JAX-RS application per Web Application. The list of available JAX-RS applications can be got through the method public JaxRsApplicationMBean[] getJaxRsApplications() at weblogic.management.runtime.WebAppComponentRuntimeMBean The lookup method to find a specific JAX-RS application with given name is public JaxRsApplicationMBean lookupJaxRsApplication(String name) "
      ::= { wls 1885  }
      
   
   jaxRsApplicationRuntimeEntry OBJECT-TYPE
      SYNTAX      JaxRsApplicationRuntimeEntry
      MAX-ACCESS  not-accessible
      STATUS      current
      DESCRIPTION "Generated SNMP Table Entry."
      INDEX { jaxRsApplicationRuntimeIndex}
      ::= { jaxRsApplicationRuntimeTable 1 }
      
   JaxRsApplicationRuntimeEntry ::=
      SEQUENCE
      {
         jaxRsApplicationRuntimeIndex OCTET STRING,
         jaxRsApplicationRuntimeObjectName OCTET STRING,
         jaxRsApplicationRuntimeApplicationEnabled OCTET STRING,
         jaxRsApplicationRuntimeType OCTET STRING,
         jaxRsApplicationRuntimeExecutionTimeAverage Counter64,
         jaxRsApplicationRuntimeExecutionTimeHigh Counter64,
         jaxRsApplicationRuntimeInvocationCount Counter64,
         jaxRsApplicationRuntimeLastErrorMapper OCTET STRING,
         jaxRsApplicationRuntimeStartTime Counter64,
         jaxRsApplicationRuntimeWadlGenerationEnabled OCTET STRING,
         jaxRsApplicationRuntimeResourcePattern OCTET STRING,
         jaxRsApplicationRuntimeErrorCount Counter64,
         jaxRsApplicationRuntimeLastResponseCode Integer32,
         jaxRsApplicationRuntimeExecutionTimeLow Counter64,
         jaxRsApplicationRuntimeName OCTET STRING,
         jaxRsApplicationRuntimeLastErrorDetails OCTET STRING,
         jaxRsApplicationRuntimeLastInvocationTime Counter64,
         jaxRsApplicationRuntimeExecutionTimeTotal Counter64,
         jaxRsApplicationRuntimeWadlUrl OCTET STRING,
         jaxRsApplicationRuntimeLastHttpMethod OCTET STRING,
         jaxRsApplicationRuntimeLastErrorTime Counter64,
         jaxRsApplicationRuntimeRootPath OCTET STRING,
         jaxRsApplicationRuntimeApplicationName OCTET STRING,
         jaxRsApplicationRuntimeApplicationClass OCTET STRING
      }
      
   
   jaxRsApplicationRuntimeIndex OBJECT-TYPE
      SYNTAX      OCTET STRING
      MAX-ACCESS  not-accessible
      STATUS      current
      DESCRIPTION "Index column"
      ::= { jaxRsApplicationRuntimeEntry 1  }
   
   
   jaxRsApplicationRuntimeObjectName OBJECT-TYPE
      SYNTAX      OCTET STRING
      MAX-ACCESS  read-only
      STATUS      current
      DESCRIPTION "ObjectName column"
      ::= { jaxRsApplicationRuntimeEntry 2  }
   
   
   jaxRsApplicationRuntimeApplicationEnabled OBJECT-TYPE
      SYNTAX      OCTET STRING
      MAX-ACCESS  read-only
      STATUS      current
      DESCRIPTION "Indicates whether this JAX-RS application is currently enabled  "
      ::= { jaxRsApplicationRuntimeEntry 3  }
   
   
   jaxRsApplicationRuntimeType OBJECT-TYPE
      SYNTAX      OCTET STRING
      MAX-ACCESS  read-only
      STATUS      current
      DESCRIPTION "Returns the type of the MBean. "
      ::= { jaxRsApplicationRuntimeEntry 4  }
   
   
   jaxRsApplicationRuntimeExecutionTimeAverage OBJECT-TYPE
      SYNTAX      Counter64
      MAX-ACCESS  read-only
      STATUS      current
      DESCRIPTION "Provides the average execution time (in ms) per execution. Returns 0 if it was never invoked. "
      ::= { jaxRsApplicationRuntimeEntry 5  }
   
   
   jaxRsApplicationRuntimeExecutionTimeHigh OBJECT-TYPE
      SYNTAX      Counter64
      MAX-ACCESS  read-only
      STATUS      current
      DESCRIPTION "Provides the highest time taken (in ms) by an execution. Returns 0 if it was never invoked. "
      ::= { jaxRsApplicationRuntimeEntry 6  }
   
   
   jaxRsApplicationRuntimeInvocationCount OBJECT-TYPE
      SYNTAX      Counter64
      MAX-ACCESS  read-only
      STATUS      current
      DESCRIPTION "Provides the total invocation count. "
      ::= { jaxRsApplicationRuntimeEntry 7  }
   
   
   jaxRsApplicationRuntimeLastErrorMapper OBJECT-TYPE
      SYNTAX      OCTET STRING
      MAX-ACCESS  read-only
      STATUS      current
      DESCRIPTION "Provides the exception mapper class used against the last error (if any) occurred. It returns null if no error has been mapped yet. "
      ::= { jaxRsApplicationRuntimeEntry 8  }
   
   
   jaxRsApplicationRuntimeStartTime OBJECT-TYPE
      SYNTAX      Counter64
      MAX-ACCESS  read-only
      STATUS      current
      DESCRIPTION "Get the start time of the application (when application was initialized). "
      ::= { jaxRsApplicationRuntimeEntry 9  }
   
   
   jaxRsApplicationRuntimeWadlGenerationEnabled OBJECT-TYPE
      SYNTAX      OCTET STRING
      MAX-ACCESS  read-only
      STATUS      current
      DESCRIPTION "Indicates whether this JAX-RS application currently has WADL generation enabled. "
      ::= { jaxRsApplicationRuntimeEntry 10  }
   
   
   jaxRsApplicationRuntimeResourcePattern OBJECT-TYPE
      SYNTAX      OCTET STRING
      MAX-ACCESS  read-only
      STATUS      current
      DESCRIPTION "Gets the WSM resource pattern for this JAX-RS application. "
      ::= { jaxRsApplicationRuntimeEntry 11  }
   
   
   jaxRsApplicationRuntimeErrorCount OBJECT-TYPE
      SYNTAX      Counter64
      MAX-ACCESS  read-only
      STATUS      current
      DESCRIPTION "Provides the errors count, the number of un-handled exceptions from the JAX-RS application "
      ::= { jaxRsApplicationRuntimeEntry 12  }
   
   
   jaxRsApplicationRuntimeLastResponseCode OBJECT-TYPE
      SYNTAX      Integer32
      MAX-ACCESS  read-only
      STATUS      current
      DESCRIPTION "Provides the response code of the last response. Returns -1 if there is no response yet. "
      ::= { jaxRsApplicationRuntimeEntry 13  }
   
   
   jaxRsApplicationRuntimeExecutionTimeLow OBJECT-TYPE
      SYNTAX      Counter64
      MAX-ACCESS  read-only
      STATUS      current
      DESCRIPTION "Provides the lowest time taken (in ms) by an execution. Returns 0 if it was never invoked. "
      ::= { jaxRsApplicationRuntimeEntry 14  }
   
   
   jaxRsApplicationRuntimeName OBJECT-TYPE
      SYNTAX      OCTET STRING
      MAX-ACCESS  read-only
      STATUS      current
      DESCRIPTION "The name of this configuration. WebLogic Server uses an MBean to implement and persist the configuration. "
      ::= { jaxRsApplicationRuntimeEntry 15  }
   
   
   jaxRsApplicationRuntimeLastErrorDetails OBJECT-TYPE
      SYNTAX      OCTET STRING
      MAX-ACCESS  read-only
      STATUS      current
      DESCRIPTION "Provides details of the last error. It returns null if there is not exception yet "
      ::= { jaxRsApplicationRuntimeEntry 16  }
   
   
   jaxRsApplicationRuntimeLastInvocationTime OBJECT-TYPE
      SYNTAX      Counter64
      MAX-ACCESS  read-only
      STATUS      current
      DESCRIPTION "Provides the last invocation time. Returns 0 if it was never invoked. "
      ::= { jaxRsApplicationRuntimeEntry 17  }
   
   
   jaxRsApplicationRuntimeExecutionTimeTotal OBJECT-TYPE
      SYNTAX      Counter64
      MAX-ACCESS  read-only
      STATUS      current
      DESCRIPTION "Provides the total execution time (in ms) of all the requests. Returns 0 if it was never invoked. "
      ::= { jaxRsApplicationRuntimeEntry 18  }
   
   
   jaxRsApplicationRuntimeWadlUrl OBJECT-TYPE
      SYNTAX      OCTET STRING
      MAX-ACCESS  read-only
      STATUS      current
      DESCRIPTION "Retrieve the WADL URI for this JAX-RS Application. "
      ::= { jaxRsApplicationRuntimeEntry 19  }
   
   
   jaxRsApplicationRuntimeLastHttpMethod OBJECT-TYPE
      SYNTAX      OCTET STRING
      MAX-ACCESS  read-only
      STATUS      current
      DESCRIPTION "Provides the http method name of the last request "
      ::= { jaxRsApplicationRuntimeEntry 20  }
   
   
   jaxRsApplicationRuntimeLastErrorTime OBJECT-TYPE
      SYNTAX      Counter64
      MAX-ACCESS  read-only
      STATUS      current
      DESCRIPTION "Provides the date-time at which the last error(if any) occurred "
      ::= { jaxRsApplicationRuntimeEntry 21  }
   
   
   jaxRsApplicationRuntimeRootPath OBJECT-TYPE
      SYNTAX      OCTET STRING
      MAX-ACCESS  read-only
      STATUS      current
      DESCRIPTION "Retrieve the root path for this JAX-RS Application.  The path consists of (servlet) context path + application (servlet or filter) path. "
      ::= { jaxRsApplicationRuntimeEntry 22  }
   
   
   jaxRsApplicationRuntimeApplicationName OBJECT-TYPE
      SYNTAX      OCTET STRING
      MAX-ACCESS  read-only
      STATUS      current
      DESCRIPTION "Get the application name. "
      ::= { jaxRsApplicationRuntimeEntry 23  }
   
   
   jaxRsApplicationRuntimeApplicationClass OBJECT-TYPE
      SYNTAX      OCTET STRING
      MAX-ACCESS  read-only
      STATUS      current
      DESCRIPTION "Get the application class used for configuration of Jersey application. "
      ::= { jaxRsApplicationRuntimeEntry 24  }
   
   
   jaxRsResourceConfigTypeRuntimeTable OBJECT-TYPE
      SYNTAX      SEQUENCE OF JaxRsResourceConfigTypeRuntimeEntry
      MAX-ACCESS  not-accessible
      STATUS      current
      DESCRIPTION "The runtime MBean for the JAX-RS application resource config."
      ::= { wls 1890  }
      
   
   jaxRsResourceConfigTypeRuntimeEntry OBJECT-TYPE
      SYNTAX      JaxRsResourceConfigTypeRuntimeEntry
      MAX-ACCESS  not-accessible
      STATUS      current
      DESCRIPTION "Generated SNMP Table Entry."
      INDEX { jaxRsResourceConfigTypeRuntimeIndex}
      ::= { jaxRsResourceConfigTypeRuntimeTable 1 }
      
   JaxRsResourceConfigTypeRuntimeEntry ::=
      SEQUENCE
      {
         jaxRsResourceConfigTypeRuntimeIndex OCTET STRING,
         jaxRsResourceConfigTypeRuntimeObjectName OCTET STRING,
         jaxRsResourceConfigTypeRuntimeType OCTET STRING,
         jaxRsResourceConfigTypeRuntimeName OCTET STRING,
         jaxRsResourceConfigTypeRuntimeClassName OCTET STRING
      }
      
   
   jaxRsResourceConfigTypeRuntimeIndex OBJECT-TYPE
      SYNTAX      OCTET STRING
      MAX-ACCESS  not-accessible
      STATUS      current
      DESCRIPTION "Index column"
      ::= { jaxRsResourceConfigTypeRuntimeEntry 1  }
   
   
   jaxRsResourceConfigTypeRuntimeObjectName OBJECT-TYPE
      SYNTAX      OCTET STRING
      MAX-ACCESS  read-only
      STATUS      current
      DESCRIPTION "ObjectName column"
      ::= { jaxRsResourceConfigTypeRuntimeEntry 2  }
   
   
   jaxRsResourceConfigTypeRuntimeType OBJECT-TYPE
      SYNTAX      OCTET STRING
      MAX-ACCESS  read-only
      STATUS      current
      DESCRIPTION "Returns the type of the MBean."
      ::= { jaxRsResourceConfigTypeRuntimeEntry 3  }
   
   
   jaxRsResourceConfigTypeRuntimeName OBJECT-TYPE
      SYNTAX      OCTET STRING
      MAX-ACCESS  read-only
      STATUS      current
      DESCRIPTION "The name of this configuration. WebLogic Server uses an MBean to implement and persist the configuration."
      ::= { jaxRsResourceConfigTypeRuntimeEntry 4  }
   
   
   jaxRsResourceConfigTypeRuntimeClassName OBJECT-TYPE
      SYNTAX      OCTET STRING
      MAX-ACCESS  read-only
      STATUS      current
      DESCRIPTION "Provides the class name of the Jax-Rs application resource config"
      ::= { jaxRsResourceConfigTypeRuntimeEntry 5  }
   
   
   jaxRsResourceMethodRuntimeTable OBJECT-TYPE
      SYNTAX      SEQUENCE OF JaxRsResourceMethodRuntimeEntry
      MAX-ACCESS  not-accessible
      STATUS      current
      DESCRIPTION "The runtime MBean of a resource method. A resource method is Java method that is available on a JAX-RS resource class. The resource method is always annotated with exactly one http method designator. "
      ::= { wls 1895  }
      
   
   jaxRsResourceMethodRuntimeEntry OBJECT-TYPE
      SYNTAX      JaxRsResourceMethodRuntimeEntry
      MAX-ACCESS  not-accessible
      STATUS      current
      DESCRIPTION "Generated SNMP Table Entry."
      INDEX { jaxRsResourceMethodRuntimeIndex}
      ::= { jaxRsResourceMethodRuntimeTable 1 }
      
   JaxRsResourceMethodRuntimeEntry ::=
      SEQUENCE
      {
         jaxRsResourceMethodRuntimeIndex OCTET STRING,
         jaxRsResourceMethodRuntimeObjectName OCTET STRING,
         jaxRsResourceMethodRuntimeType OCTET STRING,
         jaxRsResourceMethodRuntimeReturnType OCTET STRING,
         jaxRsResourceMethodRuntimeParameterTypes OCTET STRING,
         jaxRsResourceMethodRuntimeExecutionTimeLow Counter64,
         jaxRsResourceMethodRuntimePath OCTET STRING,
         jaxRsResourceMethodRuntimeName OCTET STRING,
         jaxRsResourceMethodRuntimeLastInvocationTime Counter64,
         jaxRsResourceMethodRuntimeExecutionTimeTotal Counter64,
         jaxRsResourceMethodRuntimeMethodName OCTET STRING,
         jaxRsResourceMethodRuntimeProducingMediaTypes OCTET STRING,
         jaxRsResourceMethodRuntimeExecutionTimeAverage Counter64,
         jaxRsResourceMethodRuntimeStartTime Counter64,
         jaxRsResourceMethodRuntimeInvocationCount Counter64,
         jaxRsResourceMethodRuntimeExecutionTimeHigh Counter64,
         jaxRsResourceMethodRuntimeConsumingMediaTypes OCTET STRING,
         jaxRsResourceMethodRuntimeHttpMethod OCTET STRING,
         jaxRsResourceMethodRuntimeSubResourceMethod OCTET STRING,
         jaxRsResourceMethodRuntimeExtended OCTET STRING,
         jaxRsResourceMethodRuntimeClassName OCTET STRING,
         jaxRsResourceMethodRuntimeSubResource OCTET STRING
      }
      
   
   jaxRsResourceMethodRuntimeIndex OBJECT-TYPE
      SYNTAX      OCTET STRING
      MAX-ACCESS  not-accessible
      STATUS      current
      DESCRIPTION "Index column"
      ::= { jaxRsResourceMethodRuntimeEntry 1  }
   
   
   jaxRsResourceMethodRuntimeObjectName OBJECT-TYPE
      SYNTAX      OCTET STRING
      MAX-ACCESS  read-only
      STATUS      current
      DESCRIPTION "ObjectName column"
      ::= { jaxRsResourceMethodRuntimeEntry 2  }
   
   
   jaxRsResourceMethodRuntimeType OBJECT-TYPE
      SYNTAX      OCTET STRING
      MAX-ACCESS  read-only
      STATUS      current
      DESCRIPTION "Returns the type of the MBean. "
      ::= { jaxRsResourceMethodRuntimeEntry 3  }
   
   
   jaxRsResourceMethodRuntimeReturnType OBJECT-TYPE
      SYNTAX      OCTET STRING
      MAX-ACCESS  read-only
      STATUS      current
      DESCRIPTION "Provides the return type of the method. "
      ::= { jaxRsResourceMethodRuntimeEntry 4  }
   
   
   jaxRsResourceMethodRuntimeParameterTypes OBJECT-TYPE
      SYNTAX      OCTET STRING
      MAX-ACCESS  read-only
      STATUS      current
      DESCRIPTION "Provides the parameter types of the method. "
      ::= { jaxRsResourceMethodRuntimeEntry 5  }
   
   
   jaxRsResourceMethodRuntimeExecutionTimeLow OBJECT-TYPE
      SYNTAX      Counter64
      MAX-ACCESS  read-only
      STATUS      current
      DESCRIPTION "Provides the lowest time taken (in ms) by an execution. Returns 0 if it was never invoked. "
      ::= { jaxRsResourceMethodRuntimeEntry 6  }
   
   
   jaxRsResourceMethodRuntimePath OBJECT-TYPE
      SYNTAX      OCTET STRING
      MAX-ACCESS  read-only
      STATUS      current
      DESCRIPTION "Provides the path annotated in the method. "
      ::= { jaxRsResourceMethodRuntimeEntry 7  }
   
   
   jaxRsResourceMethodRuntimeName OBJECT-TYPE
      SYNTAX      OCTET STRING
      MAX-ACCESS  read-only
      STATUS      current
      DESCRIPTION "The name of this configuration. WebLogic Server uses an MBean to implement and persist the configuration. "
      ::= { jaxRsResourceMethodRuntimeEntry 8  }
   
   
   jaxRsResourceMethodRuntimeLastInvocationTime OBJECT-TYPE
      SYNTAX      Counter64
      MAX-ACCESS  read-only
      STATUS      current
      DESCRIPTION "Provides the last invocation time. Returns 0 if it was never invoked. "
      ::= { jaxRsResourceMethodRuntimeEntry 9  }
   
   
   jaxRsResourceMethodRuntimeExecutionTimeTotal OBJECT-TYPE
      SYNTAX      Counter64
      MAX-ACCESS  read-only
      STATUS      current
      DESCRIPTION "Provides the total execution time (in ms) of all the requests. Returns 0 if it was never invoked. "
      ::= { jaxRsResourceMethodRuntimeEntry 10  }
   
   
   jaxRsResourceMethodRuntimeMethodName OBJECT-TYPE
      SYNTAX      OCTET STRING
      MAX-ACCESS  read-only
      STATUS      current
      DESCRIPTION "Provides the method name "
      ::= { jaxRsResourceMethodRuntimeEntry 11  }
   
   
   jaxRsResourceMethodRuntimeProducingMediaTypes OBJECT-TYPE
      SYNTAX      OCTET STRING
      MAX-ACCESS  read-only
      STATUS      current
      DESCRIPTION "Provides the media-types that are produced by this resource method. "
      ::= { jaxRsResourceMethodRuntimeEntry 12  }
   
   
   jaxRsResourceMethodRuntimeExecutionTimeAverage OBJECT-TYPE
      SYNTAX      Counter64
      MAX-ACCESS  read-only
      STATUS      current
      DESCRIPTION "Provides the average execution time (in ms) per execution. Returns 0 if it was never invoked. "
      ::= { jaxRsResourceMethodRuntimeEntry 13  }
   
   
   jaxRsResourceMethodRuntimeStartTime OBJECT-TYPE
      SYNTAX      Counter64
      MAX-ACCESS  read-only
      STATUS      current
      DESCRIPTION "The start time of this MBean. "
      ::= { jaxRsResourceMethodRuntimeEntry 14  }
   
   
   jaxRsResourceMethodRuntimeInvocationCount OBJECT-TYPE
      SYNTAX      Counter64
      MAX-ACCESS  read-only
      STATUS      current
      DESCRIPTION "Provides the total invocation count. "
      ::= { jaxRsResourceMethodRuntimeEntry 15  }
   
   
   jaxRsResourceMethodRuntimeExecutionTimeHigh OBJECT-TYPE
      SYNTAX      Counter64
      MAX-ACCESS  read-only
      STATUS      current
      DESCRIPTION "Provides the highest time taken (in ms) by an execution. Returns 0 if it was never invoked. "
      ::= { jaxRsResourceMethodRuntimeEntry 16  }
   
   
   jaxRsResourceMethodRuntimeConsumingMediaTypes OBJECT-TYPE
      SYNTAX      OCTET STRING
      MAX-ACCESS  read-only
      STATUS      current
      DESCRIPTION "Provides the media-types that are consumed by this resource method. "
      ::= { jaxRsResourceMethodRuntimeEntry 17  }
   
   
   jaxRsResourceMethodRuntimeHttpMethod OBJECT-TYPE
      SYNTAX      OCTET STRING
      MAX-ACCESS  read-only
      STATUS      current
      DESCRIPTION "Provides the HTTP designator that is annotated on the resource method. "
      ::= { jaxRsResourceMethodRuntimeEntry 18  }
   
   
   jaxRsResourceMethodRuntimeSubResourceMethod OBJECT-TYPE
      SYNTAX      OCTET STRING
      MAX-ACCESS  read-only
      STATUS      current
      DESCRIPTION "Indicates whether this MBean represents a sub-resource method. "
      ::= { jaxRsResourceMethodRuntimeEntry 19  }
   
   
   jaxRsResourceMethodRuntimeExtended OBJECT-TYPE
      SYNTAX      OCTET STRING
      MAX-ACCESS  read-only
      STATUS      current
      DESCRIPTION "Get the flag indicating whether the resource method is extended or is a core of exposed RESTful API.  Extended resource model components are helper components that are not considered as a core of a RESTful API. These can be for example {@code OPTIONS} resource methods added by model processors or {@code application.wadl} resource producing the WADL. Both resource are rather supportive than the core of RESTful API.   If not set, the resource will not be defined as extended by default.  "
      ::= { jaxRsResourceMethodRuntimeEntry 20  }
   
   
   jaxRsResourceMethodRuntimeClassName OBJECT-TYPE
      SYNTAX      OCTET STRING
      MAX-ACCESS  read-only
      STATUS      current
      DESCRIPTION "Provides the resource class name. "
      ::= { jaxRsResourceMethodRuntimeEntry 21  }
   
   
   jaxRsResourceMethodRuntimeSubResource OBJECT-TYPE
      SYNTAX      OCTET STRING
      MAX-ACCESS  read-only
      STATUS      current
      DESCRIPTION "Indicates whether this MBean represents a sub-resource. "
      ::= { jaxRsResourceMethodRuntimeEntry 22  }
   
   
   jaxRsResourceRuntimeTable OBJECT-TYPE
      SYNTAX      SEQUENCE OF JaxRsResourceRuntimeEntry
      MAX-ACCESS  not-accessible
      STATUS      current
      DESCRIPTION "The runtime MBean of a JAX-RS resource. EJB(Stateless and Singleton), POJO are the two component types that are supported.  Each JAX-RS resource has a scope associated with that. Any object that is managed by a container (such as EJB) will have application scope. All other resources by default will have request scope. "
      ::= { wls 1900  }
      
   
   jaxRsResourceRuntimeEntry OBJECT-TYPE
      SYNTAX      JaxRsResourceRuntimeEntry
      MAX-ACCESS  not-accessible
      STATUS      current
      DESCRIPTION "Generated SNMP Table Entry."
      INDEX { jaxRsResourceRuntimeIndex}
      ::= { jaxRsResourceRuntimeTable 1 }
      
   JaxRsResourceRuntimeEntry ::=
      SEQUENCE
      {
         jaxRsResourceRuntimeIndex OCTET STRING,
         jaxRsResourceRuntimeObjectName OCTET STRING,
         jaxRsResourceRuntimeType OCTET STRING,
         jaxRsResourceRuntimeExecutionTimeLow Counter64,
         jaxRsResourceRuntimePath OCTET STRING,
         jaxRsResourceRuntimeName OCTET STRING,
         jaxRsResourceRuntimeLastInvocationTime Counter64,
         jaxRsResourceRuntimeResourceType OCTET STRING,
         jaxRsResourceRuntimeExecutionTimeTotal Counter64,
         jaxRsResourceRuntimeExecutionTimeAverage Counter64,
         jaxRsResourceRuntimeStartTime Counter64,
         jaxRsResourceRuntimeInvocationCount Counter64,
         jaxRsResourceRuntimeExecutionTimeHigh Counter64,
         jaxRsResourceRuntimeClassName OCTET STRING,
         jaxRsResourceRuntimeExtended OCTET STRING
      }
      
   
   jaxRsResourceRuntimeIndex OBJECT-TYPE
      SYNTAX      OCTET STRING
      MAX-ACCESS  not-accessible
      STATUS      current
      DESCRIPTION "Index column"
      ::= { jaxRsResourceRuntimeEntry 1  }
   
   
   jaxRsResourceRuntimeObjectName OBJECT-TYPE
      SYNTAX      OCTET STRING
      MAX-ACCESS  read-only
      STATUS      current
      DESCRIPTION "ObjectName column"
      ::= { jaxRsResourceRuntimeEntry 2  }
   
   
   jaxRsResourceRuntimeType OBJECT-TYPE
      SYNTAX      OCTET STRING
      MAX-ACCESS  read-only
      STATUS      current
      DESCRIPTION "Returns the type of the MBean. "
      ::= { jaxRsResourceRuntimeEntry 3  }
   
   
   jaxRsResourceRuntimeExecutionTimeLow OBJECT-TYPE
      SYNTAX      Counter64
      MAX-ACCESS  read-only
      STATUS      current
      DESCRIPTION "Provides the lowest time taken (in ms) by an execution. Returns 0 if it was never invoked. "
      ::= { jaxRsResourceRuntimeEntry 4  }
   
   
   jaxRsResourceRuntimePath OBJECT-TYPE
      SYNTAX      OCTET STRING
      MAX-ACCESS  read-only
      STATUS      current
      DESCRIPTION "The relative path that is assigned to this resource. "
      ::= { jaxRsResourceRuntimeEntry 5  }
   
   
   jaxRsResourceRuntimeName OBJECT-TYPE
      SYNTAX      OCTET STRING
      MAX-ACCESS  read-only
      STATUS      current
      DESCRIPTION "The name of this configuration. WebLogic Server uses an MBean to implement and persist the configuration. "
      ::= { jaxRsResourceRuntimeEntry 6  }
   
   
   jaxRsResourceRuntimeLastInvocationTime OBJECT-TYPE
      SYNTAX      Counter64
      MAX-ACCESS  read-only
      STATUS      current
      DESCRIPTION "Provides the last invocation time. Returns 0 if it was never invoked. "
      ::= { jaxRsResourceRuntimeEntry 7  }
   
   
   jaxRsResourceRuntimeResourceType OBJECT-TYPE
      SYNTAX      OCTET STRING
      MAX-ACCESS  read-only
      STATUS      current
      DESCRIPTION "Provides the type (e.g., POJO, EJB, CDI, etc.) of the resource. "
      ::= { jaxRsResourceRuntimeEntry 8  }
   
   
   jaxRsResourceRuntimeExecutionTimeTotal OBJECT-TYPE
      SYNTAX      Counter64
      MAX-ACCESS  read-only
      STATUS      current
      DESCRIPTION "Provides the total execution time (in ms) of all the requests. Returns 0 if it was never invoked. "
      ::= { jaxRsResourceRuntimeEntry 9  }
   
   
   jaxRsResourceRuntimeExecutionTimeAverage OBJECT-TYPE
      SYNTAX      Counter64
      MAX-ACCESS  read-only
      STATUS      current
      DESCRIPTION "Provides the average execution time (in ms) per execution. Returns 0 if it was never invoked. "
      ::= { jaxRsResourceRuntimeEntry 10  }
   
   
   jaxRsResourceRuntimeStartTime OBJECT-TYPE
      SYNTAX      Counter64
      MAX-ACCESS  read-only
      STATUS      current
      DESCRIPTION "The start time of this MBean. "
      ::= { jaxRsResourceRuntimeEntry 11  }
   
   
   jaxRsResourceRuntimeInvocationCount OBJECT-TYPE
      SYNTAX      Counter64
      MAX-ACCESS  read-only
      STATUS      current
      DESCRIPTION "Provides the total invocation count. "
      ::= { jaxRsResourceRuntimeEntry 12  }
   
   
   jaxRsResourceRuntimeExecutionTimeHigh OBJECT-TYPE
      SYNTAX      Counter64
      MAX-ACCESS  read-only
      STATUS      current
      DESCRIPTION "Provides the highest time taken (in ms) by an execution. Returns 0 if it was never invoked. "
      ::= { jaxRsResourceRuntimeEntry 13  }
   
   
   jaxRsResourceRuntimeClassName OBJECT-TYPE
      SYNTAX      OCTET STRING
      MAX-ACCESS  read-only
      STATUS      current
      DESCRIPTION "Get the class name of the resource. "
      ::= { jaxRsResourceRuntimeEntry 14  }
   
   
   jaxRsResourceRuntimeExtended OBJECT-TYPE
      SYNTAX      OCTET STRING
      MAX-ACCESS  read-only
      STATUS      current
      DESCRIPTION "Get the flag indicating whether the resource is extended or is a core of exposed RESTful API.  Extended resource model components are helper components that are not considered as a core of a RESTful API. These can be for example {@code OPTIONS} resource methods added by model processors or {@code application.wadl} resource producing the WADL. Both resource are rather supportive than the core of RESTful API.  "
      ::= { jaxRsResourceRuntimeEntry 15  }
   
   
   jaxRsSubResourceLocatorRuntimeTable OBJECT-TYPE
      SYNTAX      SEQUENCE OF JaxRsSubResourceLocatorRuntimeEntry
      MAX-ACCESS  not-accessible
      STATUS      current
      DESCRIPTION "The runtime MBean for a JAX-RS sub-resource locator. A sub-resource locator is a resource method that is with out a HTTP designator "
      ::= { wls 1905  }
      
   
   jaxRsSubResourceLocatorRuntimeEntry OBJECT-TYPE
      SYNTAX      JaxRsSubResourceLocatorRuntimeEntry
      MAX-ACCESS  not-accessible
      STATUS      current
      DESCRIPTION "Generated SNMP Table Entry."
      INDEX { jaxRsSubResourceLocatorRuntimeIndex}
      ::= { jaxRsSubResourceLocatorRuntimeTable 1 }
      
   JaxRsSubResourceLocatorRuntimeEntry ::=
      SEQUENCE
      {
         jaxRsSubResourceLocatorRuntimeIndex OCTET STRING,
         jaxRsSubResourceLocatorRuntimeObjectName OCTET STRING,
         jaxRsSubResourceLocatorRuntimeType OCTET STRING,
         jaxRsSubResourceLocatorRuntimeReturnType OCTET STRING,
         jaxRsSubResourceLocatorRuntimeParameterTypes OCTET STRING,
         jaxRsSubResourceLocatorRuntimeExecutionTimeLow Counter64,
         jaxRsSubResourceLocatorRuntimePath OCTET STRING,
         jaxRsSubResourceLocatorRuntimeName OCTET STRING,
         jaxRsSubResourceLocatorRuntimeLastInvocationTime Counter64,
         jaxRsSubResourceLocatorRuntimeExecutionTimeTotal Counter64,
         jaxRsSubResourceLocatorRuntimeMethodName OCTET STRING,
         jaxRsSubResourceLocatorRuntimeExecutionTimeAverage Counter64,
         jaxRsSubResourceLocatorRuntimeStartTime Counter64,
         jaxRsSubResourceLocatorRuntimeInvocationCount Counter64,
         jaxRsSubResourceLocatorRuntimeExecutionTimeHigh Counter64,
         jaxRsSubResourceLocatorRuntimeExtended OCTET STRING,
         jaxRsSubResourceLocatorRuntimeClassName OCTET STRING
      }
      
   
   jaxRsSubResourceLocatorRuntimeIndex OBJECT-TYPE
      SYNTAX      OCTET STRING
      MAX-ACCESS  not-accessible
      STATUS      current
      DESCRIPTION "Index column"
      ::= { jaxRsSubResourceLocatorRuntimeEntry 1  }
   
   
   jaxRsSubResourceLocatorRuntimeObjectName OBJECT-TYPE
      SYNTAX      OCTET STRING
      MAX-ACCESS  read-only
      STATUS      current
      DESCRIPTION "ObjectName column"
      ::= { jaxRsSubResourceLocatorRuntimeEntry 2  }
   
   
   jaxRsSubResourceLocatorRuntimeType OBJECT-TYPE
      SYNTAX      OCTET STRING
      MAX-ACCESS  read-only
      STATUS      current
      DESCRIPTION "Returns the type of the MBean. "
      ::= { jaxRsSubResourceLocatorRuntimeEntry 3  }
   
   
   jaxRsSubResourceLocatorRuntimeReturnType OBJECT-TYPE
      SYNTAX      OCTET STRING
      MAX-ACCESS  read-only
      STATUS      current
      DESCRIPTION "Provides the return type of the method. "
      ::= { jaxRsSubResourceLocatorRuntimeEntry 4  }
   
   
   jaxRsSubResourceLocatorRuntimeParameterTypes OBJECT-TYPE
      SYNTAX      OCTET STRING
      MAX-ACCESS  read-only
      STATUS      current
      DESCRIPTION "Provides the parameter types of the method. "
      ::= { jaxRsSubResourceLocatorRuntimeEntry 5  }
   
   
   jaxRsSubResourceLocatorRuntimeExecutionTimeLow OBJECT-TYPE
      SYNTAX      Counter64
      MAX-ACCESS  read-only
      STATUS      current
      DESCRIPTION "Provides the lowest time taken (in ms) by an execution. Returns 0 if it was never invoked. "
      ::= { jaxRsSubResourceLocatorRuntimeEntry 6  }
   
   
   jaxRsSubResourceLocatorRuntimePath OBJECT-TYPE
      SYNTAX      OCTET STRING
      MAX-ACCESS  read-only
      STATUS      current
      DESCRIPTION "Provides the path annotated in the method. "
      ::= { jaxRsSubResourceLocatorRuntimeEntry 7  }
   
   
   jaxRsSubResourceLocatorRuntimeName OBJECT-TYPE
      SYNTAX      OCTET STRING
      MAX-ACCESS  read-only
      STATUS      current
      DESCRIPTION "The name of this configuration. WebLogic Server uses an MBean to implement and persist the configuration. "
      ::= { jaxRsSubResourceLocatorRuntimeEntry 8  }
   
   
   jaxRsSubResourceLocatorRuntimeLastInvocationTime OBJECT-TYPE
      SYNTAX      Counter64
      MAX-ACCESS  read-only
      STATUS      current
      DESCRIPTION "Provides the last invocation time. Returns 0 if it was never invoked. "
      ::= { jaxRsSubResourceLocatorRuntimeEntry 9  }
   
   
   jaxRsSubResourceLocatorRuntimeExecutionTimeTotal OBJECT-TYPE
      SYNTAX      Counter64
      MAX-ACCESS  read-only
      STATUS      current
      DESCRIPTION "Provides the total execution time (in ms) of all the requests. Returns 0 if it was never invoked. "
      ::= { jaxRsSubResourceLocatorRuntimeEntry 10  }
   
   
   jaxRsSubResourceLocatorRuntimeMethodName OBJECT-TYPE
      SYNTAX      OCTET STRING
      MAX-ACCESS  read-only
      STATUS      current
      DESCRIPTION "Provides the method name "
      ::= { jaxRsSubResourceLocatorRuntimeEntry 11  }
   
   
   jaxRsSubResourceLocatorRuntimeExecutionTimeAverage OBJECT-TYPE
      SYNTAX      Counter64
      MAX-ACCESS  read-only
      STATUS      current
      DESCRIPTION "Provides the average execution time (in ms) per execution. Returns 0 if it was never invoked. "
      ::= { jaxRsSubResourceLocatorRuntimeEntry 12  }
   
   
   jaxRsSubResourceLocatorRuntimeStartTime OBJECT-TYPE
      SYNTAX      Counter64
      MAX-ACCESS  read-only
      STATUS      current
      DESCRIPTION "The start time of this MBean. "
      ::= { jaxRsSubResourceLocatorRuntimeEntry 13  }
   
   
   jaxRsSubResourceLocatorRuntimeInvocationCount OBJECT-TYPE
      SYNTAX      Counter64
      MAX-ACCESS  read-only
      STATUS      current
      DESCRIPTION "Provides the total invocation count. "
      ::= { jaxRsSubResourceLocatorRuntimeEntry 14  }
   
   
   jaxRsSubResourceLocatorRuntimeExecutionTimeHigh OBJECT-TYPE
      SYNTAX      Counter64
      MAX-ACCESS  read-only
      STATUS      current
      DESCRIPTION "Provides the highest time taken (in ms) by an execution. Returns 0 if it was never invoked. "
      ::= { jaxRsSubResourceLocatorRuntimeEntry 15  }
   
   
   jaxRsSubResourceLocatorRuntimeExtended OBJECT-TYPE
      SYNTAX      OCTET STRING
      MAX-ACCESS  read-only
      STATUS      current
      DESCRIPTION "Get the flag indicating whether the resource method is extended or is a core of exposed RESTful API.  Extended resource model components are helper components that are not considered as a core of a RESTful API. These can be for example {@code OPTIONS} resource methods added by model processors or {@code application.wadl} resource producing the WADL. Both resource are rather supportive than the core of RESTful API.   If not set, the resource will not be defined as extended by default.  "
      ::= { jaxRsSubResourceLocatorRuntimeEntry 16  }
   
   
   jaxRsSubResourceLocatorRuntimeClassName OBJECT-TYPE
      SYNTAX      OCTET STRING
      MAX-ACCESS  read-only
      STATUS      current
      DESCRIPTION "Provides the resource class name. "
      ::= { jaxRsSubResourceLocatorRuntimeEntry 17  }
   
   
   libDeploymentRuntimeTable OBJECT-TYPE
      SYNTAX      SEQUENCE OF LibDeploymentRuntimeEntry
      MAX-ACCESS  not-accessible
      STATUS      current
      DESCRIPTION "This MBean provides deployment operations for a library.. "
      ::= { wls 1910  }
      
   
   libDeploymentRuntimeEntry OBJECT-TYPE
      SYNTAX      LibDeploymentRuntimeEntry
      MAX-ACCESS  not-accessible
      STATUS      current
      DESCRIPTION "Generated SNMP Table Entry."
      INDEX { libDeploymentRuntimeIndex}
      ::= { libDeploymentRuntimeTable 1 }
      
   LibDeploymentRuntimeEntry ::=
      SEQUENCE
      {
         libDeploymentRuntimeIndex OCTET STRING,
         libDeploymentRuntimeObjectName OCTET STRING,
         libDeploymentRuntimeType OCTET STRING,
         libDeploymentRuntimeLibraryName OCTET STRING,
         libDeploymentRuntimeLibraryIdentifier OCTET STRING,
         libDeploymentRuntimeName OCTET STRING,
         libDeploymentRuntimeImplementationVersion OCTET STRING,
         libDeploymentRuntimeSpecificationVersion OCTET STRING,
         libDeploymentRuntimePartitionName OCTET STRING
      }
      
   
   libDeploymentRuntimeIndex OBJECT-TYPE
      SYNTAX      OCTET STRING
      MAX-ACCESS  not-accessible
      STATUS      current
      DESCRIPTION "Index column"
      ::= { libDeploymentRuntimeEntry 1  }
   
   
   libDeploymentRuntimeObjectName OBJECT-TYPE
      SYNTAX      OCTET STRING
      MAX-ACCESS  read-only
      STATUS      current
      DESCRIPTION "ObjectName column"
      ::= { libDeploymentRuntimeEntry 2  }
   
   
   libDeploymentRuntimeType OBJECT-TYPE
      SYNTAX      OCTET STRING
      MAX-ACCESS  read-only
      STATUS      current
      DESCRIPTION "Returns the type of the MBean. "
      ::= { libDeploymentRuntimeEntry 3  }
   
   
   libDeploymentRuntimeLibraryName OBJECT-TYPE
      SYNTAX      OCTET STRING
      MAX-ACCESS  read-only
      STATUS      current
      DESCRIPTION "The library's name. "
      ::= { libDeploymentRuntimeEntry 4  }
   
   
   libDeploymentRuntimeLibraryIdentifier OBJECT-TYPE
      SYNTAX      OCTET STRING
      MAX-ACCESS  read-only
      STATUS      current
      DESCRIPTION "The library's identifier. "
      ::= { libDeploymentRuntimeEntry 5  }
   
   
   libDeploymentRuntimeName OBJECT-TYPE
      SYNTAX      OCTET STRING
      MAX-ACCESS  read-only
      STATUS      current
      DESCRIPTION "The name of this configuration. WebLogic Server uses an MBean to implement and persist the configuration. "
      ::= { libDeploymentRuntimeEntry 6  }
   
   
   libDeploymentRuntimeImplementationVersion OBJECT-TYPE
      SYNTAX      OCTET STRING
      MAX-ACCESS  read-only
      STATUS      current
      DESCRIPTION "The library's implementation version, null if none is set "
      ::= { libDeploymentRuntimeEntry 7  }
   
   
   libDeploymentRuntimeSpecificationVersion OBJECT-TYPE
      SYNTAX      OCTET STRING
      MAX-ACCESS  read-only
      STATUS      current
      DESCRIPTION "The library's specification version, null if none is set "
      ::= { libDeploymentRuntimeEntry 8  }
   
   
   libDeploymentRuntimePartitionName OBJECT-TYPE
      SYNTAX      OCTET STRING
      MAX-ACCESS  read-only
      STATUS      current
      DESCRIPTION "The name of the partition the library is in. "
      ::= { libDeploymentRuntimeEntry 9  }
   
   
   singletonEJBRuntimeTable OBJECT-TYPE
      SYNTAX      SEQUENCE OF SingletonEJBRuntimeEntry
      MAX-ACCESS  not-accessible
      STATUS      current
      DESCRIPTION "This interface contains accessor methods for all EJB run-time information collected for a Singleton session bean. "
      ::= { wls 1915  }
      
   
   singletonEJBRuntimeEntry OBJECT-TYPE
      SYNTAX      SingletonEJBRuntimeEntry
      MAX-ACCESS  not-accessible
      STATUS      current
      DESCRIPTION "Generated SNMP Table Entry."
      INDEX { singletonEJBRuntimeIndex}
      ::= { singletonEJBRuntimeTable 1 }
      
   SingletonEJBRuntimeEntry ::=
      SEQUENCE
      {
         singletonEJBRuntimeIndex OCTET STRING,
         singletonEJBRuntimeObjectName OCTET STRING,
         singletonEJBRuntimeType OCTET STRING,
         singletonEJBRuntimeReadLockTotalCount Counter64,
         singletonEJBRuntimeWaiterCurrentCount Integer32,
         singletonEJBRuntimeName OCTET STRING,
         singletonEJBRuntimeWriteLockTotalCount Counter64,
         singletonEJBRuntimeEJBName OCTET STRING,
         singletonEJBRuntimeReadLockTimeoutTotalCount Integer32,
         singletonEJBRuntimeWriteLockTimeoutTotalCount Integer32
      }
      
   
   singletonEJBRuntimeIndex OBJECT-TYPE
      SYNTAX      OCTET STRING
      MAX-ACCESS  not-accessible
      STATUS      current
      DESCRIPTION "Index column"
      ::= { singletonEJBRuntimeEntry 1  }
   
   
   singletonEJBRuntimeObjectName OBJECT-TYPE
      SYNTAX      OCTET STRING
      MAX-ACCESS  read-only
      STATUS      current
      DESCRIPTION "ObjectName column"
      ::= { singletonEJBRuntimeEntry 2  }
   
   
   singletonEJBRuntimeType OBJECT-TYPE
      SYNTAX      OCTET STRING
      MAX-ACCESS  read-only
      STATUS      current
      DESCRIPTION "Returns the type of the MBean. "
      ::= { singletonEJBRuntimeEntry 3  }
   
   
   singletonEJBRuntimeReadLockTotalCount OBJECT-TYPE
      SYNTAX      Counter64
      MAX-ACCESS  read-only
      STATUS      current
      DESCRIPTION "Provides the total count of read locks requested since deployment; -1 will be returned if bean-managed concurrency is in use. "
      ::= { singletonEJBRuntimeEntry 4  }
   
   
   singletonEJBRuntimeWaiterCurrentCount OBJECT-TYPE
      SYNTAX      Integer32
      MAX-ACCESS  read-only
      STATUS      current
      DESCRIPTION "Provides the total count of threads waiting for the lock; -1 will be returned if bean-managed concurrency is in use. "
      ::= { singletonEJBRuntimeEntry 5  }
   
   
   singletonEJBRuntimeName OBJECT-TYPE
      SYNTAX      OCTET STRING
      MAX-ACCESS  read-only
      STATUS      current
      DESCRIPTION "The name of this configuration. WebLogic Server uses an MBean to implement and persist the configuration. "
      ::= { singletonEJBRuntimeEntry 6  }
   
   
   singletonEJBRuntimeWriteLockTotalCount OBJECT-TYPE
      SYNTAX      Counter64
      MAX-ACCESS  read-only
      STATUS      current
      DESCRIPTION "Provides the total count of write locks requested since deployment; -1 will be returned if bean-managed concurrency is in use. "
      ::= { singletonEJBRuntimeEntry 7  }
   
   
   singletonEJBRuntimeEJBName OBJECT-TYPE
      SYNTAX      OCTET STRING
      MAX-ACCESS  read-only
      STATUS      current
      DESCRIPTION "Provides the name for this EJB as defined in the javax.ejb.EJB annotation, or the ejb-name when * using the ejb-jar.xml deployment descriptor. "
      ::= { singletonEJBRuntimeEntry 8  }
   
   
   singletonEJBRuntimeReadLockTimeoutTotalCount OBJECT-TYPE
      SYNTAX      Integer32
      MAX-ACCESS  read-only
      STATUS      current
      DESCRIPTION "Provides the count of read lock requests that have timed out since deployment; -1 will be returned if bean-managed concurrency is in use. "
      ::= { singletonEJBRuntimeEntry 9  }
   
   
   singletonEJBRuntimeWriteLockTimeoutTotalCount OBJECT-TYPE
      SYNTAX      Integer32
      MAX-ACCESS  read-only
      STATUS      current
      DESCRIPTION "Provides the count of write lock requests that have timed out since deployment; -1 will be returned if bean-managed concurrency is in use. "
      ::= { singletonEJBRuntimeEntry 10  }
   
   
   systemComponentLifeCycleRuntimeTable OBJECT-TYPE
      SYNTAX      SEQUENCE OF SystemComponentLifeCycleRuntimeEntry
      MAX-ACCESS  not-accessible
      STATUS      current
      DESCRIPTION "Provides methods that transition system component from one state to another. This class is instantiated only on the Administration Server, but you can use it to transition the states of all managed system component servers.  To start system components, you must first configure a Node Manager on each component's host machine. "
      ::= { wls 1920  }
      
   
   systemComponentLifeCycleRuntimeEntry OBJECT-TYPE
      SYNTAX      SystemComponentLifeCycleRuntimeEntry
      MAX-ACCESS  not-accessible
      STATUS      current
      DESCRIPTION "Generated SNMP Table Entry."
      INDEX { systemComponentLifeCycleRuntimeIndex}
      ::= { systemComponentLifeCycleRuntimeTable 1 }
      
   SystemComponentLifeCycleRuntimeEntry ::=
      SEQUENCE
      {
         systemComponentLifeCycleRuntimeIndex OCTET STRING,
         systemComponentLifeCycleRuntimeObjectName OCTET STRING,
         systemComponentLifeCycleRuntimeType OCTET STRING,
         systemComponentLifeCycleRuntimeNodeManagerRestartCount Integer32,
         systemComponentLifeCycleRuntimeName OCTET STRING,
         systemComponentLifeCycleRuntimeState OCTET STRING
      }
      
   
   systemComponentLifeCycleRuntimeIndex OBJECT-TYPE
      SYNTAX      OCTET STRING
      MAX-ACCESS  not-accessible
      STATUS      current
      DESCRIPTION "Index column"
      ::= { systemComponentLifeCycleRuntimeEntry 1  }
   
   
   systemComponentLifeCycleRuntimeObjectName OBJECT-TYPE
      SYNTAX      OCTET STRING
      MAX-ACCESS  read-only
      STATUS      current
      DESCRIPTION "ObjectName column"
      ::= { systemComponentLifeCycleRuntimeEntry 2  }
   
   
   systemComponentLifeCycleRuntimeType OBJECT-TYPE
      SYNTAX      OCTET STRING
      MAX-ACCESS  read-only
      STATUS      current
      DESCRIPTION "Returns the type of the MBean. "
      ::= { systemComponentLifeCycleRuntimeEntry 3  }
   
   
   systemComponentLifeCycleRuntimeNodeManagerRestartCount OBJECT-TYPE
      SYNTAX      Integer32
      MAX-ACCESS  read-only
      STATUS      current
      DESCRIPTION "The number of times the server has been restarted using the Node Manager since its creation. The first start does not count. The count is valid only if the Node Manager is used to start and restart the server every time. "
      ::= { systemComponentLifeCycleRuntimeEntry 4  }
   
   
   systemComponentLifeCycleRuntimeName OBJECT-TYPE
      SYNTAX      OCTET STRING
      MAX-ACCESS  read-only
      STATUS      current
      DESCRIPTION "The name of this configuration. WebLogic Server uses an MBean to implement and persist the configuration. "
      ::= { systemComponentLifeCycleRuntimeEntry 5  }
   
   
   systemComponentLifeCycleRuntimeState OBJECT-TYPE
      SYNTAX      OCTET STRING
      MAX-ACCESS  read-only
      STATUS      current
      DESCRIPTION "The current state of the server. Server states are described in 'Managing Server Startup and Shutdown for Oracle WebLogic Server.' "
      ::= { systemComponentLifeCycleRuntimeEntry 6  }
   
   
   systemComponentLifeCycleTaskRuntimeTable OBJECT-TYPE
      SYNTAX      SEQUENCE OF SystemComponentLifeCycleTaskRuntimeEntry
      MAX-ACCESS  not-accessible
      STATUS      current
      DESCRIPTION "Exposes monitoring information about a system component's life cycle.  An operation (task) to change a system component's state will fork a separate thread to perform the actual work and immediately return an instance of this MBean to the caller. The caller can then use this MBean to track the task's progress as desired. "
      ::= { wls 1925  }
      
   
   systemComponentLifeCycleTaskRuntimeEntry OBJECT-TYPE
      SYNTAX      SystemComponentLifeCycleTaskRuntimeEntry
      MAX-ACCESS  not-accessible
      STATUS      current
      DESCRIPTION "Generated SNMP Table Entry."
      INDEX { systemComponentLifeCycleTaskRuntimeIndex}
      ::= { systemComponentLifeCycleTaskRuntimeTable 1 }
      
   SystemComponentLifeCycleTaskRuntimeEntry ::=
      SEQUENCE
      {
         systemComponentLifeCycleTaskRuntimeIndex OCTET STRING,
         systemComponentLifeCycleTaskRuntimeObjectName OCTET STRING,
         systemComponentLifeCycleTaskRuntimeOperation OCTET STRING,
         systemComponentLifeCycleTaskRuntimeDescription OCTET STRING,
         systemComponentLifeCycleTaskRuntimeType OCTET STRING,
         systemComponentLifeCycleTaskRuntimeRunning OCTET STRING,
         systemComponentLifeCycleTaskRuntimeSystemTask OCTET STRING,
         systemComponentLifeCycleTaskRuntimeServerName OCTET STRING,
         systemComponentLifeCycleTaskRuntimeName OCTET STRING,
         systemComponentLifeCycleTaskRuntimeStatus OCTET STRING,
         systemComponentLifeCycleTaskRuntimeBeginTime Counter64,
         systemComponentLifeCycleTaskRuntimeEndTime Counter64,
         systemComponentLifeCycleTaskRuntimeProgress OCTET STRING
      }
      
   
   systemComponentLifeCycleTaskRuntimeIndex OBJECT-TYPE
      SYNTAX      OCTET STRING
      MAX-ACCESS  not-accessible
      STATUS      current
      DESCRIPTION "Index column"
      ::= { systemComponentLifeCycleTaskRuntimeEntry 1  }
   
   
   systemComponentLifeCycleTaskRuntimeObjectName OBJECT-TYPE
      SYNTAX      OCTET STRING
      MAX-ACCESS  read-only
      STATUS      current
      DESCRIPTION "ObjectName column"
      ::= { systemComponentLifeCycleTaskRuntimeEntry 2  }
   
   
   systemComponentLifeCycleTaskRuntimeOperation OBJECT-TYPE
      SYNTAX      OCTET STRING
      MAX-ACCESS  read-only
      STATUS      current
      DESCRIPTION "Gets the name of the method that was invoked on the ServerLifeCycleRuntime to initiate this task. "
      ::= { systemComponentLifeCycleTaskRuntimeEntry 3  }
   
   
   systemComponentLifeCycleTaskRuntimeDescription OBJECT-TYPE
      SYNTAX      OCTET STRING
      MAX-ACCESS  read-only
      STATUS      current
      DESCRIPTION "A description of this task. "
      ::= { systemComponentLifeCycleTaskRuntimeEntry 4  }
   
   
   systemComponentLifeCycleTaskRuntimeType OBJECT-TYPE
      SYNTAX      OCTET STRING
      MAX-ACCESS  read-only
      STATUS      current
      DESCRIPTION "Returns the type of the MBean. "
      ::= { systemComponentLifeCycleTaskRuntimeEntry 5  }
   
   
   systemComponentLifeCycleTaskRuntimeRunning OBJECT-TYPE
      SYNTAX      OCTET STRING
      MAX-ACCESS  read-only
      STATUS      current
      DESCRIPTION "Indicates whether the task is still running. "
      ::= { systemComponentLifeCycleTaskRuntimeEntry 6  }
   
   
   systemComponentLifeCycleTaskRuntimeSystemTask OBJECT-TYPE
      SYNTAX      OCTET STRING
      MAX-ACCESS  read-only
      STATUS      current
      DESCRIPTION "Indicates whether this task was initiated by the server versus a user. "
      ::= { systemComponentLifeCycleTaskRuntimeEntry 7  }
   
   
   systemComponentLifeCycleTaskRuntimeServerName OBJECT-TYPE
      SYNTAX      OCTET STRING
      MAX-ACCESS  read-only
      STATUS      current
      DESCRIPTION "The name of the server. "
      ::= { systemComponentLifeCycleTaskRuntimeEntry 8  }
   
   
   systemComponentLifeCycleTaskRuntimeName OBJECT-TYPE
      SYNTAX      OCTET STRING
      MAX-ACCESS  read-only
      STATUS      current
      DESCRIPTION "The name of this configuration. WebLogic Server uses an MBean to implement and persist the configuration. "
      ::= { systemComponentLifeCycleTaskRuntimeEntry 9  }
   
   
   systemComponentLifeCycleTaskRuntimeStatus OBJECT-TYPE
      SYNTAX      OCTET STRING
      MAX-ACCESS  read-only
      STATUS      current
      DESCRIPTION "The status of this task. "
      ::= { systemComponentLifeCycleTaskRuntimeEntry 10  }
   
   
   systemComponentLifeCycleTaskRuntimeBeginTime OBJECT-TYPE
      SYNTAX      Counter64
      MAX-ACCESS  read-only
      STATUS      current
      DESCRIPTION "The time at which this task was started. "
      ::= { systemComponentLifeCycleTaskRuntimeEntry 11  }
   
   
   systemComponentLifeCycleTaskRuntimeEndTime OBJECT-TYPE
      SYNTAX      Counter64
      MAX-ACCESS  read-only
      STATUS      current
      DESCRIPTION "The time at which this task was completed.  A value of -1 indicates that the task is currently running. "
      ::= { systemComponentLifeCycleTaskRuntimeEntry 12  }
   
   
   systemComponentLifeCycleTaskRuntimeProgress OBJECT-TYPE
      SYNTAX      OCTET STRING
      MAX-ACCESS  read-only
      STATUS      current
      DESCRIPTION "The progress of this task. "
      ::= { systemComponentLifeCycleTaskRuntimeEntry 13  }
   
   
   wldfControlRuntimeTable OBJECT-TYPE
      SYNTAX      SEQUENCE OF WldfControlRuntimeEntry
      MAX-ACCESS  not-accessible
      STATUS      current
      DESCRIPTION "This MBean acts as a factory for WLDFSystemResourceControlRuntimeMBeans "
      ::= { wls 1930  }
      
   
   wldfControlRuntimeEntry OBJECT-TYPE
      SYNTAX      WldfControlRuntimeEntry
      MAX-ACCESS  not-accessible
      STATUS      current
      DESCRIPTION "Generated SNMP Table Entry."
      INDEX { wldfControlRuntimeIndex}
      ::= { wldfControlRuntimeTable 1 }
      
   WldfControlRuntimeEntry ::=
      SEQUENCE
      {
         wldfControlRuntimeIndex OCTET STRING,
         wldfControlRuntimeObjectName OCTET STRING,
         wldfControlRuntimeType OCTET STRING,
         wldfControlRuntimeName OCTET STRING
      }
      
   
   wldfControlRuntimeIndex OBJECT-TYPE
      SYNTAX      OCTET STRING
      MAX-ACCESS  not-accessible
      STATUS      current
      DESCRIPTION "Index column"
      ::= { wldfControlRuntimeEntry 1  }
   
   
   wldfControlRuntimeObjectName OBJECT-TYPE
      SYNTAX      OCTET STRING
      MAX-ACCESS  read-only
      STATUS      current
      DESCRIPTION "ObjectName column"
      ::= { wldfControlRuntimeEntry 2  }
   
   
   wldfControlRuntimeType OBJECT-TYPE
      SYNTAX      OCTET STRING
      MAX-ACCESS  read-only
      STATUS      current
      DESCRIPTION "Returns the type of the MBean. "
      ::= { wldfControlRuntimeEntry 3  }
   
   
   wldfControlRuntimeName OBJECT-TYPE
      SYNTAX      OCTET STRING
      MAX-ACCESS  read-only
      STATUS      current
      DESCRIPTION "The name of this configuration. WebLogic Server uses an MBean to implement and persist the configuration. "
      ::= { wldfControlRuntimeEntry 4  }
   
   
   wldfHarvesterManagerRuntimeTable OBJECT-TYPE
      SYNTAX      SEQUENCE OF WldfHarvesterManagerRuntimeEntry
      MAX-ACCESS  not-accessible
      STATUS      current
      DESCRIPTION "Provides statistical information relative to a particular configured Harvester instance, and a means to retreive an on-demand snapshot of configured attribute values. "
      ::= { wls 1935  }
      
   
   wldfHarvesterManagerRuntimeEntry OBJECT-TYPE
      SYNTAX      WldfHarvesterManagerRuntimeEntry
      MAX-ACCESS  not-accessible
      STATUS      current
      DESCRIPTION "Generated SNMP Table Entry."
      INDEX { wldfHarvesterManagerRuntimeIndex}
      ::= { wldfHarvesterManagerRuntimeTable 1 }
      
   WldfHarvesterManagerRuntimeEntry ::=
      SEQUENCE
      {
         wldfHarvesterManagerRuntimeIndex OCTET STRING,
         wldfHarvesterManagerRuntimeObjectName OCTET STRING,
         wldfHarvesterManagerRuntimeType OCTET STRING,
         wldfHarvesterManagerRuntimeCurrentSnapshotElapsedTime Counter64,
         wldfHarvesterManagerRuntimeTotalSamplingCycles Counter64,
         wldfHarvesterManagerRuntimeCurrentDataSampleCount Counter64,
         wldfHarvesterManagerRuntimeAverageSamplingTime Counter64,
         wldfHarvesterManagerRuntimeMinimumSamplingTime Counter64,
         wldfHarvesterManagerRuntimeName OCTET STRING,
         wldfHarvesterManagerRuntimeMaximumSamplingTime Counter64,
         wldfHarvesterManagerRuntimeTotalSamplingTime Counter64,
         wldfHarvesterManagerRuntimeCurrentSnapshotStartTime Counter64,
         wldfHarvesterManagerRuntimeTotalDataSampleCount Counter64
      }
      
   
   wldfHarvesterManagerRuntimeIndex OBJECT-TYPE
      SYNTAX      OCTET STRING
      MAX-ACCESS  not-accessible
      STATUS      current
      DESCRIPTION "Index column"
      ::= { wldfHarvesterManagerRuntimeEntry 1  }
   
   
   wldfHarvesterManagerRuntimeObjectName OBJECT-TYPE
      SYNTAX      OCTET STRING
      MAX-ACCESS  read-only
      STATUS      current
      DESCRIPTION "ObjectName column"
      ::= { wldfHarvesterManagerRuntimeEntry 2  }
   
   
   wldfHarvesterManagerRuntimeType OBJECT-TYPE
      SYNTAX      OCTET STRING
      MAX-ACCESS  read-only
      STATUS      current
      DESCRIPTION "Returns the type of the MBean. "
      ::= { wldfHarvesterManagerRuntimeEntry 3  }
   
   
   wldfHarvesterManagerRuntimeCurrentSnapshotElapsedTime OBJECT-TYPE
      SYNTAX      Counter64
      MAX-ACCESS  read-only
      STATUS      current
      DESCRIPTION "The elapsed time, in nanoseconds, of a snapshot. "
      ::= { wldfHarvesterManagerRuntimeEntry 4  }
   
   
   wldfHarvesterManagerRuntimeTotalSamplingCycles OBJECT-TYPE
      SYNTAX      Counter64
      MAX-ACCESS  read-only
      STATUS      current
      DESCRIPTION "The total number of periodic sampling cycles taken thus far. "
      ::= { wldfHarvesterManagerRuntimeEntry 5  }
   
   
   wldfHarvesterManagerRuntimeCurrentDataSampleCount OBJECT-TYPE
      SYNTAX      Counter64
      MAX-ACCESS  read-only
      STATUS      current
      DESCRIPTION "The number of collected data samples in the current snapshot. "
      ::= { wldfHarvesterManagerRuntimeEntry 6  }
   
   
   wldfHarvesterManagerRuntimeAverageSamplingTime OBJECT-TYPE
      SYNTAX      Counter64
      MAX-ACCESS  read-only
      STATUS      current
      DESCRIPTION "The average amount of time, in nanoseconds, spent in sampling cycles. "
      ::= { wldfHarvesterManagerRuntimeEntry 7  }
   
   
   wldfHarvesterManagerRuntimeMinimumSamplingTime OBJECT-TYPE
      SYNTAX      Counter64
      MAX-ACCESS  read-only
      STATUS      current
      DESCRIPTION "The minimum observed sampling time, in nanoseconds. "
      ::= { wldfHarvesterManagerRuntimeEntry 8  }
   
   
   wldfHarvesterManagerRuntimeName OBJECT-TYPE
      SYNTAX      OCTET STRING
      MAX-ACCESS  read-only
      STATUS      current
      DESCRIPTION "The name of this configuration. WebLogic Server uses an MBean to implement and persist the configuration. "
      ::= { wldfHarvesterManagerRuntimeEntry 9  }
   
   
   wldfHarvesterManagerRuntimeMaximumSamplingTime OBJECT-TYPE
      SYNTAX      Counter64
      MAX-ACCESS  read-only
      STATUS      current
      DESCRIPTION "The maximum observed sampling time, in nanoseconds. "
      ::= { wldfHarvesterManagerRuntimeEntry 10  }
   
   
   wldfHarvesterManagerRuntimeTotalSamplingTime OBJECT-TYPE
      SYNTAX      Counter64
      MAX-ACCESS  read-only
      STATUS      current
      DESCRIPTION "The total amount of observed time, in nanoseconds, spent in sampling cycles. "
      ::= { wldfHarvesterManagerRuntimeEntry 11  }
   
   
   wldfHarvesterManagerRuntimeCurrentSnapshotStartTime OBJECT-TYPE
      SYNTAX      Counter64
      MAX-ACCESS  read-only
      STATUS      current
      DESCRIPTION "The start time, in milliseconds, of the latest archived snapshot. "
      ::= { wldfHarvesterManagerRuntimeEntry 12  }
   
   
   wldfHarvesterManagerRuntimeTotalDataSampleCount OBJECT-TYPE
      SYNTAX      Counter64
      MAX-ACCESS  read-only
      STATUS      current
      DESCRIPTION "The number of configured data samples that have been collected and archived so far in this server session. "
      ::= { wldfHarvesterManagerRuntimeEntry 13  }
   
   
   wldfSystemResourceControlRuntimeTable OBJECT-TYPE
      SYNTAX      SEQUENCE OF WldfSystemResourceControlRuntimeEntry
      MAX-ACCESS  not-accessible
      STATUS      current
      DESCRIPTION " This MBean acts as a Runtime Control for a WLDF profile. An WLDF profile could either be a configured system resource or an external descriptor provided by a an user at runtime.  "
      ::= { wls 1940  }
      
   
   wldfSystemResourceControlRuntimeEntry OBJECT-TYPE
      SYNTAX      WldfSystemResourceControlRuntimeEntry
      MAX-ACCESS  not-accessible
      STATUS      current
      DESCRIPTION "Generated SNMP Table Entry."
      INDEX { wldfSystemResourceControlRuntimeIndex}
      ::= { wldfSystemResourceControlRuntimeTable 1 }
      
   WldfSystemResourceControlRuntimeEntry ::=
      SEQUENCE
      {
         wldfSystemResourceControlRuntimeIndex OCTET STRING,
         wldfSystemResourceControlRuntimeObjectName OCTET STRING,
         wldfSystemResourceControlRuntimeEnabled OCTET STRING,
         wldfSystemResourceControlRuntimeType OCTET STRING,
         wldfSystemResourceControlRuntimeName OCTET STRING
      }
      
   
   wldfSystemResourceControlRuntimeIndex OBJECT-TYPE
      SYNTAX      OCTET STRING
      MAX-ACCESS  not-accessible
      STATUS      current
      DESCRIPTION "Index column"
      ::= { wldfSystemResourceControlRuntimeEntry 1  }
   
   
   wldfSystemResourceControlRuntimeObjectName OBJECT-TYPE
      SYNTAX      OCTET STRING
      MAX-ACCESS  read-only
      STATUS      current
      DESCRIPTION "ObjectName column"
      ::= { wldfSystemResourceControlRuntimeEntry 2  }
   
   
   wldfSystemResourceControlRuntimeEnabled OBJECT-TYPE
      SYNTAX      OCTET STRING
      MAX-ACCESS  read-only
      STATUS      current
      DESCRIPTION "is the descriptor enabled "
      ::= { wldfSystemResourceControlRuntimeEntry 3  }
   
   
   wldfSystemResourceControlRuntimeType OBJECT-TYPE
      SYNTAX      OCTET STRING
      MAX-ACCESS  read-only
      STATUS      current
      DESCRIPTION "Returns the type of the MBean. "
      ::= { wldfSystemResourceControlRuntimeEntry 4  }
   
   
   wldfSystemResourceControlRuntimeName OBJECT-TYPE
      SYNTAX      OCTET STRING
      MAX-ACCESS  read-only
      STATUS      current
      DESCRIPTION "The name of this configuration. WebLogic Server uses an MBean to implement and persist the configuration. "
      ::= { wldfSystemResourceControlRuntimeEntry 5  }
   
   
   wldfWatchNotificationSourceRuntimeTable OBJECT-TYPE
      SYNTAX      SEQUENCE OF WldfWatchNotificationSourceRuntimeEntry
      MAX-ACCESS  not-accessible
      STATUS      current
      DESCRIPTION "Attaches an action listener in order to receive action events when a policy evaluates to true. Note that the listener will receive all actions; the caller must filter the output.  Unlike the deprecated WLDFWatchJMXNotificationRuntimeMBean, the action generated by this source is a Java Map object comprised of simple JDK types, and does not require a client dependency on any WLDF code.  Note: As of WebLogic Server 12.2.1, the terms watch and notification are replaced by policy and action, respectively. However, the definition of these terms has not changed. "
      ::= { wls 1945  }
      
   
   wldfWatchNotificationSourceRuntimeEntry OBJECT-TYPE
      SYNTAX      WldfWatchNotificationSourceRuntimeEntry
      MAX-ACCESS  not-accessible
      STATUS      current
      DESCRIPTION "Generated SNMP Table Entry."
      INDEX { wldfWatchNotificationSourceRuntimeIndex}
      ::= { wldfWatchNotificationSourceRuntimeTable 1 }
      
   WldfWatchNotificationSourceRuntimeEntry ::=
      SEQUENCE
      {
         wldfWatchNotificationSourceRuntimeIndex OCTET STRING,
         wldfWatchNotificationSourceRuntimeObjectName OCTET STRING,
         wldfWatchNotificationSourceRuntimeType OCTET STRING,
         wldfWatchNotificationSourceRuntimeName OCTET STRING
      }
      
   
   wldfWatchNotificationSourceRuntimeIndex OBJECT-TYPE
      SYNTAX      OCTET STRING
      MAX-ACCESS  not-accessible
      STATUS      current
      DESCRIPTION "Index column"
      ::= { wldfWatchNotificationSourceRuntimeEntry 1  }
   
   
   wldfWatchNotificationSourceRuntimeObjectName OBJECT-TYPE
      SYNTAX      OCTET STRING
      MAX-ACCESS  read-only
      STATUS      current
      DESCRIPTION "ObjectName column"
      ::= { wldfWatchNotificationSourceRuntimeEntry 2  }
   
   
   wldfWatchNotificationSourceRuntimeType OBJECT-TYPE
      SYNTAX      OCTET STRING
      MAX-ACCESS  read-only
      STATUS      current
      DESCRIPTION "Returns the type of the MBean. "
      ::= { wldfWatchNotificationSourceRuntimeEntry 3  }
   
   
   wldfWatchNotificationSourceRuntimeName OBJECT-TYPE
      SYNTAX      OCTET STRING
      MAX-ACCESS  read-only
      STATUS      current
      DESCRIPTION "The name of this configuration. WebLogic Server uses an MBean to implement and persist the configuration. "
      ::= { wldfWatchNotificationSourceRuntimeEntry 4  }
   
   
   debugScopeTable OBJECT-TYPE
      SYNTAX      SEQUENCE OF DebugScopeEntry
      MAX-ACCESS  not-accessible
      STATUS      current
      DESCRIPTION "This interface captures whether the enabled state of a debug scope. The name of a debug scope is the fully qualified scope name for example weblogic.security.SSL "
      ::= { wls 1950  }
      
   
   debugScopeEntry OBJECT-TYPE
      SYNTAX      DebugScopeEntry
      MAX-ACCESS  not-accessible
      STATUS      current
      DESCRIPTION "Generated SNMP Table Entry."
      INDEX { debugScopeIndex}
      ::= { debugScopeTable 1 }
      
   DebugScopeEntry ::=
      SEQUENCE
      {
         debugScopeIndex      OCTET STRING,
         debugScopeObjectName OCTET STRING,
         debugScopeEnabled    OCTET STRING,
         debugScopeType       OCTET STRING,
         debugScopeName       OCTET STRING,
         debugScopeTags       OCTET STRING
      }
      
   
   debugScopeIndex OBJECT-TYPE
      SYNTAX      OCTET STRING
      MAX-ACCESS  not-accessible
      STATUS      current
      DESCRIPTION "Index column"
      ::= { debugScopeEntry 1  }
   
   
   debugScopeObjectName OBJECT-TYPE
      SYNTAX      OCTET STRING
      MAX-ACCESS  read-only
      STATUS      current
      DESCRIPTION "ObjectName column"
      ::= { debugScopeEntry 2  }
   
   
   debugScopeEnabled OBJECT-TYPE
      SYNTAX      OCTET STRING
      MAX-ACCESS  read-only
      STATUS      current
      DESCRIPTION "Gets the enabled state of the debug scope mbean. By default a debug scope is disabled. "
      ::= { debugScopeEntry 3  }
   
   
   debugScopeType OBJECT-TYPE
      SYNTAX      OCTET STRING
      MAX-ACCESS  read-only
      STATUS      current
      DESCRIPTION "Returns the type of the MBean. "
      ::= { debugScopeEntry 4  }
   
   
   debugScopeName OBJECT-TYPE
      SYNTAX      OCTET STRING
      MAX-ACCESS  read-only
      STATUS      current
      DESCRIPTION "It seems that the getter must be overriden because the setter is. "
      ::= { debugScopeEntry 5  }
   
   
   debugScopeTags OBJECT-TYPE
      SYNTAX      OCTET STRING
      MAX-ACCESS  read-only
      STATUS      current
      DESCRIPTION "Return all tags on this Configuration MBean "
      ::= { debugScopeEntry 6  }
   
   
   deploymentValidationPluginTable OBJECT-TYPE
      SYNTAX      SEQUENCE OF DeploymentValidationPluginEntry
      MAX-ACCESS  not-accessible
      STATUS      current
      DESCRIPTION "Specifies the deployment validation plug-in configuration attributes. The plug-in factory must have a no-argument constructor and must implement this interface: weblogic.deployment.configuration.DeploymentValidationPluginFactory "
      ::= { wls 1955  }
      
   
   deploymentValidationPluginEntry OBJECT-TYPE
      SYNTAX      DeploymentValidationPluginEntry
      MAX-ACCESS  not-accessible
      STATUS      current
      DESCRIPTION "Generated SNMP Table Entry."
      INDEX { deploymentValidationPluginIndex}
      ::= { deploymentValidationPluginTable 1 }
      
   DeploymentValidationPluginEntry ::=
      SEQUENCE
      {
         deploymentValidationPluginIndex OCTET STRING,
         deploymentValidationPluginObjectName OCTET STRING,
         deploymentValidationPluginType OCTET STRING,
         deploymentValidationPluginName OCTET STRING,
         deploymentValidationPluginFactoryClassname OCTET STRING,
         deploymentValidationPluginTags OCTET STRING
      }
      
   
   deploymentValidationPluginIndex OBJECT-TYPE
      SYNTAX      OCTET STRING
      MAX-ACCESS  not-accessible
      STATUS      current
      DESCRIPTION "Index column"
      ::= { deploymentValidationPluginEntry 1  }
   
   
   deploymentValidationPluginObjectName OBJECT-TYPE
      SYNTAX      OCTET STRING
      MAX-ACCESS  read-only
      STATUS      current
      DESCRIPTION "ObjectName column"
      ::= { deploymentValidationPluginEntry 2  }
   
   
   deploymentValidationPluginType OBJECT-TYPE
      SYNTAX      OCTET STRING
      MAX-ACCESS  read-only
      STATUS      current
      DESCRIPTION "Returns the type of the MBean. "
      ::= { deploymentValidationPluginEntry 3  }
   
   
   deploymentValidationPluginName OBJECT-TYPE
      SYNTAX      OCTET STRING
      MAX-ACCESS  read-only
      STATUS      current
      DESCRIPTION "The user-specified name of this MBean instance.  This name is included as one of the key properties in the MBean's javax.management.ObjectName:  Name=user-specified-name "
      ::= { deploymentValidationPluginEntry 4  }
   
   
   deploymentValidationPluginFactoryClassname OBJECT-TYPE
      SYNTAX      OCTET STRING
      MAX-ACCESS  read-only
      STATUS      current
      DESCRIPTION "Gets the classname of the plug-in factory used for validation. This is a fully qualified name. The class must be in the Administration Server classpath.  "
      ::= { deploymentValidationPluginEntry 5  }
   
   
   deploymentValidationPluginTags OBJECT-TYPE
      SYNTAX      OCTET STRING
      MAX-ACCESS  read-only
      STATUS      current
      DESCRIPTION "Return all tags on this Configuration MBean "
      ::= { deploymentValidationPluginEntry 6  }
   
   
   parameterTable OBJECT-TYPE
      SYNTAX      SEQUENCE OF ParameterEntry
      MAX-ACCESS  not-accessible
      STATUS      current
      DESCRIPTION "Specifies the parameters used to configure the DeploymentValidationPluginMBean. "
      ::= { wls 1960  }
      
   
   parameterEntry OBJECT-TYPE
      SYNTAX      ParameterEntry
      MAX-ACCESS  not-accessible
      STATUS      current
      DESCRIPTION "Generated SNMP Table Entry."
      INDEX { parameterIndex}
      ::= { parameterTable 1 }
      
   ParameterEntry ::=
      SEQUENCE
      {
         parameterIndex       OCTET STRING,
         parameterObjectName  OCTET STRING,
         parameterValue       OCTET STRING,
         parameterDescription OCTET STRING,
         parameterType        OCTET STRING,
         parameterName        OCTET STRING,
         parameterTags        OCTET STRING
      }
      
   
   parameterIndex OBJECT-TYPE
      SYNTAX      OCTET STRING
      MAX-ACCESS  not-accessible
      STATUS      current
      DESCRIPTION "Index column"
      ::= { parameterEntry 1  }
   
   
   parameterObjectName OBJECT-TYPE
      SYNTAX      OCTET STRING
      MAX-ACCESS  read-only
      STATUS      current
      DESCRIPTION "ObjectName column"
      ::= { parameterEntry 2  }
   
   
   parameterValue OBJECT-TYPE
      SYNTAX      OCTET STRING
      MAX-ACCESS  read-only
      STATUS      current
      DESCRIPTION "Gets the parameter value.  "
      ::= { parameterEntry 3  }
   
   
   parameterDescription OBJECT-TYPE
      SYNTAX      OCTET STRING
      MAX-ACCESS  read-only
      STATUS      current
      DESCRIPTION "Gets the parameter description.  "
      ::= { parameterEntry 4  }
   
   
   parameterType OBJECT-TYPE
      SYNTAX      OCTET STRING
      MAX-ACCESS  read-only
      STATUS      current
      DESCRIPTION "Returns the type of the MBean. "
      ::= { parameterEntry 5  }
   
   
   parameterName OBJECT-TYPE
      SYNTAX      OCTET STRING
      MAX-ACCESS  read-only
      STATUS      current
      DESCRIPTION "Gets the parameter name.  "
      ::= { parameterEntry 6  }
   
   
   parameterTags OBJECT-TYPE
      SYNTAX      OCTET STRING
      MAX-ACCESS  read-only
      STATUS      current
      DESCRIPTION "Return all tags on this Configuration MBean "
      ::= { parameterEntry 7  }
   
   
   replicatedStoreTable OBJECT-TYPE
      SYNTAX      SEQUENCE OF ReplicatedStoreEntry
      MAX-ACCESS  not-accessible
      STATUS      current
      DESCRIPTION "Defines an instance of a Replicated Store.  A WebLogic Replicated Store is a high performance storage option for Exalogic hosted Weblogic Messaging Services and is an alternative to WebLogic Server's File and JDBC persistent storage options. Replicated stores depend on Exalogic replicated memory that is managed by a separately administered Daemon Cluster that must be started before a WebLogic Replicated Store can boot.   See Using the WebLogic Replicated Store in Administering WebLogic Server for Oracle Exalogic Elastic Cloud.  This feature should be used only in Oracle Exalogic Elastic Cloud environments."
      ::= { wls 1965  }
      
   
   replicatedStoreEntry OBJECT-TYPE
      SYNTAX      ReplicatedStoreEntry
      MAX-ACCESS  not-accessible
      STATUS      current
      DESCRIPTION "Generated SNMP Table Entry."
      INDEX { replicatedStoreIndex}
      ::= { replicatedStoreTable 1 }
      
   ReplicatedStoreEntry ::=
      SEQUENCE
      {
         replicatedStoreIndex OCTET STRING,
         replicatedStoreObjectName OCTET STRING,
         replicatedStoreLogicalName OCTET STRING,
         replicatedStoreType  OCTET STRING,
         replicatedStoreIoBufferSize Integer32,
         replicatedStoreXAResourceName OCTET STRING,
         replicatedStoreLocalIndex Integer32,
         replicatedStoreName  OCTET STRING,
         replicatedStoreRegionSize Integer32,
         replicatedStoreDirectory OCTET STRING,
         replicatedStoreDeploymentOrder Integer32,
         replicatedStorePartialClusterStabilityDelaySeconds Counter64,
         replicatedStoreRestartInPlace OCTET STRING,
         replicatedStoreNumberOfRestartAttempts INTEGER,
         replicatedStoreSecondsBetweenRestarts INTEGER,
         replicatedStoreDistributionPolicy OCTET STRING,
         replicatedStoreTags  OCTET STRING,
         replicatedStoreMigrationPolicy OCTET STRING,
         replicatedStoreFailbackDelaySeconds Counter64,
         replicatedStoreInitialBootDelaySeconds Counter64
      }
      
   
   replicatedStoreIndex OBJECT-TYPE
      SYNTAX      OCTET STRING
      MAX-ACCESS  not-accessible
      STATUS      current
      DESCRIPTION "Index column"
      ::= { replicatedStoreEntry 1  }
   
   
   replicatedStoreObjectName OBJECT-TYPE
      SYNTAX      OCTET STRING
      MAX-ACCESS  read-only
      STATUS      current
      DESCRIPTION "ObjectName column"
      ::= { replicatedStoreEntry 2  }
   
   
   replicatedStoreLogicalName OBJECT-TYPE
      SYNTAX      OCTET STRING
      MAX-ACCESS  read-only
      STATUS      current
      DESCRIPTION "The name used by subsystems to refer to different stores on different servers using the same name.  For example, an EJB that uses the timer service may refer to its store using the logical name, and this name may be valid on multiple servers in the same cluster, even if each server has a store with a different physical name.  Multiple stores in the same domain or the same cluster may share the same logical name. However, a given logical name may not be assigned to more than one store on the same server."
      ::= { replicatedStoreEntry 3  }
   
   
   replicatedStoreType OBJECT-TYPE
      SYNTAX      OCTET STRING
      MAX-ACCESS  read-only
      STATUS      current
      DESCRIPTION "Returns the type of the MBean."
      ::= { replicatedStoreEntry 5  }
   
   
   replicatedStoreIoBufferSize OBJECT-TYPE
      SYNTAX      Integer32
      MAX-ACCESS  read-only
      STATUS      current
      DESCRIPTION "The I/O buffer size, in bytes, automatically rounded down to the nearest power of 2.  Controls the amount of WebLogic Server JVM off-heap (native) memory that is allocated for a replicated store.  For the best runtime performance, Oracle recommends setting IOBufferSize so that it is larger than the largest write (multiple concurrent store requests may be combined into a single write).  For the best boot recovery time performance of large stores, Oracle recommends setting IOBufferSize to at least 2 megabytes."
      ::= { replicatedStoreEntry 7  }
   
   
   replicatedStoreXAResourceName OBJECT-TYPE
      SYNTAX      OCTET STRING
      MAX-ACCESS  read-only
      STATUS      current
      DESCRIPTION "Overrides the name of the XAResource that this store registers with JTA.  You should not normally set this attribute. Its purpose is to allow the name of the XAResource to be overridden when a store has been upgraded from an older release and the store contained prepared transactions. The generated name should be used in all other cases."
      ::= { replicatedStoreEntry 9  }
   
   
   replicatedStoreLocalIndex OBJECT-TYPE
      SYNTAX      Integer32
      MAX-ACCESS  read-only
      STATUS      current
      DESCRIPTION "Specifies a local Daemon to attach to when a Daemon Cluster has multiple Daemons configured to run on the current node.  The local Daemon is chosen using the formula: ((localindex) modulo (number-of-local-daemons)). When 0, it always resolves to the first available Daemon entry in the rs_daemons.cfg  file that has an address on the current node. The default value is 0.  This setting is not applicable to production environments. To ensure high availability, a Daemon Cluster in a production environment should have multiple nodes with one Daemon on each node."
      ::= { replicatedStoreEntry 10  }
   
   
   replicatedStoreName OBJECT-TYPE
      SYNTAX      OCTET STRING
      MAX-ACCESS  read-only
      STATUS      current
      DESCRIPTION "The user-specified name of this MBean instance.  This name is included as one of the key properties in the MBean's javax.management.ObjectName:  Name=user-specified-name"
      ::= { replicatedStoreEntry 11  }
   
   
   replicatedStoreRegionSize OBJECT-TYPE
      SYNTAX      Integer32
      MAX-ACCESS  read-only
      STATUS      current
      DESCRIPTION "The region size, in bytes. Data is stored in one or more uniquely named Regions within a Daemon Cluster where each region is created with this size. Oracle recommends that regions sizes should be tuned to be a small fraction of the available local Daemon memory."
      ::= { replicatedStoreEntry 16  }
   
   
   replicatedStoreDirectory OBJECT-TYPE
      SYNTAX      OCTET STRING
      MAX-ACCESS  read-only
      STATUS      current
      DESCRIPTION "Specifies the path of the Replicated Store Global Directory. This must be the same directory that is used to store the Daemon Cluster rs_daemons.cfg configuration file and requires a specially tuned NFS mount. Oracle recommends using an absolute directory path on a shared NFS mount."
      ::= { replicatedStoreEntry 17  }
   
   
   replicatedStoreDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { replicatedStoreEntry 18  }
   
   
   replicatedStorePartialClusterStabilityDelaySeconds OBJECT-TYPE
      SYNTAX      Counter64
      MAX-ACCESS  read-only
      STATUS      current
      DESCRIPTION "Specifies the amount of time, in seconds, to delay before a partially started cluster starts all cluster targeted JMS artifact instances that are configured with a Migration Policy of Always or On-Failure.   Before this timeout expires or all servers are running, a cluster starts a subset of such instances based on the total number of servers running and the configured cluster size. Once the timeout expires or all servers have started, the system considers the cluster stable and starts any remaining services.  This delay ensures that services are balanced across a cluster even if the servers are started sequentially. It is ignored once a cluster is fully started (stable) or when individual servers are started.   A value > 0 specifies the time, in seconds, to delay before a partially started cluster starts dynamically configured services. A value of 0 specifies no delay."
      ::= { replicatedStoreEntry 19  }
   
   
   replicatedStoreRestartInPlace OBJECT-TYPE
      SYNTAX      OCTET STRING
      MAX-ACCESS  read-only
      STATUS      current
      DESCRIPTION "Enables periodic automatic restart of failed cluster targeted JMS artifact instance(s) running on healthy WebLogic Server instances.  Restart attempts occur before attempts to migrate an instance to a different server in the cluster. When this setting is configured on a Store it applies to all JMS artifacts that reference the store.   Restarts occur when Restart In Place is set to true, the JMS artifact is cluster targeted, and the Migration Policy is set to On-Failure or Always>.  This attribute is not used by WebLogic Messaging Bridges which automatically restart internal connections as needed."
      ::= { replicatedStoreEntry 20  }
   
   
   replicatedStoreNumberOfRestartAttempts OBJECT-TYPE
      SYNTAX      INTEGER
      MAX-ACCESS  read-only
      STATUS      current
      DESCRIPTION "Specifies the number of restart attempts before migrating a failed JMS artifact instance to another server in the WebLogic cluster.   A value > 0 specifies the number of restart attempts before migrating a failed service instance. A value of 0 specifies the same behavior as setting {@link #getRestartInPlace} to false. A value of -1 specifies the service is  never migrated. Instead, it continues to attempt to restart until it either starts or the server instance shuts down."
      ::= { replicatedStoreEntry 21  }
   
   
   replicatedStoreSecondsBetweenRestarts OBJECT-TYPE
      SYNTAX      INTEGER
      MAX-ACCESS  read-only
      STATUS      current
      DESCRIPTION "Specifies the amount of time, in seconds, to wait in between attempts to restart a failed service instance."
      ::= { replicatedStoreEntry 22  }
   
   
   replicatedStoreDistributionPolicy OBJECT-TYPE
      SYNTAX      OCTET STRING
      MAX-ACCESS  read-only
      STATUS      current
      DESCRIPTION "Specifies how the instances of a configured JMS artifact are named and distributed when deployed to a cluster. When this setting is configured on a Store it applies to all JMS artifacts that reference the store. Valid options:   Distributed creates an artifact instance on each cluster member in a cluster. Required for all SAF Agents and for cluster targeted or resource group scoped JMS Servers that host distributed destinations.    Singleton creates one artifact instance on a single cluster member of a cluster. Required for cluster targeted or resource group scoped JMS Servers that host standalone (non-distributed) destinations and for cluster targeted or resource group scoped Path Services.  The Migration Policy must be On-Failure or Always when using this option with a JMS Server, On-Failure when using this option with a Messaging Bridge, and Always when using this option with a Path Service.    The DistributionPolicy determines the instance name suffix for cluster targeted JMS artifacts.  The suffix for a cluster targeted Singleton is -01 and for a cluster targeted Distributed is @ClusterMemberName."
      ::= { replicatedStoreEntry 23  }
   
   
   replicatedStoreTags OBJECT-TYPE
      SYNTAX      OCTET STRING
      MAX-ACCESS  read-only
      STATUS      current
      DESCRIPTION "Return all tags on this Configuration MBean"
      ::= { replicatedStoreEntry 24  }
   
   
   replicatedStoreMigrationPolicy OBJECT-TYPE
      SYNTAX      OCTET STRING
      MAX-ACCESS  read-only
      STATUS      current
      DESCRIPTION "Controls migration and restart behavior of cluster targeted JMS service artifact instances. When this setting is configured on a Store it applies to all JMS artifacts that reference the store. Valid options:  Off disables migration and restart support for cluster targeted JMS service objects, including the ability to restart a failed persistent store instance and its associated services.   This policy can not be combined with the Singleton Migration Policy.  On-Failure enables automatic migration and restart of instances on the failure of a subsystem Service or WebLogic Server instance, including automatic fail-back and load balancing of instances.   Always provides the same behavior as On-Failure and automatically migrates instances even in the event of a graceful shutdown or a partial cluster start.   Note: Cluster leasing must be configured for On-Failure and Always."
      ::= { replicatedStoreEntry 25  }
   
   
   replicatedStoreFailbackDelaySeconds OBJECT-TYPE
      SYNTAX      Counter64
      MAX-ACCESS  read-only
      STATUS      current
      DESCRIPTION "Specifies the amount of time, in seconds, to delay before failing a cluster targeted JMS artifact instance back to its preferred server after the preferred server failed and was restarted.  This delay allows time for the system to stabilize and dependent services to be restarted, preventing a system failure during a reboot.   A value > 0 specifies the time, in seconds, to delay before failing a JMS artifact back to its user preferred server. A value of 0 indicates that the instance would never failback. A value of -1 indicates that there is no delay and the instance would failback immediately.   Note: This setting only applies when the JMS artifact is cluster targeted and the Migration Policy is set to On-Failure or Always>."
      ::= { replicatedStoreEntry 26  }
   
   
   replicatedStoreInitialBootDelaySeconds OBJECT-TYPE
      SYNTAX      Counter64
      MAX-ACCESS  read-only
      STATUS      current
      DESCRIPTION "Specifies the amount of time, in seconds, to delay before starting a cluster targeted JMS instance on a newly booted WebLogic server. When this setting is configured on a Store it applies to all JMS artifacts that reference the store.  This allows time for the system to stabilize and dependent services to be restarted, preventing a system failure during a reboot.   A value > 0 is the time, in seconds, to delay before before loading resources after a failure and restart. A value of 0 specifies no delay.  Note: This setting only applies when the JMS artifact is cluster targeted and the Migration Policy is set to On-Failure or Always>."
      ::= { replicatedStoreEntry 27  }
   
   
   serverLogRuntimeTable OBJECT-TYPE
      SYNTAX      SEQUENCE OF ServerLogRuntimeEntry
      MAX-ACCESS  not-accessible
      STATUS      current
      DESCRIPTION "This interface defines the control operations for a log in the WebLogic Server. "
      ::= { wls 1970  }
      
   
   serverLogRuntimeEntry OBJECT-TYPE
      SYNTAX      ServerLogRuntimeEntry
      MAX-ACCESS  not-accessible
      STATUS      current
      DESCRIPTION "Generated SNMP Table Entry."
      INDEX { serverLogRuntimeIndex}
      ::= { serverLogRuntimeTable 1 }
      
   ServerLogRuntimeEntry ::=
      SEQUENCE
      {
         serverLogRuntimeIndex OCTET STRING,
         serverLogRuntimeObjectName OCTET STRING,
         serverLogRuntimeType OCTET STRING,
         serverLogRuntimeName OCTET STRING,
         serverLogRuntimeLogFileStreamOpened OCTET STRING
      }
      
   
   serverLogRuntimeIndex OBJECT-TYPE
      SYNTAX      OCTET STRING
      MAX-ACCESS  not-accessible
      STATUS      current
      DESCRIPTION "Index column"
      ::= { serverLogRuntimeEntry 1  }
   
   
   serverLogRuntimeObjectName OBJECT-TYPE
      SYNTAX      OCTET STRING
      MAX-ACCESS  read-only
      STATUS      current
      DESCRIPTION "ObjectName column"
      ::= { serverLogRuntimeEntry 2  }
   
   
   serverLogRuntimeType OBJECT-TYPE
      SYNTAX      OCTET STRING
      MAX-ACCESS  read-only
      STATUS      current
      DESCRIPTION "Returns the type of the MBean. "
      ::= { serverLogRuntimeEntry 3  }
   
   
   serverLogRuntimeName OBJECT-TYPE
      SYNTAX      OCTET STRING
      MAX-ACCESS  read-only
      STATUS      current
      DESCRIPTION "The name of this configuration. WebLogic Server uses an MBean to implement and persist the configuration. "
      ::= { serverLogRuntimeEntry 4  }
   
   
   serverLogRuntimeLogFileStreamOpened OBJECT-TYPE
      SYNTAX      OCTET STRING
      MAX-ACCESS  read-only
      STATUS      current
      DESCRIPTION "Gets the opened state of the log file stream represented by this instance. "
      ::= { serverLogRuntimeEntry 5  }
   
   
   wseeClientConfigurationRuntimeTable OBJECT-TYPE
      SYNTAX      SEQUENCE OF WseeClientConfigurationRuntimeEntry
      MAX-ACCESS  not-accessible
      STATUS      current
      DESCRIPTION "Encapsulates runtime policy subject information about a particular Web Service reference. The name attribute of this MBean will be the value of the service-ref-name element in service reference descriptor file or the name attribute value of WebServiceRef annotation. "
      ::= { wls 1975  }
      
   
   wseeClientConfigurationRuntimeEntry OBJECT-TYPE
      SYNTAX      WseeClientConfigurationRuntimeEntry
      MAX-ACCESS  not-accessible
      STATUS      current
      DESCRIPTION "Generated SNMP Table Entry."
      INDEX { wseeClientConfigurationRuntimeIndex}
      ::= { wseeClientConfigurationRuntimeTable 1 }
      
   WseeClientConfigurationRuntimeEntry ::=
      SEQUENCE
      {
         wseeClientConfigurationRuntimeIndex OCTET STRING,
         wseeClientConfigurationRuntimeObjectName OCTET STRING,
         wseeClientConfigurationRuntimeType OCTET STRING,
         wseeClientConfigurationRuntimeName OCTET STRING,
         wseeClientConfigurationRuntimeServiceReferenceName OCTET STRING
      }
      
   
   wseeClientConfigurationRuntimeIndex OBJECT-TYPE
      SYNTAX      OCTET STRING
      MAX-ACCESS  not-accessible
      STATUS      current
      DESCRIPTION "Index column"
      ::= { wseeClientConfigurationRuntimeEntry 1  }
   
   
   wseeClientConfigurationRuntimeObjectName OBJECT-TYPE
      SYNTAX      OCTET STRING
      MAX-ACCESS  read-only
      STATUS      current
      DESCRIPTION "ObjectName column"
      ::= { wseeClientConfigurationRuntimeEntry 2  }
   
   
   wseeClientConfigurationRuntimeType OBJECT-TYPE
      SYNTAX      OCTET STRING
      MAX-ACCESS  read-only
      STATUS      current
      DESCRIPTION "Returns the type of the MBean. "
      ::= { wseeClientConfigurationRuntimeEntry 3  }
   
   
   wseeClientConfigurationRuntimeName OBJECT-TYPE
      SYNTAX      OCTET STRING
      MAX-ACCESS  read-only
      STATUS      current
      DESCRIPTION "The name of this configuration. WebLogic Server uses an MBean to implement and persist the configuration. "
      ::= { wseeClientConfigurationRuntimeEntry 4  }
   
   
   wseeClientConfigurationRuntimeServiceReferenceName OBJECT-TYPE
      SYNTAX      OCTET STRING
      MAX-ACCESS  read-only
      STATUS      current
      DESCRIPTION "Specifies the qualified name of this client configuration.  This attribute is grabbed from service reference descriptor bean. "
      ::= { wseeClientConfigurationRuntimeEntry 5  }
   
   
   wseePortConfigurationRuntimeTable OBJECT-TYPE
      SYNTAX      SEQUENCE OF WseePortConfigurationRuntimeEntry
      MAX-ACCESS  not-accessible
      STATUS      current
      DESCRIPTION " Encapsulates runtime policy subject information about a particular Port. The subject name attribute of this MBean will be the value of the local part of port QName.  "
      ::= { wls 1980  }
      
   
   wseePortConfigurationRuntimeEntry OBJECT-TYPE
      SYNTAX      WseePortConfigurationRuntimeEntry
      MAX-ACCESS  not-accessible
      STATUS      current
      DESCRIPTION "Generated SNMP Table Entry."
      INDEX { wseePortConfigurationRuntimeIndex}
      ::= { wseePortConfigurationRuntimeTable 1 }
      
   WseePortConfigurationRuntimeEntry ::=
      SEQUENCE
      {
         wseePortConfigurationRuntimeIndex OCTET STRING,
         wseePortConfigurationRuntimeObjectName OCTET STRING,
         wseePortConfigurationRuntimePolicySubjectType OCTET STRING,
         wseePortConfigurationRuntimePolicyAttachmentSupport OCTET STRING,
         wseePortConfigurationRuntimePolicySubjectResourcePattern OCTET STRING,
         wseePortConfigurationRuntimeType OCTET STRING,
         wseePortConfigurationRuntimePolicySubjectAbsolutePortableExpression OCTET STRING,
         wseePortConfigurationRuntimeName OCTET STRING,
         wseePortConfigurationRuntimePolicySubjectName OCTET STRING
      }
      
   
   wseePortConfigurationRuntimeIndex OBJECT-TYPE
      SYNTAX      OCTET STRING
      MAX-ACCESS  not-accessible
      STATUS      current
      DESCRIPTION "Index column"
      ::= { wseePortConfigurationRuntimeEntry 1  }
   
   
   wseePortConfigurationRuntimeObjectName OBJECT-TYPE
      SYNTAX      OCTET STRING
      MAX-ACCESS  read-only
      STATUS      current
      DESCRIPTION "ObjectName column"
      ::= { wseePortConfigurationRuntimeEntry 2  }
   
   
   wseePortConfigurationRuntimePolicySubjectType OBJECT-TYPE
      SYNTAX      OCTET STRING
      MAX-ACCESS  read-only
      STATUS      current
      DESCRIPTION "Get subject type for this operation MBean. "
      ::= { wseePortConfigurationRuntimeEntry 3  }
   
   
   wseePortConfigurationRuntimePolicyAttachmentSupport OBJECT-TYPE
      SYNTAX      OCTET STRING
      MAX-ACCESS  read-only
      STATUS      current
      DESCRIPTION "Get attachment support for this operation MBean. "
      ::= { wseePortConfigurationRuntimeEntry 4  }
   
   
   wseePortConfigurationRuntimePolicySubjectResourcePattern OBJECT-TYPE
      SYNTAX      OCTET STRING
      MAX-ACCESS  read-only
      STATUS      current
      DESCRIPTION "The policySubject parameter must uniquely identify what application, module, service, and port (port or operation for WLS Policy) is targeted. The syntax currently used by JRF for J2EE WebService Endpoints will be used: /{domain}/{instance}/{app}/WEBs|EJBs/{module }/WEBSERVICECLIENTs/{service-ref-name}/PORTs/{port} "
      ::= { wseePortConfigurationRuntimeEntry 5  }
   
   
   wseePortConfigurationRuntimeType OBJECT-TYPE
      SYNTAX      OCTET STRING
      MAX-ACCESS  read-only
      STATUS      current
      DESCRIPTION "Returns the type of the MBean. "
      ::= { wseePortConfigurationRuntimeEntry 6  }
   
   
   wseePortConfigurationRuntimePolicySubjectAbsolutePortableExpression OBJECT-TYPE
      SYNTAX      OCTET STRING
      MAX-ACCESS  read-only
      STATUS      current
      DESCRIPTION "The policySubject AbsolutePortableExpression This is the WSM ResourcePattern AbsolutePortableExpression string"
      ::= { wseePortConfigurationRuntimeEntry 7  }
   
   
   wseePortConfigurationRuntimeName OBJECT-TYPE
      SYNTAX      OCTET STRING
      MAX-ACCESS  read-only
      STATUS      current
      DESCRIPTION "The name of this configuration. WebLogic Server uses an MBean to implement and persist the configuration. "
      ::= { wseePortConfigurationRuntimeEntry 8  }
   
   
   wseePortConfigurationRuntimePolicySubjectName OBJECT-TYPE
      SYNTAX      OCTET STRING
      MAX-ACCESS  read-only
      STATUS      current
      DESCRIPTION "Get subject name for this operation MBean. "
      ::= { wseePortConfigurationRuntimeEntry 9  }
   
   
   coherenceManagementClusterTable OBJECT-TYPE
      SYNTAX      SEQUENCE OF CoherenceManagementClusterEntry
      MAX-ACCESS  not-accessible
      STATUS      current
      DESCRIPTION "This class is used to hold JMX information about a coherence cluster in both the standalone case and WLS managed cluster case. "
      ::= { wls 1985  }
      
   
   coherenceManagementClusterEntry OBJECT-TYPE
      SYNTAX      CoherenceManagementClusterEntry
      MAX-ACCESS  not-accessible
      STATUS      current
      DESCRIPTION "Generated SNMP Table Entry."
      INDEX { coherenceManagementClusterIndex}
      ::= { coherenceManagementClusterTable 1 }
      
   CoherenceManagementClusterEntry ::=
      SEQUENCE
      {
         coherenceManagementClusterIndex OCTET STRING,
         coherenceManagementClusterObjectName OCTET STRING,
         coherenceManagementClusterType OCTET STRING,
         coherenceManagementClusterName OCTET STRING,
         coherenceManagementClusterReportGroupFile OCTET STRING,
         coherenceManagementClusterUsername OCTET STRING,
         coherenceManagementClusterTags OCTET STRING
      }
      
   
   coherenceManagementClusterIndex OBJECT-TYPE
      SYNTAX      OCTET STRING
      MAX-ACCESS  not-accessible
      STATUS      current
      DESCRIPTION "Index column"
      ::= { coherenceManagementClusterEntry 1  }
   
   
   coherenceManagementClusterObjectName OBJECT-TYPE
      SYNTAX      OCTET STRING
      MAX-ACCESS  read-only
      STATUS      current
      DESCRIPTION "ObjectName column"
      ::= { coherenceManagementClusterEntry 2  }
   
   
   coherenceManagementClusterType OBJECT-TYPE
      SYNTAX      OCTET STRING
      MAX-ACCESS  read-only
      STATUS      current
      DESCRIPTION "Returns the type of the MBean. "
      ::= { coherenceManagementClusterEntry 3  }
   
   
   coherenceManagementClusterName OBJECT-TYPE
      SYNTAX      OCTET STRING
      MAX-ACCESS  read-only
      STATUS      current
      DESCRIPTION "The user-specified name of this MBean instance.  This name is included as one of the key properties in the MBean's javax.management.ObjectName:  Name=user-specified-name "
      ::= { coherenceManagementClusterEntry 4  }
   
   
   coherenceManagementClusterReportGroupFile OBJECT-TYPE
      SYNTAX      OCTET STRING
      MAX-ACCESS  read-only
      STATUS      current
      DESCRIPTION "Get the report group file representing the superset of metrics this bean will gather. "
      ::= { coherenceManagementClusterEntry 5  }
   
   
   coherenceManagementClusterUsername OBJECT-TYPE
      SYNTAX      OCTET STRING
      MAX-ACCESS  read-only
      STATUS      current
      DESCRIPTION "Get the JMX connection username "
      ::= { coherenceManagementClusterEntry 6  }
   
   
   coherenceManagementClusterTags OBJECT-TYPE
      SYNTAX      OCTET STRING
      MAX-ACCESS  read-only
      STATUS      current
      DESCRIPTION "Return all tags on this Configuration MBean "
      ::= { coherenceManagementClusterEntry 7  }
   
   
   coherenceManagementJMXAddressTable OBJECT-TYPE
      SYNTAX      SEQUENCE OF CoherenceManagementJMXAddressEntry
      MAX-ACCESS  not-accessible
      STATUS      current
      DESCRIPTION "This class holds the JMX connection information needed to connect to a management server.  Copyright (c) 2013, 2018, Oracle and/or its affiliates. All Rights Reserved."
      ::= { wls 1990  }
      
   
   coherenceManagementJMXAddressEntry OBJECT-TYPE
      SYNTAX      CoherenceManagementJMXAddressEntry
      MAX-ACCESS  not-accessible
      STATUS      current
      DESCRIPTION "Generated SNMP Table Entry."
      INDEX { coherenceManagementJMXAddressIndex}
      ::= { coherenceManagementJMXAddressTable 1 }
      
   CoherenceManagementJMXAddressEntry ::=
      SEQUENCE
      {
         coherenceManagementJMXAddressIndex OCTET STRING,
         coherenceManagementJMXAddressObjectName OCTET STRING,
         coherenceManagementJMXAddressType OCTET STRING,
         coherenceManagementJMXAddressName OCTET STRING,
         coherenceManagementJMXAddressUsername OCTET STRING,
         coherenceManagementJMXAddressAddress OCTET STRING,
         coherenceManagementJMXAddressRegistryPort Integer32,
         coherenceManagementJMXAddressConnectionPort Integer32
      }
      
   
   coherenceManagementJMXAddressIndex OBJECT-TYPE
      SYNTAX      OCTET STRING
      MAX-ACCESS  not-accessible
      STATUS      current
      DESCRIPTION "Index column"
      ::= { coherenceManagementJMXAddressEntry 1  }
   
   
   coherenceManagementJMXAddressObjectName OBJECT-TYPE
      SYNTAX      OCTET STRING
      MAX-ACCESS  read-only
      STATUS      current
      DESCRIPTION "ObjectName column"
      ::= { coherenceManagementJMXAddressEntry 2  }
   
   
   coherenceManagementJMXAddressType OBJECT-TYPE
      SYNTAX      OCTET STRING
      MAX-ACCESS  read-only
      STATUS      current
      DESCRIPTION "Returns the type of the MBean."
      ::= { coherenceManagementJMXAddressEntry 3  }
   
   
   coherenceManagementJMXAddressName OBJECT-TYPE
      SYNTAX      OCTET STRING
      MAX-ACCESS  read-only
      STATUS      current
      DESCRIPTION "The user-specified name of this MBean instance.  This name is included as one of the key properties in the MBean's javax.management.ObjectName: Name=user-specified-name"
      ::= { coherenceManagementJMXAddressEntry 4  }
   
   
   coherenceManagementJMXAddressUsername OBJECT-TYPE
      SYNTAX      OCTET STRING
      MAX-ACCESS  read-only
      STATUS      current
      DESCRIPTION "Get the JMX connection username"
      ::= { coherenceManagementJMXAddressEntry 5  }
   
   
   coherenceManagementJMXAddressAddress OBJECT-TYPE
      SYNTAX      OCTET STRING
      MAX-ACCESS  read-only
      STATUS      current
      DESCRIPTION "The IP address/Host"
      ::= { coherenceManagementJMXAddressEntry 6  }
   
   
   coherenceManagementJMXAddressRegistryPort OBJECT-TYPE
      SYNTAX      Integer32
      MAX-ACCESS  read-only
      STATUS      current
      DESCRIPTION "Get the JMX RMI registry port"
      ::= { coherenceManagementJMXAddressEntry 7  }
   
   
   coherenceManagementJMXAddressConnectionPort OBJECT-TYPE
      SYNTAX      Integer32
      MAX-ACCESS  read-only
      STATUS      current
      DESCRIPTION "Get the JMX RMI connection port"
      ::= { coherenceManagementJMXAddressEntry 8  }
   
   
   coherenceClusterMetricsRuntimeTable OBJECT-TYPE
      SYNTAX      SEQUENCE OF CoherenceClusterMetricsRuntimeEntry
      MAX-ACCESS  not-accessible
      STATUS      current
      DESCRIPTION "A CoherenceClusterRuntimeMetricsMBean gathers metrics from nodes in the cluster according to the specified report group xml file, and then provides a way to query for subsets of the group file by nodes and by table name, which refers to individual file names within the report group file. "
      ::= { wls 1995  }
      
   
   coherenceClusterMetricsRuntimeEntry OBJECT-TYPE
      SYNTAX      CoherenceClusterMetricsRuntimeEntry
      MAX-ACCESS  not-accessible
      STATUS      current
      DESCRIPTION "Generated SNMP Table Entry."
      INDEX { coherenceClusterMetricsRuntimeIndex}
      ::= { coherenceClusterMetricsRuntimeTable 1 }
      
   CoherenceClusterMetricsRuntimeEntry ::=
      SEQUENCE
      {
         coherenceClusterMetricsRuntimeIndex OCTET STRING,
         coherenceClusterMetricsRuntimeObjectName OCTET STRING,
         coherenceClusterMetricsRuntimeType OCTET STRING,
         coherenceClusterMetricsRuntimeInstances OCTET STRING,
         coherenceClusterMetricsRuntimeName OCTET STRING,
         coherenceClusterMetricsRuntimeReportGroupFile OCTET STRING
      }
      
   
   coherenceClusterMetricsRuntimeIndex OBJECT-TYPE
      SYNTAX      OCTET STRING
      MAX-ACCESS  not-accessible
      STATUS      current
      DESCRIPTION "Index column"
      ::= { coherenceClusterMetricsRuntimeEntry 1  }
   
   
   coherenceClusterMetricsRuntimeObjectName OBJECT-TYPE
      SYNTAX      OCTET STRING
      MAX-ACCESS  read-only
      STATUS      current
      DESCRIPTION "ObjectName column"
      ::= { coherenceClusterMetricsRuntimeEntry 2  }
   
   
   coherenceClusterMetricsRuntimeType OBJECT-TYPE
      SYNTAX      OCTET STRING
      MAX-ACCESS  read-only
      STATUS      current
      DESCRIPTION "Returns the type of the MBean. "
      ::= { coherenceClusterMetricsRuntimeEntry 3  }
   
   
   coherenceClusterMetricsRuntimeInstances OBJECT-TYPE
      SYNTAX      OCTET STRING
      MAX-ACCESS  read-only
      STATUS      current
      DESCRIPTION "Get the Management nodes names. "
      ::= { coherenceClusterMetricsRuntimeEntry 4  }
   
   
   coherenceClusterMetricsRuntimeName OBJECT-TYPE
      SYNTAX      OCTET STRING
      MAX-ACCESS  read-only
      STATUS      current
      DESCRIPTION "The name of this configuration. WebLogic Server uses an MBean to implement and persist the configuration. "
      ::= { coherenceClusterMetricsRuntimeEntry 5  }
   
   
   coherenceClusterMetricsRuntimeReportGroupFile OBJECT-TYPE
      SYNTAX      OCTET STRING
      MAX-ACCESS  read-only
      STATUS      current
      DESCRIPTION "The report group file representing the superset of metrics this bean will gather "
      ::= { coherenceClusterMetricsRuntimeEntry 6  }
   
   
   coherenceMetricsRuntimeTable OBJECT-TYPE
      SYNTAX      SEQUENCE OF CoherenceMetricsRuntimeEntry
      MAX-ACCESS  not-accessible
      STATUS      current
      DESCRIPTION "A CoherenceMetricsRuntimeMBean holds all CoherenceClusterRuntimeMetricsMBeans, which represent clusters that can be monitored.  Copyright (c) 2013 Oracle and/or its affiliates. All Rights Reserved."
      ::= { wls 2000  }
      
   
   coherenceMetricsRuntimeEntry OBJECT-TYPE
      SYNTAX      CoherenceMetricsRuntimeEntry
      MAX-ACCESS  not-accessible
      STATUS      current
      DESCRIPTION "Generated SNMP Table Entry."
      INDEX { coherenceMetricsRuntimeIndex}
      ::= { coherenceMetricsRuntimeTable 1 }
      
   CoherenceMetricsRuntimeEntry ::=
      SEQUENCE
      {
         coherenceMetricsRuntimeIndex OCTET STRING,
         coherenceMetricsRuntimeObjectName OCTET STRING,
         coherenceMetricsRuntimeType OCTET STRING,
         coherenceMetricsRuntimeName OCTET STRING
      }
      
   
   coherenceMetricsRuntimeIndex OBJECT-TYPE
      SYNTAX      OCTET STRING
      MAX-ACCESS  not-accessible
      STATUS      current
      DESCRIPTION "Index column"
      ::= { coherenceMetricsRuntimeEntry 1  }
   
   
   coherenceMetricsRuntimeObjectName OBJECT-TYPE
      SYNTAX      OCTET STRING
      MAX-ACCESS  read-only
      STATUS      current
      DESCRIPTION "ObjectName column"
      ::= { coherenceMetricsRuntimeEntry 2  }
   
   
   coherenceMetricsRuntimeType OBJECT-TYPE
      SYNTAX      OCTET STRING
      MAX-ACCESS  read-only
      STATUS      current
      DESCRIPTION "Returns the type of the MBean."
      ::= { coherenceMetricsRuntimeEntry 3  }
   
   
   coherenceMetricsRuntimeName OBJECT-TYPE
      SYNTAX      OCTET STRING
      MAX-ACCESS  read-only
      STATUS      current
      DESCRIPTION "The name of this configuration. WebLogic Server uses an MBean to implement and persist the configuration."
      ::= { coherenceMetricsRuntimeEntry 4  }
   
   
   wtcStatisticsRuntimeTable OBJECT-TYPE
      SYNTAX      SEQUENCE OF WtcStatisticsRuntimeEntry
      MAX-ACCESS  not-accessible
      STATUS      current
      DESCRIPTION "This class is used to:  query statistics of WTC connections. query statistics of WTC imported and exported services.  "
      ::= { wls 2005  }
      
   
   wtcStatisticsRuntimeEntry OBJECT-TYPE
      SYNTAX      WtcStatisticsRuntimeEntry
      MAX-ACCESS  not-accessible
      STATUS      current
      DESCRIPTION "Generated SNMP Table Entry."
      INDEX { wtcStatisticsRuntimeIndex}
      ::= { wtcStatisticsRuntimeTable 1 }
      
   WtcStatisticsRuntimeEntry ::=
      SEQUENCE
      {
         wtcStatisticsRuntimeIndex OCTET STRING,
         wtcStatisticsRuntimeObjectName OCTET STRING,
         wtcStatisticsRuntimeType OCTET STRING,
         wtcStatisticsRuntimeName OCTET STRING
      }
      
   
   wtcStatisticsRuntimeIndex OBJECT-TYPE
      SYNTAX      OCTET STRING
      MAX-ACCESS  not-accessible
      STATUS      current
      DESCRIPTION "Index column"
      ::= { wtcStatisticsRuntimeEntry 1  }
   
   
   wtcStatisticsRuntimeObjectName OBJECT-TYPE
      SYNTAX      OCTET STRING
      MAX-ACCESS  read-only
      STATUS      current
      DESCRIPTION "ObjectName column"
      ::= { wtcStatisticsRuntimeEntry 2  }
   
   
   wtcStatisticsRuntimeType OBJECT-TYPE
      SYNTAX      OCTET STRING
      MAX-ACCESS  read-only
      STATUS      current
      DESCRIPTION "Returns the type of the MBean. "
      ::= { wtcStatisticsRuntimeEntry 3  }
   
   
   wtcStatisticsRuntimeName OBJECT-TYPE
      SYNTAX      OCTET STRING
      MAX-ACCESS  read-only
      STATUS      current
      DESCRIPTION "The name of this configuration. WebLogic Server uses an MBean to implement and persist the configuration. "
      ::= { wtcStatisticsRuntimeEntry 4  }
   
   
   batchConfigTable OBJECT-TYPE
      SYNTAX      SEQUENCE OF BatchConfigEntry
      MAX-ACCESS  not-accessible
      STATUS      current
      DESCRIPTION "This class represents the configuration for Batch Runtime. "
      ::= { wls 2010  }
      
   
   batchConfigEntry OBJECT-TYPE
      SYNTAX      BatchConfigEntry
      MAX-ACCESS  not-accessible
      STATUS      current
      DESCRIPTION "Generated SNMP Table Entry."
      INDEX { batchConfigIndex}
      ::= { batchConfigTable 1 }
      
   BatchConfigEntry ::=
      SEQUENCE
      {
         batchConfigIndex     OCTET STRING,
         batchConfigObjectName OCTET STRING,
         batchConfigName      OCTET STRING,
         batchConfigType      OCTET STRING,
         batchConfigSchemaName OCTET STRING,
         batchConfigTags      OCTET STRING
      }
      
   
   batchConfigIndex OBJECT-TYPE
      SYNTAX      OCTET STRING
      MAX-ACCESS  not-accessible
      STATUS      current
      DESCRIPTION "Index column"
      ::= { batchConfigEntry 1  }
   
   
   batchConfigObjectName OBJECT-TYPE
      SYNTAX      OCTET STRING
      MAX-ACCESS  read-only
      STATUS      current
      DESCRIPTION "ObjectName column"
      ::= { batchConfigEntry 2  }
   
   
   batchConfigName OBJECT-TYPE
      SYNTAX      OCTET STRING
      MAX-ACCESS  read-only
      STATUS      current
      DESCRIPTION "The user-specified name of this MBean instance.  This name is included as one of the key properties in the MBean's javax.management.ObjectName:  Name=user-specified-name "
      ::= { batchConfigEntry 3  }
   
   
   batchConfigType OBJECT-TYPE
      SYNTAX      OCTET STRING
      MAX-ACCESS  read-only
      STATUS      current
      DESCRIPTION "Returns the type of the MBean. "
      ::= { batchConfigEntry 4  }
   
   
   batchConfigSchemaName OBJECT-TYPE
      SYNTAX      OCTET STRING
      MAX-ACCESS  read-only
      STATUS      current
      DESCRIPTION "The schema name where the JobRepository tables have been created. Note that if the JobRepository data source is shared by applications, then this schema name must be the same name that the application expects. "
      ::= { batchConfigEntry 5  }
   
   
   batchConfigTags OBJECT-TYPE
      SYNTAX      OCTET STRING
      MAX-ACCESS  read-only
      STATUS      current
      DESCRIPTION "Return all tags on this Configuration MBean "
      ::= { batchConfigEntry 6  }
   
   
   cdiContainerTable OBJECT-TYPE
      SYNTAX      SEQUENCE OF CdiContainerEntry
      MAX-ACCESS  not-accessible
      STATUS      current
      DESCRIPTION "This MBean is used to specify domain-wide defaults for the CDI container "
      ::= { wls 2015  }
      
   
   cdiContainerEntry OBJECT-TYPE
      SYNTAX      CdiContainerEntry
      MAX-ACCESS  not-accessible
      STATUS      current
      DESCRIPTION "Generated SNMP Table Entry."
      INDEX { cdiContainerIndex}
      ::= { cdiContainerTable 1 }
      
   CdiContainerEntry ::=
      SEQUENCE
      {
         cdiContainerIndex    OCTET STRING,
         cdiContainerObjectName OCTET STRING,
         cdiContainerImplicitBeanDiscoveryEnabled OCTET STRING,
         cdiContainerName     OCTET STRING,
         cdiContainerType     OCTET STRING,
         cdiContainerTags     OCTET STRING,
         cdiContainerPolicy   OCTET STRING
      }
      
   
   cdiContainerIndex OBJECT-TYPE
      SYNTAX      OCTET STRING
      MAX-ACCESS  not-accessible
      STATUS      current
      DESCRIPTION "Index column"
      ::= { cdiContainerEntry 1  }
   
   
   cdiContainerObjectName OBJECT-TYPE
      SYNTAX      OCTET STRING
      MAX-ACCESS  read-only
      STATUS      current
      DESCRIPTION "ObjectName column"
      ::= { cdiContainerEntry 2  }
   
   
   cdiContainerImplicitBeanDiscoveryEnabled OBJECT-TYPE
      SYNTAX      OCTET STRING
      MAX-ACCESS  read-only
      STATUS      current
      DESCRIPTION "This flag may be used to limit implicit Bean discovery "
      ::= { cdiContainerEntry 3  }
   
   
   cdiContainerName OBJECT-TYPE
      SYNTAX      OCTET STRING
      MAX-ACCESS  read-only
      STATUS      current
      DESCRIPTION "The user-specified name of this MBean instance.  This name is included as one of the key properties in the MBean's javax.management.ObjectName:  Name=user-specified-name "
      ::= { cdiContainerEntry 4  }
   
   
   cdiContainerType OBJECT-TYPE
      SYNTAX      OCTET STRING
      MAX-ACCESS  read-only
      STATUS      current
      DESCRIPTION "Returns the type of the MBean. "
      ::= { cdiContainerEntry 5  }
   
   
   cdiContainerTags OBJECT-TYPE
      SYNTAX      OCTET STRING
      MAX-ACCESS  read-only
      STATUS      current
      DESCRIPTION "Return all tags on this Configuration MBean "
      ::= { cdiContainerEntry 6  }
   
   
   cdiContainerPolicy OBJECT-TYPE
      SYNTAX      OCTET STRING
      MAX-ACCESS  read-only
      STATUS      current
      DESCRIPTION "Indicates the CDI policy.  CDI can be 'Enabled' (the default) or 'Disabled'. If CDI is disabled then no CDI processing will occur including scanning of pojos and initialization of Weld and CDI will not be available to the application via the CDI apis.   "
      ::= { cdiContainerEntry 7  }
   
   
   coherenceManagementAddressProviderTable OBJECT-TYPE
      SYNTAX      SEQUENCE OF CoherenceManagementAddressProviderEntry
      MAX-ACCESS  not-accessible
      STATUS      current
      DESCRIPTION "This class holds the connection information needed to connect to a Coherence server.  Copyright (c) 2014,2015, Oracle and/or its affiliates. All Rights Reserved. "
      ::= { wls 2020  }
      
   
   coherenceManagementAddressProviderEntry OBJECT-TYPE
      SYNTAX      CoherenceManagementAddressProviderEntry
      MAX-ACCESS  not-accessible
      STATUS      current
      DESCRIPTION "Generated SNMP Table Entry."
      INDEX { coherenceManagementAddressProviderIndex}
      ::= { coherenceManagementAddressProviderTable 1 }
      
   CoherenceManagementAddressProviderEntry ::=
      SEQUENCE
      {
         coherenceManagementAddressProviderIndex OCTET STRING,
         coherenceManagementAddressProviderObjectName OCTET STRING,
         coherenceManagementAddressProviderAddress OCTET STRING,
         coherenceManagementAddressProviderPort Integer32,
         coherenceManagementAddressProviderName OCTET STRING,
         coherenceManagementAddressProviderType OCTET STRING,
         coherenceManagementAddressProviderTags OCTET STRING
      }
      
   
   coherenceManagementAddressProviderIndex OBJECT-TYPE
      SYNTAX      OCTET STRING
      MAX-ACCESS  not-accessible
      STATUS      current
      DESCRIPTION "Index column"
      ::= { coherenceManagementAddressProviderEntry 1  }
   
   
   coherenceManagementAddressProviderObjectName OBJECT-TYPE
      SYNTAX      OCTET STRING
      MAX-ACCESS  read-only
      STATUS      current
      DESCRIPTION "ObjectName column"
      ::= { coherenceManagementAddressProviderEntry 2  }
   
   
   coherenceManagementAddressProviderAddress OBJECT-TYPE
      SYNTAX      OCTET STRING
      MAX-ACCESS  read-only
      STATUS      current
      DESCRIPTION "The IP address/Host "
      ::= { coherenceManagementAddressProviderEntry 3  }
   
   
   coherenceManagementAddressProviderPort OBJECT-TYPE
      SYNTAX      Integer32
      MAX-ACCESS  read-only
      STATUS      current
      DESCRIPTION "Return the server port "
      ::= { coherenceManagementAddressProviderEntry 4  }
   
   
   coherenceManagementAddressProviderName OBJECT-TYPE
      SYNTAX      OCTET STRING
      MAX-ACCESS  read-only
      STATUS      current
      DESCRIPTION "The user-specified name of this MBean instance.  This name is included as one of the key properties in the MBean's javax.management.ObjectName:  Name=user-specified-name "
      ::= { coherenceManagementAddressProviderEntry 5  }
   
   
   coherenceManagementAddressProviderType OBJECT-TYPE
      SYNTAX      OCTET STRING
      MAX-ACCESS  read-only
      STATUS      current
      DESCRIPTION "Returns the type of the MBean. "
      ::= { coherenceManagementAddressProviderEntry 6  }
   
   
   coherenceManagementAddressProviderTags OBJECT-TYPE
      SYNTAX      OCTET STRING
      MAX-ACCESS  read-only
      STATUS      current
      DESCRIPTION "Return all tags on this Configuration MBean "
      ::= { coherenceManagementAddressProviderEntry 7  }
   
   
   coherencePartitionCacheConfigTable OBJECT-TYPE
      SYNTAX      SEQUENCE OF CoherencePartitionCacheConfigEntry
      MAX-ACCESS  not-accessible
      STATUS      current
      DESCRIPTION "The CoherencePartitionCacheConfigMBean is used to define which Coherence caches are shared/not-shared in an MT environment as well as specific cache properties that apply to deployments underneath a partition.  Note: the Name attribute is inherited from ConfigurationMBean and is a key only. "
      ::= { wls 2025  }
      
   
   coherencePartitionCacheConfigEntry OBJECT-TYPE
      SYNTAX      CoherencePartitionCacheConfigEntry
      MAX-ACCESS  not-accessible
      STATUS      current
      DESCRIPTION "Generated SNMP Table Entry."
      INDEX { coherencePartitionCacheConfigIndex}
      ::= { coherencePartitionCacheConfigTable 1 }
      
   CoherencePartitionCacheConfigEntry ::=
      SEQUENCE
      {
         coherencePartitionCacheConfigIndex OCTET STRING,
         coherencePartitionCacheConfigObjectName OCTET STRING,
         coherencePartitionCacheConfigApplicationName OCTET STRING,
         coherencePartitionCacheConfigShared OCTET STRING,
         coherencePartitionCacheConfigName OCTET STRING,
         coherencePartitionCacheConfigType OCTET STRING,
         coherencePartitionCacheConfigCacheName OCTET STRING,
         coherencePartitionCacheConfigTags OCTET STRING
      }
      
   
   coherencePartitionCacheConfigIndex OBJECT-TYPE
      SYNTAX      OCTET STRING
      MAX-ACCESS  not-accessible
      STATUS      current
      DESCRIPTION "Index column"
      ::= { coherencePartitionCacheConfigEntry 1  }
   
   
   coherencePartitionCacheConfigObjectName OBJECT-TYPE
      SYNTAX      OCTET STRING
      MAX-ACCESS  read-only
      STATUS      current
      DESCRIPTION "ObjectName column"
      ::= { coherencePartitionCacheConfigEntry 2  }
   
   
   coherencePartitionCacheConfigApplicationName OBJECT-TYPE
      SYNTAX      OCTET STRING
      MAX-ACCESS  read-only
      STATUS      current
      DESCRIPTION "The name of the GAR application that this setting should apply to. "
      ::= { coherencePartitionCacheConfigEntry 3  }
   
   
   coherencePartitionCacheConfigShared OBJECT-TYPE
      SYNTAX      OCTET STRING
      MAX-ACCESS  read-only
      STATUS      current
      DESCRIPTION "Specifies whether you want this cache to be shared. "
      ::= { coherencePartitionCacheConfigEntry 4  }
   
   
   coherencePartitionCacheConfigName OBJECT-TYPE
      SYNTAX      OCTET STRING
      MAX-ACCESS  read-only
      STATUS      current
      DESCRIPTION "The user-specified name of this MBean instance.  This name is included as one of the key properties in the MBean's javax.management.ObjectName:  Name=user-specified-name "
      ::= { coherencePartitionCacheConfigEntry 5  }
   
   
   coherencePartitionCacheConfigType OBJECT-TYPE
      SYNTAX      OCTET STRING
      MAX-ACCESS  read-only
      STATUS      current
      DESCRIPTION "Returns the type of the MBean. "
      ::= { coherencePartitionCacheConfigEntry 6  }
   
   
   coherencePartitionCacheConfigCacheName OBJECT-TYPE
      SYNTAX      OCTET STRING
      MAX-ACCESS  read-only
      STATUS      current
      DESCRIPTION "The name of the cache that the settings should apply to. "
      ::= { coherencePartitionCacheConfigEntry 7  }
   
   
   coherencePartitionCacheConfigTags OBJECT-TYPE
      SYNTAX      OCTET STRING
      MAX-ACCESS  read-only
      STATUS      current
      DESCRIPTION "Return all tags on this Configuration MBean "
      ::= { coherencePartitionCacheConfigEntry 8  }
   
   
   coherencePartitionCachePropertyTable OBJECT-TYPE
      SYNTAX      SEQUENCE OF CoherencePartitionCachePropertyEntry
      MAX-ACCESS  not-accessible
      STATUS      current
      DESCRIPTION "The CoherencePartitionCachePropertyMBean is used to define specific properties, name and value that apply to a CoherenceMTCacheConfigMBean.  Note: the Name attribute is inherited from ConfigurationMBean. "
      ::= { wls 2030  }
      
   
   coherencePartitionCachePropertyEntry OBJECT-TYPE
      SYNTAX      CoherencePartitionCachePropertyEntry
      MAX-ACCESS  not-accessible
      STATUS      current
      DESCRIPTION "Generated SNMP Table Entry."
      INDEX { coherencePartitionCachePropertyIndex}
      ::= { coherencePartitionCachePropertyTable 1 }
      
   CoherencePartitionCachePropertyEntry ::=
      SEQUENCE
      {
         coherencePartitionCachePropertyIndex OCTET STRING,
         coherencePartitionCachePropertyObjectName OCTET STRING,
         coherencePartitionCachePropertyName OCTET STRING,
         coherencePartitionCachePropertyType OCTET STRING,
         coherencePartitionCachePropertyValue OCTET STRING,
         coherencePartitionCachePropertyTags OCTET STRING
      }
      
   
   coherencePartitionCachePropertyIndex OBJECT-TYPE
      SYNTAX      OCTET STRING
      MAX-ACCESS  not-accessible
      STATUS      current
      DESCRIPTION "Index column"
      ::= { coherencePartitionCachePropertyEntry 1  }
   
   
   coherencePartitionCachePropertyObjectName OBJECT-TYPE
      SYNTAX      OCTET STRING
      MAX-ACCESS  read-only
      STATUS      current
      DESCRIPTION "ObjectName column"
      ::= { coherencePartitionCachePropertyEntry 2  }
   
   
   coherencePartitionCachePropertyName OBJECT-TYPE
      SYNTAX      OCTET STRING
      MAX-ACCESS  read-only
      STATUS      current
      DESCRIPTION "The user-specified name of this MBean instance.  This name is included as one of the key properties in the MBean's javax.management.ObjectName:  Name=user-specified-name "
      ::= { coherencePartitionCachePropertyEntry 3  }
   
   
   coherencePartitionCachePropertyType OBJECT-TYPE
      SYNTAX      OCTET STRING
      MAX-ACCESS  read-only
      STATUS      current
      DESCRIPTION "Returns the type of the MBean. "
      ::= { coherencePartitionCachePropertyEntry 4  }
   
   
   coherencePartitionCachePropertyValue OBJECT-TYPE
      SYNTAX      OCTET STRING
      MAX-ACCESS  read-only
      STATUS      current
      DESCRIPTION "Get the value of the parameter "
      ::= { coherencePartitionCachePropertyEntry 5  }
   
   
   coherencePartitionCachePropertyTags OBJECT-TYPE
      SYNTAX      OCTET STRING
      MAX-ACCESS  read-only
      STATUS      current
      DESCRIPTION "Return all tags on this Configuration MBean "
      ::= { coherencePartitionCachePropertyEntry 6  }
   
   
   cpuUtilizationTable OBJECT-TYPE
      SYNTAX      SEQUENCE OF CpuUtilizationEntry
      MAX-ACCESS  not-accessible
      STATUS      current
      DESCRIPTION " A {@code CpuUtilizationMBean} represents a resource consumption management policy for the 'CPU Utilization' resource type.   The 'CPU Utilization' resource type tracks the percentage of CPU time utilized by a Domain Partition with respect to the available CPU time to the Server runtime.   Triggers (Usage limits) and Fair share policies can be defined for a 'CPU Utilization' resource type through this MBean.   The valid set of recourse action types for the 'CPU Utilization' resource type are:   notify slow shutdown   The trigger value must be in the range [0..100]%.  "
      ::= { wls 2035  }
      
   
   cpuUtilizationEntry OBJECT-TYPE
      SYNTAX      CpuUtilizationEntry
      MAX-ACCESS  not-accessible
      STATUS      current
      DESCRIPTION "Generated SNMP Table Entry."
      INDEX { cpuUtilizationIndex}
      ::= { cpuUtilizationTable 1 }
      
   CpuUtilizationEntry ::=
      SEQUENCE
      {
         cpuUtilizationIndex  OCTET STRING,
         cpuUtilizationObjectName OCTET STRING,
         cpuUtilizationName   OCTET STRING,
         cpuUtilizationType   OCTET STRING,
         cpuUtilizationTags   OCTET STRING
      }
      
   
   cpuUtilizationIndex OBJECT-TYPE
      SYNTAX      OCTET STRING
      MAX-ACCESS  not-accessible
      STATUS      current
      DESCRIPTION "Index column"
      ::= { cpuUtilizationEntry 1  }
   
   
   cpuUtilizationObjectName OBJECT-TYPE
      SYNTAX      OCTET STRING
      MAX-ACCESS  read-only
      STATUS      current
      DESCRIPTION "ObjectName column"
      ::= { cpuUtilizationEntry 2  }
   
   
   cpuUtilizationName OBJECT-TYPE
      SYNTAX      OCTET STRING
      MAX-ACCESS  read-only
      STATUS      current
      DESCRIPTION "The user-specified name of this MBean instance.  This name is included as one of the key properties in the MBean's javax.management.ObjectName:  Name=user-specified-name "
      ::= { cpuUtilizationEntry 3  }
   
   
   cpuUtilizationType OBJECT-TYPE
      SYNTAX      OCTET STRING
      MAX-ACCESS  read-only
      STATUS      current
      DESCRIPTION "Returns the type of the MBean. "
      ::= { cpuUtilizationEntry 4  }
   
   
   cpuUtilizationTags OBJECT-TYPE
      SYNTAX      OCTET STRING
      MAX-ACCESS  read-only
      STATUS      current
      DESCRIPTION "Return all tags on this Configuration MBean "
      ::= { cpuUtilizationEntry 5  }
   
   
   dataSourcePartitionTable OBJECT-TYPE
      SYNTAX      SEQUENCE OF DataSourcePartitionEntry
      MAX-ACCESS  not-accessible
      STATUS      current
      DESCRIPTION "This interface provides access to the DataSourcePartition configuration attributes.  The methods defined herein are applicable for DataSource configuration at the partition level. "
      ::= { wls 2040  }
      
   
   dataSourcePartitionEntry OBJECT-TYPE
      SYNTAX      DataSourcePartitionEntry
      MAX-ACCESS  not-accessible
      STATUS      current
      DESCRIPTION "Generated SNMP Table Entry."
      INDEX { dataSourcePartitionIndex}
      ::= { dataSourcePartitionTable 1 }
      
   DataSourcePartitionEntry ::=
      SEQUENCE
      {
         dataSourcePartitionIndex OCTET STRING,
         dataSourcePartitionObjectName OCTET STRING,
         dataSourcePartitionName OCTET STRING,
         dataSourcePartitionType OCTET STRING,
         dataSourcePartitionDefaultDatasource OCTET STRING,
         dataSourcePartitionTags OCTET STRING
      }
      
   
   dataSourcePartitionIndex OBJECT-TYPE
      SYNTAX      OCTET STRING
      MAX-ACCESS  not-accessible
      STATUS      current
      DESCRIPTION "Index column"
      ::= { dataSourcePartitionEntry 1  }
   
   
   dataSourcePartitionObjectName OBJECT-TYPE
      SYNTAX      OCTET STRING
      MAX-ACCESS  read-only
      STATUS      current
      DESCRIPTION "ObjectName column"
      ::= { dataSourcePartitionEntry 2  }
   
   
   dataSourcePartitionName OBJECT-TYPE
      SYNTAX      OCTET STRING
      MAX-ACCESS  read-only
      STATUS      current
      DESCRIPTION "The user-specified name of this MBean instance.  This name is included as one of the key properties in the MBean's javax.management.ObjectName:  Name=user-specified-name "
      ::= { dataSourcePartitionEntry 3  }
   
   
   dataSourcePartitionType OBJECT-TYPE
      SYNTAX      OCTET STRING
      MAX-ACCESS  read-only
      STATUS      current
      DESCRIPTION "Returns the type of the MBean. "
      ::= { dataSourcePartitionEntry 4  }
   
   
   dataSourcePartitionDefaultDatasource OBJECT-TYPE
      SYNTAX      OCTET STRING
      MAX-ACCESS  read-only
      STATUS      current
      DESCRIPTION "The JNDI name of a system resource data source used to override the default datasource. "
      ::= { dataSourcePartitionEntry 5  }
   
   
   dataSourcePartitionTags OBJECT-TYPE
      SYNTAX      OCTET STRING
      MAX-ACCESS  read-only
      STATUS      current
      DESCRIPTION "Return all tags on this Configuration MBean "
      ::= { dataSourcePartitionEntry 6  }
   
   
   datasourceInterceptorTable OBJECT-TYPE
      SYNTAX      SEQUENCE OF DatasourceInterceptorEntry
      MAX-ACCESS  not-accessible
      STATUS      current
      DESCRIPTION "This interface describes the configuration for a data source interceptor used to intercept the elastic scale up and scale down operations. "
      ::= { wls 2045  }
      
   
   datasourceInterceptorEntry OBJECT-TYPE
      SYNTAX      DatasourceInterceptorEntry
      MAX-ACCESS  not-accessible
      STATUS      current
      DESCRIPTION "Generated SNMP Table Entry."
      INDEX { datasourceInterceptorIndex}
      ::= { datasourceInterceptorTable 1 }
      
   DatasourceInterceptorEntry ::=
      SEQUENCE
      {
         datasourceInterceptorIndex OCTET STRING,
         datasourceInterceptorObjectName OCTET STRING,
         datasourceInterceptorInterceptorTypeName OCTET STRING,
         datasourceInterceptorConnectionUrlsPattern OCTET STRING,
         datasourceInterceptorPriority Integer32,
         datasourceInterceptorInterceptedOperationNames OCTET STRING,
         datasourceInterceptorName OCTET STRING,
         datasourceInterceptorInterceptedTargetKey OCTET STRING,
         datasourceInterceptorDependsOn OCTET STRING,
         datasourceInterceptorType OCTET STRING,
         datasourceInterceptorConnectionQuota Integer32,
         datasourceInterceptorTags OCTET STRING
      }
      
   
   datasourceInterceptorIndex OBJECT-TYPE
      SYNTAX      OCTET STRING
      MAX-ACCESS  not-accessible
      STATUS      current
      DESCRIPTION "Index column"
      ::= { datasourceInterceptorEntry 1  }
   
   
   datasourceInterceptorObjectName OBJECT-TYPE
      SYNTAX      OCTET STRING
      MAX-ACCESS  read-only
      STATUS      current
      DESCRIPTION "ObjectName column"
      ::= { datasourceInterceptorEntry 2  }
   
   
   datasourceInterceptorInterceptorTypeName OBJECT-TYPE
      SYNTAX      OCTET STRING
      MAX-ACCESS  read-only
      STATUS      current
      DESCRIPTION "The HK2 name of the interceptor class. "
      ::= { datasourceInterceptorEntry 3  }
   
   
   datasourceInterceptorConnectionUrlsPattern OBJECT-TYPE
      SYNTAX      OCTET STRING
      MAX-ACCESS  read-only
      STATUS      current
      DESCRIPTION "Returns the regex pattern for the connection urls. The url pattern may cover multiple databases in case such databases are actually running on the same database machine. "
      ::= { datasourceInterceptorEntry 4  }
   
   
   datasourceInterceptorPriority OBJECT-TYPE
      SYNTAX      Integer32
      MAX-ACCESS  read-only
      STATUS      current
      DESCRIPTION "The priority of this intercepted method in the interceptor chain. An interceptor with a higher priority will be executed earlier than an interceptor with a lower priority. Note:  1073741823 is actually Integer.MAX_VALUE / 2 as defined in InterceptorPriorities. "
      ::= { datasourceInterceptorEntry 5  }
   
   
   datasourceInterceptorInterceptedOperationNames OBJECT-TYPE
      SYNTAX      OCTET STRING
      MAX-ACCESS  read-only
      STATUS      current
      DESCRIPTION "The name of the operation / method that needs to intercepted by this interceptor's method. If the return value is null or '*' then all operations are intercepted by this interceptor. "
      ::= { datasourceInterceptorEntry 6  }
   
   
   datasourceInterceptorName OBJECT-TYPE
      SYNTAX      OCTET STRING
      MAX-ACCESS  read-only
      STATUS      current
      DESCRIPTION "The user-specified name of this MBean instance.  This name is included as one of the key properties in the MBean's javax.management.ObjectName:  Name=user-specified-name "
      ::= { datasourceInterceptorEntry 7  }
   
   
   datasourceInterceptorInterceptedTargetKey OBJECT-TYPE
      SYNTAX      OCTET STRING
      MAX-ACCESS  read-only
      STATUS      current
      DESCRIPTION " "
      ::= { datasourceInterceptorEntry 8  }
   
   
   datasourceInterceptorDependsOn OBJECT-TYPE
      SYNTAX      OCTET STRING
      MAX-ACCESS  read-only
      STATUS      current
      DESCRIPTION "The set of interceptor names this interceptor depends on. The specified interceptors will appear before this interceptor in the invocation chain. "
      ::= { datasourceInterceptorEntry 9  }
   
   
   datasourceInterceptorType OBJECT-TYPE
      SYNTAX      OCTET STRING
      MAX-ACCESS  read-only
      STATUS      current
      DESCRIPTION "Returns the type of the MBean. "
      ::= { datasourceInterceptorEntry 10  }
   
   
   datasourceInterceptorConnectionQuota OBJECT-TYPE
      SYNTAX      Integer32
      MAX-ACCESS  read-only
      STATUS      current
      DESCRIPTION " "
      ::= { datasourceInterceptorEntry 11  }
   
   
   datasourceInterceptorTags OBJECT-TYPE
      SYNTAX      OCTET STRING
      MAX-ACCESS  read-only
      STATUS      current
      DESCRIPTION "Return all tags on this Configuration MBean "
      ::= { datasourceInterceptorEntry 12  }
   
   
   debugPatchesTable OBJECT-TYPE
      SYNTAX      SEQUENCE OF DebugPatchesEntry
      MAX-ACCESS  not-accessible
      STATUS      current
      DESCRIPTION "Dynamic Debug patches configuration. "
      ::= { wls 2050  }
      
   
   debugPatchesEntry OBJECT-TYPE
      SYNTAX      DebugPatchesEntry
      MAX-ACCESS  not-accessible
      STATUS      current
      DESCRIPTION "Generated SNMP Table Entry."
      INDEX { debugPatchesIndex}
      ::= { debugPatchesTable 1 }
      
   DebugPatchesEntry ::=
      SEQUENCE
      {
         debugPatchesIndex    OCTET STRING,
         debugPatchesObjectName OCTET STRING,
         debugPatchesDebugPatchDirectory OCTET STRING,
         debugPatchesName     OCTET STRING,
         debugPatchesType     OCTET STRING,
         debugPatchesTags     OCTET STRING
      }
      
   
   debugPatchesIndex OBJECT-TYPE
      SYNTAX      OCTET STRING
      MAX-ACCESS  not-accessible
      STATUS      current
      DESCRIPTION "Index column"
      ::= { debugPatchesEntry 1  }
   
   
   debugPatchesObjectName OBJECT-TYPE
      SYNTAX      OCTET STRING
      MAX-ACCESS  read-only
      STATUS      current
      DESCRIPTION "ObjectName column"
      ::= { debugPatchesEntry 2  }
   
   
   debugPatchesDebugPatchDirectory OBJECT-TYPE
      SYNTAX      OCTET STRING
      MAX-ACCESS  read-only
      STATUS      current
      DESCRIPTION " "
      ::= { debugPatchesEntry 3  }
   
   
   debugPatchesName OBJECT-TYPE
      SYNTAX      OCTET STRING
      MAX-ACCESS  read-only
      STATUS      current
      DESCRIPTION "The user-specified name of this MBean instance.  This name is included as one of the key properties in the MBean's javax.management.ObjectName:  Name=user-specified-name "
      ::= { debugPatchesEntry 4  }
   
   
   debugPatchesType OBJECT-TYPE
      SYNTAX      OCTET STRING
      MAX-ACCESS  read-only
      STATUS      current
      DESCRIPTION "Returns the type of the MBean. "
      ::= { debugPatchesEntry 5  }
   
   
   debugPatchesTags OBJECT-TYPE
      SYNTAX      OCTET STRING
      MAX-ACCESS  read-only
      STATUS      current
      DESCRIPTION "Return all tags on this Configuration MBean "
      ::= { debugPatchesEntry 6  }
   
   
   fairShareConstraintTable OBJECT-TYPE
      SYNTAX      SEQUENCE OF FairShareConstraintEntry
      MAX-ACCESS  not-accessible
      STATUS      current
      DESCRIPTION "This mbean is used to configure a Fair Share based policy for a resource type. "
      ::= { wls 2055  }
      
   
   fairShareConstraintEntry OBJECT-TYPE
      SYNTAX      FairShareConstraintEntry
      MAX-ACCESS  not-accessible
      STATUS      current
      DESCRIPTION "Generated SNMP Table Entry."
      INDEX { fairShareConstraintIndex}
      ::= { fairShareConstraintTable 1 }
      
   FairShareConstraintEntry ::=
      SEQUENCE
      {
         fairShareConstraintIndex OCTET STRING,
         fairShareConstraintObjectName OCTET STRING,
         fairShareConstraintName OCTET STRING,
         fairShareConstraintType OCTET STRING,
         fairShareConstraintValue Integer32,
         fairShareConstraintTags OCTET STRING
      }
      
   
   fairShareConstraintIndex OBJECT-TYPE
      SYNTAX      OCTET STRING
      MAX-ACCESS  not-accessible
      STATUS      current
      DESCRIPTION "Index column"
      ::= { fairShareConstraintEntry 1  }
   
   
   fairShareConstraintObjectName OBJECT-TYPE
      SYNTAX      OCTET STRING
      MAX-ACCESS  read-only
      STATUS      current
      DESCRIPTION "ObjectName column"
      ::= { fairShareConstraintEntry 2  }
   
   
   fairShareConstraintName OBJECT-TYPE
      SYNTAX      OCTET STRING
      MAX-ACCESS  read-only
      STATUS      current
      DESCRIPTION "The user-specified name of this MBean instance.  This name is included as one of the key properties in the MBean's javax.management.ObjectName:  Name=user-specified-name "
      ::= { fairShareConstraintEntry 3  }
   
   
   fairShareConstraintType OBJECT-TYPE
      SYNTAX      OCTET STRING
      MAX-ACCESS  read-only
      STATUS      current
      DESCRIPTION "Returns the type of the MBean. "
      ::= { fairShareConstraintEntry 4  }
   
   
   fairShareConstraintValue OBJECT-TYPE
      SYNTAX      Integer32
      MAX-ACCESS  read-only
      STATUS      current
      DESCRIPTION "Gets the fair-share value associated with this resource type. "
      ::= { fairShareConstraintEntry 5  }
   
   
   fairShareConstraintTags OBJECT-TYPE
      SYNTAX      OCTET STRING
      MAX-ACCESS  read-only
      STATUS      current
      DESCRIPTION "Return all tags on this Configuration MBean "
      ::= { fairShareConstraintEntry 6  }
   
   
   fileOpenTable OBJECT-TYPE
      SYNTAX      SEQUENCE OF FileOpenEntry
      MAX-ACCESS  not-accessible
      STATUS      current
      DESCRIPTION " A {@code FileOpenMBean} represents a resource consumption management policy for the 'File Open' resource type.   The 'File open' resource type governs the number of open files. This includes files that have been opened through {@code java.io} ( {@code FileInputStream, FileOutputStream, RandomAccessFile} etc) and {@code java.nio} (NIO file channels) APIs.   Trigger (Usage limits) based policies can be defined for a 'File Open' resource type through this MBean.   The valid set of recourse action types for the 'File Open' resource type are:   notify slow shutdown fail  "
      ::= { wls 2060  }
      
   
   fileOpenEntry OBJECT-TYPE
      SYNTAX      FileOpenEntry
      MAX-ACCESS  not-accessible
      STATUS      current
      DESCRIPTION "Generated SNMP Table Entry."
      INDEX { fileOpenIndex}
      ::= { fileOpenTable 1 }
      
   FileOpenEntry ::=
      SEQUENCE
      {
         fileOpenIndex        OCTET STRING,
         fileOpenObjectName   OCTET STRING,
         fileOpenName         OCTET STRING,
         fileOpenType         OCTET STRING,
         fileOpenTags         OCTET STRING
      }
      
   
   fileOpenIndex OBJECT-TYPE
      SYNTAX      OCTET STRING
      MAX-ACCESS  not-accessible
      STATUS      current
      DESCRIPTION "Index column"
      ::= { fileOpenEntry 1  }
   
   
   fileOpenObjectName OBJECT-TYPE
      SYNTAX      OCTET STRING
      MAX-ACCESS  read-only
      STATUS      current
      DESCRIPTION "ObjectName column"
      ::= { fileOpenEntry 2  }
   
   
   fileOpenName OBJECT-TYPE
      SYNTAX      OCTET STRING
      MAX-ACCESS  read-only
      STATUS      current
      DESCRIPTION "The user-specified name of this MBean instance.  This name is included as one of the key properties in the MBean's javax.management.ObjectName:  Name=user-specified-name "
      ::= { fileOpenEntry 3  }
   
   
   fileOpenType OBJECT-TYPE
      SYNTAX      OCTET STRING
      MAX-ACCESS  read-only
      STATUS      current
      DESCRIPTION "Returns the type of the MBean. "
      ::= { fileOpenEntry 4  }
   
   
   fileOpenTags OBJECT-TYPE
      SYNTAX      OCTET STRING
      MAX-ACCESS  read-only
      STATUS      current
      DESCRIPTION "Return all tags on this Configuration MBean "
      ::= { fileOpenEntry 5  }
   
   
   foreignConnectionFactoryOverrideTable OBJECT-TYPE
      SYNTAX      SEQUENCE OF ForeignConnectionFactoryOverrideEntry
      MAX-ACCESS  not-accessible
      STATUS      current
      DESCRIPTION "For each configuration entity that supports per-partition-override via a MBean, we have two MBeans, the original configure MBean and the corresponding override MBean, that eventually determine the effective settings of the configured resource.  We mark an attribute of an override MBean 'dynamic true' even though the original configure MBean masks it 'dynamic false'. This is to make sure that the overriding settings take effect on partition restart. Otherwise a server restart is required.  Defines partition-specific overrides for the most commonly overridden attributes in a ForeignConnectionFactory MBean. It overrides some of the settings in a same-named ForeignConnectionFactory MBean instance in the same multi-tenant scope to which this override MBean belongs.  "
      ::= { wls 2065  }
      
   
   foreignConnectionFactoryOverrideEntry OBJECT-TYPE
      SYNTAX      ForeignConnectionFactoryOverrideEntry
      MAX-ACCESS  not-accessible
      STATUS      current
      DESCRIPTION "Generated SNMP Table Entry."
      INDEX { foreignConnectionFactoryOverrideIndex}
      ::= { foreignConnectionFactoryOverrideTable 1 }
      
   ForeignConnectionFactoryOverrideEntry ::=
      SEQUENCE
      {
         foreignConnectionFactoryOverrideIndex OCTET STRING,
         foreignConnectionFactoryOverrideObjectName OCTET STRING,
         foreignConnectionFactoryOverrideName OCTET STRING,
         foreignConnectionFactoryOverrideType OCTET STRING,
         foreignConnectionFactoryOverrideUsername OCTET STRING,
         foreignConnectionFactoryOverrideRemoteJNDIName OCTET STRING,
         foreignConnectionFactoryOverrideTags OCTET STRING
      }
      
   
   foreignConnectionFactoryOverrideIndex OBJECT-TYPE
      SYNTAX      OCTET STRING
      MAX-ACCESS  not-accessible
      STATUS      current
      DESCRIPTION "Index column"
      ::= { foreignConnectionFactoryOverrideEntry 1  }
   
   
   foreignConnectionFactoryOverrideObjectName OBJECT-TYPE
      SYNTAX      OCTET STRING
      MAX-ACCESS  read-only
      STATUS      current
      DESCRIPTION "ObjectName column"
      ::= { foreignConnectionFactoryOverrideEntry 2  }
   
   
   foreignConnectionFactoryOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { foreignConnectionFactoryOverrideEntry 3  }
   
   
   foreignConnectionFactoryOverrideType OBJECT-TYPE
      SYNTAX      OCTET STRING
      MAX-ACCESS  read-only
      STATUS      current
      DESCRIPTION "Returns the type of the MBean. "
      ::= { foreignConnectionFactoryOverrideEntry 4  }
   
   
   foreignConnectionFactoryOverrideUsername OBJECT-TYPE
      SYNTAX      OCTET STRING
      MAX-ACCESS  read-only
      STATUS      current
      DESCRIPTION "The user name that is passed when opening a connection to the remote server (represented by this foreign connection factory). "
      ::= { foreignConnectionFactoryOverrideEntry 5  }
   
   
   foreignConnectionFactoryOverrideRemoteJNDIName OBJECT-TYPE
      SYNTAX      OCTET STRING
      MAX-ACCESS  read-only
      STATUS      current
      DESCRIPTION "The name of the remote object that will be looked up in the remote JNDI directory. "
      ::= { foreignConnectionFactoryOverrideEntry 6  }
   
   
   foreignConnectionFactoryOverrideTags OBJECT-TYPE
      SYNTAX      OCTET STRING
      MAX-ACCESS  read-only
      STATUS      current
      DESCRIPTION "Return all tags on this Configuration MBean "
      ::= { foreignConnectionFactoryOverrideEntry 7  }
   
   
   foreignJNDILinkOverrideTable OBJECT-TYPE
      SYNTAX      SEQUENCE OF ForeignJNDILinkOverrideEntry
      MAX-ACCESS  not-accessible
      STATUS      current
      DESCRIPTION "Defines partition-specific overrides for the most commonly overridden attributes in a ForeignJNDILink MBean. It overrides some of the settings in a same-named ForeignJNDILink MBean instance in the same multi-tenant scope to which this override MBean belongs.  "
      ::= { wls 2070  }
      
   
   foreignJNDILinkOverrideEntry OBJECT-TYPE
      SYNTAX      ForeignJNDILinkOverrideEntry
      MAX-ACCESS  not-accessible
      STATUS      current
      DESCRIPTION "Generated SNMP Table Entry."
      INDEX { foreignJNDILinkOverrideIndex}
      ::= { foreignJNDILinkOverrideTable 1 }
      
   ForeignJNDILinkOverrideEntry ::=
      SEQUENCE
      {
         foreignJNDILinkOverrideIndex OCTET STRING,
         foreignJNDILinkOverrideObjectName OCTET STRING,
         foreignJNDILinkOverrideName OCTET STRING,
         foreignJNDILinkOverrideType OCTET STRING,
         foreignJNDILinkOverrideRemoteJNDIName OCTET STRING,
         foreignJNDILinkOverrideTags OCTET STRING,
         foreignJNDILinkOverrideLocalJNDIName OCTET STRING
      }
      
   
   foreignJNDILinkOverrideIndex OBJECT-TYPE
      SYNTAX      OCTET STRING
      MAX-ACCESS  not-accessible
      STATUS      current
      DESCRIPTION "Index column"
      ::= { foreignJNDILinkOverrideEntry 1  }
   
   
   foreignJNDILinkOverrideObjectName OBJECT-TYPE
      SYNTAX      OCTET STRING
      MAX-ACCESS  read-only
      STATUS      current
      DESCRIPTION "ObjectName column"
      ::= { foreignJNDILinkOverrideEntry 2  }
   
   
   foreignJNDILinkOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { foreignJNDILinkOverrideEntry 3  }
   
   
   foreignJNDILinkOverrideType OBJECT-TYPE
      SYNTAX      OCTET STRING
      MAX-ACCESS  read-only
      STATUS      current
      DESCRIPTION "Returns the type of the MBean. "
      ::= { foreignJNDILinkOverrideEntry 4  }
   
   
   foreignJNDILinkOverrideRemoteJNDIName OBJECT-TYPE
      SYNTAX      OCTET STRING
      MAX-ACCESS  read-only
      STATUS      current
      DESCRIPTION "The foreign JNDI name. "
      ::= { foreignJNDILinkOverrideEntry 5  }
   
   
   foreignJNDILinkOverrideTags OBJECT-TYPE
      SYNTAX      OCTET STRING
      MAX-ACCESS  read-only
      STATUS      current
      DESCRIPTION "Return all tags on this Configuration MBean "
      ::= { foreignJNDILinkOverrideEntry 6  }
   
   
   foreignJNDILinkOverrideLocalJNDIName OBJECT-TYPE
      SYNTAX      OCTET STRING
      MAX-ACCESS  read-only
      STATUS      current
      DESCRIPTION "The local JNDI name. "
      ::= { foreignJNDILinkOverrideEntry 7  }
   
   
   foreignJNDIProviderOverrideTable OBJECT-TYPE
      SYNTAX      SEQUENCE OF ForeignJNDIProviderOverrideEntry
      MAX-ACCESS  not-accessible
      STATUS      current
      DESCRIPTION "Defines partition-specific overrides for the most commonly overridden attributes in a ForeignJNDIProvider MBean. It overrides some of the settings in a same-named ForeignJNDIProvider MBean instance in the same multi-tenant scope to which this override MBean belongs.  "
      ::= { wls 2075  }
      
   
   foreignJNDIProviderOverrideEntry OBJECT-TYPE
      SYNTAX      ForeignJNDIProviderOverrideEntry
      MAX-ACCESS  not-accessible
      STATUS      current
      DESCRIPTION "Generated SNMP Table Entry."
      INDEX { foreignJNDIProviderOverrideIndex}
      ::= { foreignJNDIProviderOverrideTable 1 }
      
   ForeignJNDIProviderOverrideEntry ::=
      SEQUENCE
      {
         foreignJNDIProviderOverrideIndex OCTET STRING,
         foreignJNDIProviderOverrideObjectName OCTET STRING,
         foreignJNDIProviderOverrideUser OCTET STRING,
         foreignJNDIProviderOverrideProviderURL OCTET STRING,
         foreignJNDIProviderOverrideInitialContextFactory OCTET STRING,
         foreignJNDIProviderOverrideName OCTET STRING,
         foreignJNDIProviderOverrideType OCTET STRING,
         foreignJNDIProviderOverrideTags OCTET STRING
      }
      
   
   foreignJNDIProviderOverrideIndex OBJECT-TYPE
      SYNTAX      OCTET STRING
      MAX-ACCESS  not-accessible
      STATUS      current
      DESCRIPTION "Index column"
      ::= { foreignJNDIProviderOverrideEntry 1  }
   
   
   foreignJNDIProviderOverrideObjectName OBJECT-TYPE
      SYNTAX      OCTET STRING
      MAX-ACCESS  read-only
      STATUS      current
      DESCRIPTION "ObjectName column"
      ::= { foreignJNDIProviderOverrideEntry 2  }
   
   
   foreignJNDIProviderOverrideUser OBJECT-TYPE
      SYNTAX      OCTET STRING
      MAX-ACCESS  read-only
      STATUS      current
      DESCRIPTION "The remote server's user name. "
      ::= { foreignJNDIProviderOverrideEntry 3  }
   
   
   foreignJNDIProviderOverrideProviderURL OBJECT-TYPE
      SYNTAX      OCTET STRING
      MAX-ACCESS  read-only
      STATUS      current
      DESCRIPTION "The foreign JNDI provider URL. This value corresponds to the standard JNDI property, java.naming.provider.url. "
      ::= { foreignJNDIProviderOverrideEntry 4  }
   
   
   foreignJNDIProviderOverrideInitialContextFactory OBJECT-TYPE
      SYNTAX      OCTET STRING
      MAX-ACCESS  read-only
      STATUS      current
      DESCRIPTION "The initial context factory to use to connect. This class name depends on the JNDI provider and the vendor you are using. The value corresponds to the standard JNDI property, java.naming.factory.initial. "
      ::= { foreignJNDIProviderOverrideEntry 5  }
   
   
   foreignJNDIProviderOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { foreignJNDIProviderOverrideEntry 6  }
   
   
   foreignJNDIProviderOverrideType OBJECT-TYPE
      SYNTAX      OCTET STRING
      MAX-ACCESS  read-only
      STATUS      current
      DESCRIPTION "Returns the type of the MBean. "
      ::= { foreignJNDIProviderOverrideEntry 7  }
   
   
   foreignJNDIProviderOverrideTags OBJECT-TYPE
      SYNTAX      OCTET STRING
      MAX-ACCESS  read-only
      STATUS      current
      DESCRIPTION "Return all tags on this Configuration MBean "
      ::= { foreignJNDIProviderOverrideEntry 8  }
   
   
   foreignServerOverrideTable OBJECT-TYPE
      SYNTAX      SEQUENCE OF ForeignServerOverrideEntry
      MAX-ACCESS  not-accessible
      STATUS      current
      DESCRIPTION "For each configuration entity that supports per-partition-override via a MBean, we have two MBeans, the original configure MBean and the corresponding override MBean, that eventually determine the effective settings of the configured resource.  We mark an attribute of an override MBean 'dynamic true' even though the original configure MBean masks it 'dynamic false'. This is to make sure that the overriding settings take effect on partition restart. Otherwise a server restart is required.  Defines partition-specific overrides for the most commonly overridden attributes in a ForeignServer MBean. It overrides some of the settings in a same-named ForeignServer MBean instance in the same multi-tenant scope to which this override MBean belongs.  "
      ::= { wls 2080  }
      
   
   foreignServerOverrideEntry OBJECT-TYPE
      SYNTAX      ForeignServerOverrideEntry
      MAX-ACCESS  not-accessible
      STATUS      current
      DESCRIPTION "Generated SNMP Table Entry."
      INDEX { foreignServerOverrideIndex}
      ::= { foreignServerOverrideTable 1 }
      
   ForeignServerOverrideEntry ::=
      SEQUENCE
      {
         foreignServerOverrideIndex OCTET STRING,
         foreignServerOverrideObjectName OCTET STRING,
         foreignServerOverrideInitialContextFactory OCTET STRING,
         foreignServerOverrideName OCTET STRING,
         foreignServerOverrideType OCTET STRING,
         foreignServerOverrideConnectionURL OCTET STRING,
         foreignServerOverrideTags OCTET STRING
      }
      
   
   foreignServerOverrideIndex OBJECT-TYPE
      SYNTAX      OCTET STRING
      MAX-ACCESS  not-accessible
      STATUS      current
      DESCRIPTION "Index column"
      ::= { foreignServerOverrideEntry 1  }
   
   
   foreignServerOverrideObjectName OBJECT-TYPE
      SYNTAX      OCTET STRING
      MAX-ACCESS  read-only
      STATUS      current
      DESCRIPTION "ObjectName column"
      ::= { foreignServerOverrideEntry 2  }
   
   
   foreignServerOverrideInitialContextFactory OBJECT-TYPE
      SYNTAX      OCTET STRING
      MAX-ACCESS  read-only
      STATUS      current
      DESCRIPTION "The name of the class that must be instantiated to access the JNDI provider. This class name depends on the JNDI provider and the vendor that are being used.  This value corresponds to the standard JNDI property, java.naming.factory.initial.  Note: This value defaults to weblogic.jndi.WLInitialContextFactory, which is the correct value for WebLogic Server. "
      ::= { foreignServerOverrideEntry 3  }
   
   
   foreignServerOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { foreignServerOverrideEntry 4  }
   
   
   foreignServerOverrideType OBJECT-TYPE
      SYNTAX      OCTET STRING
      MAX-ACCESS  read-only
      STATUS      current
      DESCRIPTION "Returns the type of the MBean. "
      ::= { foreignServerOverrideEntry 5  }
   
   
   foreignServerOverrideConnectionURL OBJECT-TYPE
      SYNTAX      OCTET STRING
      MAX-ACCESS  read-only
      STATUS      current
      DESCRIPTION "The URL that WebLogic Server will use to contact the JNDI provider. The syntax of this URL depends on which JNDI provider is being used. For WebLogic JMS, leave this field blank if you are referencing WebLogic JMS objects within the same cluster.  This value corresponds to the standard JNDI property, java.naming.provider.url.  Note: If this value is not specified, look-ups will be performed on the JNDI server within the WebLogic Server instance where this connection factory is deployed. "
      ::= { foreignServerOverrideEntry 6  }
   
   
   foreignServerOverrideTags OBJECT-TYPE
      SYNTAX      OCTET STRING
      MAX-ACCESS  read-only
      STATUS      current
      DESCRIPTION "Return all tags on this Configuration MBean "
      ::= { foreignServerOverrideEntry 7  }
   
   
   gzipCompressionTable OBJECT-TYPE
      SYNTAX      SEQUENCE OF GzipCompressionEntry
      MAX-ACCESS  not-accessible
      STATUS      current
      DESCRIPTION " This MBean is used to specify domain-wide default values for GZIP compression support. In general, these properties can be overridden for a specific Web application (in the weblogic.xml file).  "
      ::= { wls 2085  }
      
   
   gzipCompressionEntry OBJECT-TYPE
      SYNTAX      GzipCompressionEntry
      MAX-ACCESS  not-accessible
      STATUS      current
      DESCRIPTION "Generated SNMP Table Entry."
      INDEX { gzipCompressionIndex}
      ::= { gzipCompressionTable 1 }
      
   GzipCompressionEntry ::=
      SEQUENCE
      {
         gzipCompressionIndex OCTET STRING,
         gzipCompressionObjectName OCTET STRING,
         gzipCompressionGzipCompressionContentType OCTET STRING,
         gzipCompressionGzipCompressionMinContentLength Counter64,
         gzipCompressionName  OCTET STRING,
         gzipCompressionType  OCTET STRING,
         gzipCompressionTags  OCTET STRING,
         gzipCompressionGzipCompressionEnabled OCTET STRING
      }
      
   
   gzipCompressionIndex OBJECT-TYPE
      SYNTAX      OCTET STRING
      MAX-ACCESS  not-accessible
      STATUS      current
      DESCRIPTION "Index column"
      ::= { gzipCompressionEntry 1  }
   
   
   gzipCompressionObjectName OBJECT-TYPE
      SYNTAX      OCTET STRING
      MAX-ACCESS  read-only
      STATUS      current
      DESCRIPTION "ObjectName column"
      ::= { gzipCompressionEntry 2  }
   
   
   gzipCompressionGzipCompressionContentType OBJECT-TYPE
      SYNTAX      OCTET STRING
      MAX-ACCESS  read-only
      STATUS      current
      DESCRIPTION " Returns the type of content to be included in compression.  "
      ::= { gzipCompressionEntry 3  }
   
   
   gzipCompressionGzipCompressionMinContentLength OBJECT-TYPE
      SYNTAX      Counter64
      MAX-ACCESS  read-only
      STATUS      current
      DESCRIPTION " Returns the minimum content length to trigger GZIP compression. This allows you to bypass small-sized resources where compression does not yield a great return and uses unnecessary CPU.  "
      ::= { gzipCompressionEntry 4  }
   
   
   gzipCompressionName OBJECT-TYPE
      SYNTAX      OCTET STRING
      MAX-ACCESS  read-only
      STATUS      current
      DESCRIPTION "The user-specified name of this MBean instance.  This name is included as one of the key properties in the MBean's javax.management.ObjectName:  Name=user-specified-name "
      ::= { gzipCompressionEntry 5  }
   
   
   gzipCompressionType OBJECT-TYPE
      SYNTAX      OCTET STRING
      MAX-ACCESS  read-only
      STATUS      current
      DESCRIPTION "Returns the type of the MBean. "
      ::= { gzipCompressionEntry 6  }
   
   
   gzipCompressionTags OBJECT-TYPE
      SYNTAX      OCTET STRING
      MAX-ACCESS  read-only
      STATUS      current
      DESCRIPTION "Return all tags on this Configuration MBean "
      ::= { gzipCompressionEntry 7  }
   
   
   gzipCompressionGzipCompressionEnabled OBJECT-TYPE
      SYNTAX      OCTET STRING
      MAX-ACCESS  read-only
      STATUS      current
      DESCRIPTION " This global property determines whether or not the container should provide GZIP compression.  "
      ::= { gzipCompressionEntry 8  }
   
   
   heapRetainedTable OBJECT-TYPE
      SYNTAX      SEQUENCE OF HeapRetainedEntry
      MAX-ACCESS  not-accessible
      STATUS      current
      DESCRIPTION " A {@code HeapRetainedMBean} represents a resource consumption management policy for the 'Heap Retained' resource type.   The 'Heap Retained' resource type tracks the amount of Heap memory retained (in use) by the Partition.   Triggers (Usage limits) and Fair share policies can be defined for a 'Heap Retained' resource type through this MBena.   The valid set of recourse action types for the 'Heap Retained' resource type are:   notify slow shutdown  "
      ::= { wls 2090  }
      
   
   heapRetainedEntry OBJECT-TYPE
      SYNTAX      HeapRetainedEntry
      MAX-ACCESS  not-accessible
      STATUS      current
      DESCRIPTION "Generated SNMP Table Entry."
      INDEX { heapRetainedIndex}
      ::= { heapRetainedTable 1 }
      
   HeapRetainedEntry ::=
      SEQUENCE
      {
         heapRetainedIndex    OCTET STRING,
         heapRetainedObjectName OCTET STRING,
         heapRetainedName     OCTET STRING,
         heapRetainedType     OCTET STRING,
         heapRetainedTags     OCTET STRING
      }
      
   
   heapRetainedIndex OBJECT-TYPE
      SYNTAX      OCTET STRING
      MAX-ACCESS  not-accessible
      STATUS      current
      DESCRIPTION "Index column"
      ::= { heapRetainedEntry 1  }
   
   
   heapRetainedObjectName OBJECT-TYPE
      SYNTAX      OCTET STRING
      MAX-ACCESS  read-only
      STATUS      current
      DESCRIPTION "ObjectName column"
      ::= { heapRetainedEntry 2  }
   
   
   heapRetainedName OBJECT-TYPE
      SYNTAX      OCTET STRING
      MAX-ACCESS  read-only
      STATUS      current
      DESCRIPTION "The user-specified name of this MBean instance.  This name is included as one of the key properties in the MBean's javax.management.ObjectName:  Name=user-specified-name "
      ::= { heapRetainedEntry 3  }
   
   
   heapRetainedType OBJECT-TYPE
      SYNTAX      OCTET STRING
      MAX-ACCESS  read-only
      STATUS      current
      DESCRIPTION "Returns the type of the MBean. "
      ::= { heapRetainedEntry 4  }
   
   
   heapRetainedTags OBJECT-TYPE
      SYNTAX      OCTET STRING
      MAX-ACCESS  read-only
      STATUS      current
      DESCRIPTION "Return all tags on this Configuration MBean "
      ::= { heapRetainedEntry 5  }
   
   
   interceptorsTable OBJECT-TYPE
      SYNTAX      SEQUENCE OF InterceptorsEntry
      MAX-ACCESS  not-accessible
      STATUS      current
      DESCRIPTION " "
      ::= { wls 2095  }
      
   
   interceptorsEntry OBJECT-TYPE
      SYNTAX      InterceptorsEntry
      MAX-ACCESS  not-accessible
      STATUS      current
      DESCRIPTION "Generated SNMP Table Entry."
      INDEX { interceptorsIndex}
      ::= { interceptorsTable 1 }
      
   InterceptorsEntry ::=
      SEQUENCE
      {
         interceptorsIndex    OCTET STRING,
         interceptorsObjectName OCTET STRING,
         interceptorsWhiteListingEnabled OCTET STRING,
         interceptorsName     OCTET STRING,
         interceptorsType     OCTET STRING,
         interceptorsTags     OCTET STRING
      }
      
   
   interceptorsIndex OBJECT-TYPE
      SYNTAX      OCTET STRING
      MAX-ACCESS  not-accessible
      STATUS      current
      DESCRIPTION "Index column"
      ::= { interceptorsEntry 1  }
   
   
   interceptorsObjectName OBJECT-TYPE
      SYNTAX      OCTET STRING
      MAX-ACCESS  read-only
      STATUS      current
      DESCRIPTION "ObjectName column"
      ::= { interceptorsEntry 2  }
   
   
   interceptorsWhiteListingEnabled OBJECT-TYPE
      SYNTAX      OCTET STRING
      MAX-ACCESS  read-only
      STATUS      current
      DESCRIPTION "Returns true if white listing feature is enabled. When white listing is enabled, only those Interceptors returned by getInterceptors() are enabled. If white listing is disabled, then the values returned by getInterceptor() overrides the values specified through annotations. For example the rank specified by an InterceptorMethodMBean overrides the rank specified using the "
      ::= { interceptorsEntry 3  }
   
   
   interceptorsName OBJECT-TYPE
      SYNTAX      OCTET STRING
      MAX-ACCESS  read-only
      STATUS      current
      DESCRIPTION "The user-specified name of this MBean instance.  This name is included as one of the key properties in the MBean's javax.management.ObjectName:  Name=user-specified-name "
      ::= { interceptorsEntry 4  }
   
   
   interceptorsType OBJECT-TYPE
      SYNTAX      OCTET STRING
      MAX-ACCESS  read-only
      STATUS      current
      DESCRIPTION "Returns the type of the MBean. "
      ::= { interceptorsEntry 5  }
   
   
   interceptorsTags OBJECT-TYPE
      SYNTAX      OCTET STRING
      MAX-ACCESS  read-only
      STATUS      current
      DESCRIPTION "Return all tags on this Configuration MBean "
      ::= { interceptorsEntry 6  }
   
   
   jdbcSystemResourceOverrideTable OBJECT-TYPE
      SYNTAX      SEQUENCE OF JdbcSystemResourceOverrideEntry
      MAX-ACCESS  not-accessible
      STATUS      current
      DESCRIPTION "Defines a partition-specific JDBC data source attribute override of a data source descriptor referenced by a partition resource group definition. "
      ::= { wls 2100  }
      
   
   jdbcSystemResourceOverrideEntry OBJECT-TYPE
      SYNTAX      JdbcSystemResourceOverrideEntry
      MAX-ACCESS  not-accessible
      STATUS      current
      DESCRIPTION "Generated SNMP Table Entry."
      INDEX { jdbcSystemResourceOverrideIndex}
      ::= { jdbcSystemResourceOverrideTable 1 }
      
   JdbcSystemResourceOverrideEntry ::=
      SEQUENCE
      {
         jdbcSystemResourceOverrideIndex OCTET STRING,
         jdbcSystemResourceOverrideObjectName OCTET STRING,
         jdbcSystemResourceOverrideUser OCTET STRING,
         jdbcSystemResourceOverrideURL OCTET STRING,
         jdbcSystemResourceOverrideName OCTET STRING,
         jdbcSystemResourceOverrideType OCTET STRING,
         jdbcSystemResourceOverrideTags OCTET STRING,
         jdbcSystemResourceOverrideMinCapacity INTEGER,
         jdbcSystemResourceOverrideInitialCapacity INTEGER,
         jdbcSystemResourceOverrideMaxCapacity INTEGER
      }
      
   
   jdbcSystemResourceOverrideIndex OBJECT-TYPE
      SYNTAX      OCTET STRING
      MAX-ACCESS  not-accessible
      STATUS      current
      DESCRIPTION "Index column"
      ::= { jdbcSystemResourceOverrideEntry 1  }
   
   
   jdbcSystemResourceOverrideObjectName OBJECT-TYPE
      SYNTAX      OCTET STRING
      MAX-ACCESS  read-only
      STATUS      current
      DESCRIPTION "ObjectName column"
      ::= { jdbcSystemResourceOverrideEntry 2  }
   
   
   jdbcSystemResourceOverrideUser OBJECT-TYPE
      SYNTAX      OCTET STRING
      MAX-ACCESS  read-only
      STATUS      current
      DESCRIPTION "The name of the user for the data source. "
      ::= { jdbcSystemResourceOverrideEntry 3  }
   
   
   jdbcSystemResourceOverrideURL OBJECT-TYPE
      SYNTAX      OCTET STRING
      MAX-ACCESS  read-only
      STATUS      current
      DESCRIPTION "The connection URL for the data source. "
      ::= { jdbcSystemResourceOverrideEntry 4  }
   
   
   jdbcSystemResourceOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { jdbcSystemResourceOverrideEntry 5  }
   
   
   jdbcSystemResourceOverrideType OBJECT-TYPE
      SYNTAX      OCTET STRING
      MAX-ACCESS  read-only
      STATUS      current
      DESCRIPTION "Returns the type of the MBean. "
      ::= { jdbcSystemResourceOverrideEntry 6  }
   
   
   jdbcSystemResourceOverrideTags OBJECT-TYPE
      SYNTAX      OCTET STRING
      MAX-ACCESS  read-only
      STATUS      current
      DESCRIPTION "Return all tags on this Configuration MBean "
      ::= { jdbcSystemResourceOverrideEntry 7  }
   
   
   jdbcSystemResourceOverrideMinCapacity OBJECT-TYPE
      SYNTAX      INTEGER
      MAX-ACCESS  read-only
      STATUS      current
      DESCRIPTION "Returns the min pool capacity for the partition datasource. The value -1 indicates that the attribute is not set. "
      ::= { jdbcSystemResourceOverrideEntry 8  }
   
   
   jdbcSystemResourceOverrideInitialCapacity OBJECT-TYPE
      SYNTAX      INTEGER
      MAX-ACCESS  read-only
      STATUS      current
      DESCRIPTION "Returns the initial pool capacity for the partition datasource. The value -1 indicates that the attribute is not set. "
      ::= { jdbcSystemResourceOverrideEntry 9  }
   
   
   jdbcSystemResourceOverrideMaxCapacity OBJECT-TYPE
      SYNTAX      INTEGER
      MAX-ACCESS  read-only
      STATUS      current
      DESCRIPTION "Returns the max pool capacity for the partition datasource. The value -1 indicates that the attribute is not set. "
      ::= { jdbcSystemResourceOverrideEntry 10  }
   
   
   jmsSystemResourceOverrideTable OBJECT-TYPE
      SYNTAX      SEQUENCE OF JmsSystemResourceOverrideEntry
      MAX-ACCESS  not-accessible
      STATUS      current
      DESCRIPTION "For each configuration entity that supports per-partition-override via a MBean, we have two MBeans, the original configure MBean and the corresponding override MBean, that eventually determine the effective settings of the configured resource.  We mark an attribute of an override MBean 'dynamic true' even though the original configure MBean masks it 'dynamic false'. This is to make sure that the overriding settings take effect on partition restart. Otherwise a server restart is required.  Defines partition-specific overrides for the most commonly overridden attributes in a JMS system resource descriptor file. It overrides some of the settings in a same-named JMSSystemResource MBean instance in the same multi-tenant scope to which this override MBean belongs.  "
      ::= { wls 2105  }
      
   
   jmsSystemResourceOverrideEntry OBJECT-TYPE
      SYNTAX      JmsSystemResourceOverrideEntry
      MAX-ACCESS  not-accessible
      STATUS      current
      DESCRIPTION "Generated SNMP Table Entry."
      INDEX { jmsSystemResourceOverrideIndex}
      ::= { jmsSystemResourceOverrideTable 1 }
      
   JmsSystemResourceOverrideEntry ::=
      SEQUENCE
      {
         jmsSystemResourceOverrideIndex OCTET STRING,
         jmsSystemResourceOverrideObjectName OCTET STRING,
         jmsSystemResourceOverrideName OCTET STRING,
         jmsSystemResourceOverrideType OCTET STRING,
         jmsSystemResourceOverrideTags OCTET STRING
      }
      
   
   jmsSystemResourceOverrideIndex OBJECT-TYPE
      SYNTAX      OCTET STRING
      MAX-ACCESS  not-accessible
      STATUS      current
      DESCRIPTION "Index column"
      ::= { jmsSystemResourceOverrideEntry 1  }
   
   
   jmsSystemResourceOverrideObjectName OBJECT-TYPE
      SYNTAX      OCTET STRING
      MAX-ACCESS  read-only
      STATUS      current
      DESCRIPTION "ObjectName column"
      ::= { jmsSystemResourceOverrideEntry 2  }
   
   
   jmsSystemResourceOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { jmsSystemResourceOverrideEntry 3  }
   
   
   jmsSystemResourceOverrideType OBJECT-TYPE
      SYNTAX      OCTET STRING
      MAX-ACCESS  read-only
      STATUS      current
      DESCRIPTION "Returns the type of the MBean. "
      ::= { jmsSystemResourceOverrideEntry 4  }
   
   
   jmsSystemResourceOverrideTags OBJECT-TYPE
      SYNTAX      OCTET STRING
      MAX-ACCESS  read-only
      STATUS      current
      DESCRIPTION "Return all tags on this Configuration MBean "
      ::= { jmsSystemResourceOverrideEntry 5  }
   
   
   jtaPartitionTable OBJECT-TYPE
      SYNTAX      SEQUENCE OF JtaPartitionEntry
      MAX-ACCESS  not-accessible
      STATUS      current
      DESCRIPTION "This interface provides access to the JTAPartition configuration attributes.  The methods defined herein are applicable for JTA configuration at the partition level. "
      ::= { wls 2110  }
      
   
   jtaPartitionEntry OBJECT-TYPE
      SYNTAX      JtaPartitionEntry
      MAX-ACCESS  not-accessible
      STATUS      current
      DESCRIPTION "Generated SNMP Table Entry."
      INDEX { jtaPartitionIndex}
      ::= { jtaPartitionTable 1 }
      
   JtaPartitionEntry ::=
      SEQUENCE
      {
         jtaPartitionIndex    OCTET STRING,
         jtaPartitionObjectName OCTET STRING,
         jtaPartitionName     OCTET STRING,
         jtaPartitionTimeoutSeconds Integer32,
         jtaPartitionType     OCTET STRING,
         jtaPartitionTags     OCTET STRING
      }
      
   
   jtaPartitionIndex OBJECT-TYPE
      SYNTAX      OCTET STRING
      MAX-ACCESS  not-accessible
      STATUS      current
      DESCRIPTION "Index column"
      ::= { jtaPartitionEntry 1  }
   
   
   jtaPartitionObjectName OBJECT-TYPE
      SYNTAX      OCTET STRING
      MAX-ACCESS  read-only
      STATUS      current
      DESCRIPTION "ObjectName column"
      ::= { jtaPartitionEntry 2  }
   
   
   jtaPartitionName OBJECT-TYPE
      SYNTAX      OCTET STRING
      MAX-ACCESS  read-only
      STATUS      current
      DESCRIPTION "The user-specified name of this MBean instance.  This name is included as one of the key properties in the MBean's javax.management.ObjectName:  Name=user-specified-name "
      ::= { jtaPartitionEntry 3  }
   
   
   jtaPartitionTimeoutSeconds OBJECT-TYPE
      SYNTAX      Integer32
      MAX-ACCESS  read-only
      STATUS      current
      DESCRIPTION "Specifies the maximum amount of time, in seconds, an active transaction is allowed to be in the first phase of a two-phase commit transaction. If the specified amount of time expires, the transaction is automatically rolled back. "
      ::= { jtaPartitionEntry 4  }
   
   
   jtaPartitionType OBJECT-TYPE
      SYNTAX      OCTET STRING
      MAX-ACCESS  read-only
      STATUS      current
      DESCRIPTION "Returns the type of the MBean. "
      ::= { jtaPartitionEntry 5  }
   
   
   jtaPartitionTags OBJECT-TYPE
      SYNTAX      OCTET STRING
      MAX-ACCESS  read-only
      STATUS      current
      DESCRIPTION "Return all tags on this Configuration MBean "
      ::= { jtaPartitionEntry 6  }
   
   
   lifecycleManagerConfigTable OBJECT-TYPE
      SYNTAX      SEQUENCE OF LifecycleManagerConfigEntry
      MAX-ACCESS  not-accessible
      STATUS      current
      DESCRIPTION "LifecycleManagerConfigMBean maintains the information necessary to enable and configure a LifecycleManager instance associated with this domain.  LifecycleManager instances may either be local or remote to this domain. User credentials may be configured to support authentication, especially important when interaction with a remote domain. "
      ::= { wls 2115  }
      
   
   lifecycleManagerConfigEntry OBJECT-TYPE
      SYNTAX      LifecycleManagerConfigEntry
      MAX-ACCESS  not-accessible
      STATUS      current
      DESCRIPTION "Generated SNMP Table Entry."
      INDEX { lifecycleManagerConfigIndex}
      ::= { lifecycleManagerConfigTable 1 }
      
   LifecycleManagerConfigEntry ::=
      SEQUENCE
      {
         lifecycleManagerConfigIndex OCTET STRING,
         lifecycleManagerConfigObjectName OCTET STRING,
         lifecycleManagerConfigPersistenceType OCTET STRING,
         lifecycleManagerConfigEnabled OCTET STRING,
         lifecycleManagerConfigDeploymentType OCTET STRING,
         lifecycleManagerConfigName OCTET STRING,
         lifecycleManagerConfigType OCTET STRING,
         lifecycleManagerConfigDataSourceName OCTET STRING,
         lifecycleManagerConfigOutOfBandEnabled OCTET STRING,
         lifecycleManagerConfigTags OCTET STRING,
         lifecycleManagerConfigLCMInitiatedConnectTimeout INTEGER,
         lifecycleManagerConfigPropagationActivateTimeout Counter64,
         lifecycleManagerConfigPeriodicSyncInterval INTEGER,
         lifecycleManagerConfigLCMInitiatedReadTimeoutForElasticity INTEGER,
         lifecycleManagerConfigConfigFileLockTimeout Counter64,
         lifecycleManagerConfigLCMInitiatedConnectTimeoutForElasticity INTEGER,
         lifecycleManagerConfigLCMInitiatedReadTimeout INTEGER,
         lifecycleManagerConfigServerRuntimeTimeout Counter64,
         lifecycleManagerConfigServerReadyTimeout Counter64
      }
      
   
   lifecycleManagerConfigIndex OBJECT-TYPE
      SYNTAX      OCTET STRING
      MAX-ACCESS  not-accessible
      STATUS      current
      DESCRIPTION "Index column"
      ::= { lifecycleManagerConfigEntry 1  }
   
   
   lifecycleManagerConfigObjectName OBJECT-TYPE
      SYNTAX      OCTET STRING
      MAX-ACCESS  read-only
      STATUS      current
      DESCRIPTION "ObjectName column"
      ::= { lifecycleManagerConfigEntry 2  }
   
   
   lifecycleManagerConfigPersistenceType OBJECT-TYPE
      SYNTAX      OCTET STRING
      MAX-ACCESS  read-only
      STATUS      current
      DESCRIPTION "The persistence model that is used by this LifecycleManager service. Either database or a local XML file may be used for an admin server deployment, but a database configuration model is required for a cluster deployment. "
      ::= { lifecycleManagerConfigEntry 3  }
   
   
   lifecycleManagerConfigEnabled OBJECT-TYPE
      SYNTAX      OCTET STRING
      MAX-ACCESS  read-only
      STATUS      current
      DESCRIPTION "Determine if LifeycleManager features are available, either locally on this admin server or remotely via a configured endpoint. "
      ::= { lifecycleManagerConfigEntry 4  }
   
   
   lifecycleManagerConfigDeploymentType OBJECT-TYPE
      SYNTAX      OCTET STRING
      MAX-ACCESS  read-only
      STATUS      current
      DESCRIPTION "The deployment model for LifecycleManager services in this domain. "
      ::= { lifecycleManagerConfigEntry 5  }
   
   
   lifecycleManagerConfigName OBJECT-TYPE
      SYNTAX      OCTET STRING
      MAX-ACCESS  read-only
      STATUS      current
      DESCRIPTION "The user-specified name of this MBean instance.  This name is included as one of the key properties in the MBean's javax.management.ObjectName:  Name=user-specified-name "
      ::= { lifecycleManagerConfigEntry 6  }
   
   
   lifecycleManagerConfigType OBJECT-TYPE
      SYNTAX      OCTET STRING
      MAX-ACCESS  read-only
      STATUS      current
      DESCRIPTION "Returns the type of the MBean. "
      ::= { lifecycleManagerConfigEntry 7  }
   
   
   lifecycleManagerConfigDataSourceName OBJECT-TYPE
      SYNTAX      OCTET STRING
      MAX-ACCESS  read-only
      STATUS      current
      DESCRIPTION "Returns the name of the DataSource that should be used when LifecycleManager is configured to maintain its configuration in a database. "
      ::= { lifecycleManagerConfigEntry 8  }
   
   
   lifecycleManagerConfigOutOfBandEnabled OBJECT-TYPE
      SYNTAX      OCTET STRING
      MAX-ACCESS  read-only
      STATUS      current
      DESCRIPTION "Determine if LifecycleManager should listen for configuration changes on this server. "
      ::= { lifecycleManagerConfigEntry 9  }
   
   
   lifecycleManagerConfigTags OBJECT-TYPE
      SYNTAX      OCTET STRING
      MAX-ACCESS  read-only
      STATUS      current
      DESCRIPTION "Return all tags on this Configuration MBean "
      ::= { lifecycleManagerConfigEntry 10  }
   
   
   lifecycleManagerConfigLCMInitiatedConnectTimeout OBJECT-TYPE
      SYNTAX      INTEGER
      MAX-ACCESS  read-only
      STATUS      current
      DESCRIPTION "Returns setting for connect timeout for LCM initiated REST requests which may have been triggered by OOB, sync, patching. 0 return implies that the option is disabled (i.e., timeout of infinity). "
      ::= { lifecycleManagerConfigEntry 11  }
   
   
   lifecycleManagerConfigPropagationActivateTimeout OBJECT-TYPE
      SYNTAX      Counter64
      MAX-ACCESS  read-only
      STATUS      current
      DESCRIPTION "Returns the activation timeout in milliseconds for Lifecycle configuration propagation to managed server.  "
      ::= { lifecycleManagerConfigEntry 12  }
   
   
   lifecycleManagerConfigPeriodicSyncInterval OBJECT-TYPE
      SYNTAX      INTEGER
      MAX-ACCESS  read-only
      STATUS      current
      DESCRIPTION "Get periodic interval for lifecycle configuration synchronization in hours. When synchronizing configuration, Lifecycle contacts the different runtimes that are registered with it, gets the list of partitions from those runtimes, and ensure that its configuration is synchronized with those runtimes.  "
      ::= { lifecycleManagerConfigEntry 13  }
   
   
   lifecycleManagerConfigLCMInitiatedReadTimeoutForElasticity OBJECT-TYPE
      SYNTAX      INTEGER
      MAX-ACCESS  read-only
      STATUS      current
      DESCRIPTION " "
      ::= { lifecycleManagerConfigEntry 14  }
   
   
   lifecycleManagerConfigConfigFileLockTimeout OBJECT-TYPE
      SYNTAX      Counter64
      MAX-ACCESS  read-only
      STATUS      current
      DESCRIPTION "Returns the Lifecycle configuration lock timeout. This is used when the persistence type is LifecycleManagerConfigMBean.PERSISTENCE_TYPE_XML, while attempting to lock the configuration file to persist configuration changes.  "
      ::= { lifecycleManagerConfigEntry 15  }
   
   
   lifecycleManagerConfigLCMInitiatedConnectTimeoutForElasticity OBJECT-TYPE
      SYNTAX      INTEGER
      MAX-ACCESS  read-only
      STATUS      current
      DESCRIPTION "Returns setting for connect timeout for LCM initiated REST requests triggered by Elasticity 0 return implies that the option is disabled (i.e., timeout of infinity). "
      ::= { lifecycleManagerConfigEntry 16  }
   
   
   lifecycleManagerConfigLCMInitiatedReadTimeout OBJECT-TYPE
      SYNTAX      INTEGER
      MAX-ACCESS  read-only
      STATUS      current
      DESCRIPTION " "
      ::= { lifecycleManagerConfigEntry 17  }
   
   
   lifecycleManagerConfigServerRuntimeTimeout OBJECT-TYPE
      SYNTAX      Counter64
      MAX-ACCESS  read-only
      STATUS      current
      DESCRIPTION "Returns the timeout in milliseconds for accessing server runtime mbeans.  "
      ::= { lifecycleManagerConfigEntry 18  }
   
   
   lifecycleManagerConfigServerReadyTimeout OBJECT-TYPE
      SYNTAX      Counter64
      MAX-ACCESS  read-only
      STATUS      current
      DESCRIPTION "The timeout in milliseconds for waiting for a server to be ready to receive requests. "
      ::= { lifecycleManagerConfigEntry 19  }
   
   
   lifecycleManagerEndPointTable OBJECT-TYPE
      SYNTAX      SEQUENCE OF LifecycleManagerEndPointEntry
      MAX-ACCESS  not-accessible
      STATUS      current
      DESCRIPTION "LifecycleManagerEndPointMBean maintains the information necessary to locate and interact with an MT LifecycleManager instance associated with this domain. This information is used by WebLogic Server components to share configuration and runtime changes in a broader context.  LifecycleManager instances may either be local or remote to this domain. User credentials may be configured to support authentication, especially important when interaction with a remote domain. "
      ::= { wls 2120  }
      
   
   lifecycleManagerEndPointEntry OBJECT-TYPE
      SYNTAX      LifecycleManagerEndPointEntry
      MAX-ACCESS  not-accessible
      STATUS      current
      DESCRIPTION "Generated SNMP Table Entry."
      INDEX { lifecycleManagerEndPointIndex}
      ::= { lifecycleManagerEndPointTable 1 }
      
   LifecycleManagerEndPointEntry ::=
      SEQUENCE
      {
         lifecycleManagerEndPointIndex OCTET STRING,
         lifecycleManagerEndPointObjectName OCTET STRING,
         lifecycleManagerEndPointRuntimeName OCTET STRING,
         lifecycleManagerEndPointEnabled OCTET STRING,
         lifecycleManagerEndPointURL OCTET STRING,
         lifecycleManagerEndPointName OCTET STRING,
         lifecycleManagerEndPointType OCTET STRING,
         lifecycleManagerEndPointUsername OCTET STRING,
         lifecycleManagerEndPointTags OCTET STRING
      }
      
   
   lifecycleManagerEndPointIndex OBJECT-TYPE
      SYNTAX      OCTET STRING
      MAX-ACCESS  not-accessible
      STATUS      current
      DESCRIPTION "Index column"
      ::= { lifecycleManagerEndPointEntry 1  }
   
   
   lifecycleManagerEndPointObjectName OBJECT-TYPE
      SYNTAX      OCTET STRING
      MAX-ACCESS  read-only
      STATUS      current
      DESCRIPTION "ObjectName column"
      ::= { lifecycleManagerEndPointEntry 2  }
   
   
   lifecycleManagerEndPointRuntimeName OBJECT-TYPE
      SYNTAX      OCTET STRING
      MAX-ACCESS  read-only
      STATUS      current
      DESCRIPTION "Returns the runtime name for this WebLogic Server domain. This name can be used to override the domain name of the local domain from the perspective of LifecycleManager. "
      ::= { lifecycleManagerEndPointEntry 3  }
   
   
   lifecycleManagerEndPointEnabled OBJECT-TYPE
      SYNTAX      OCTET STRING
      MAX-ACCESS  read-only
      STATUS      current
      DESCRIPTION "Returns true if this LifecycleManager endpoint configuration is active and should be used when a WebLogic Server component needs to share a configuration change. "
      ::= { lifecycleManagerEndPointEntry 4  }
   
   
   lifecycleManagerEndPointURL OBJECT-TYPE
      SYNTAX      OCTET STRING
      MAX-ACCESS  read-only
      STATUS      current
      DESCRIPTION "Returns the URL for the root REST resource for the LifecycleManager instance. For example, http://localhost:7001/lifecycle/12.2.1.0/ "
      ::= { lifecycleManagerEndPointEntry 5  }
   
   
   lifecycleManagerEndPointName OBJECT-TYPE
      SYNTAX      OCTET STRING
      MAX-ACCESS  read-only
      STATUS      current
      DESCRIPTION "The user-specified name of this MBean instance.  This name is included as one of the key properties in the MBean's javax.management.ObjectName:  Name=user-specified-name "
      ::= { lifecycleManagerEndPointEntry 6  }
   
   
   lifecycleManagerEndPointType OBJECT-TYPE
      SYNTAX      OCTET STRING
      MAX-ACCESS  read-only
      STATUS      current
      DESCRIPTION "Returns the type of the MBean. "
      ::= { lifecycleManagerEndPointEntry 7  }
   
   
   lifecycleManagerEndPointUsername OBJECT-TYPE
      SYNTAX      OCTET STRING
      MAX-ACCESS  read-only
      STATUS      current
      DESCRIPTION "The user name that will be passed when opening a connection to a LifecycleManager instance (specified by the URL value for this endpoint). If not set, then no user name will be specified when establishing an connection. "
      ::= { lifecycleManagerEndPointEntry 8  }
   
   
   lifecycleManagerEndPointTags OBJECT-TYPE
      SYNTAX      OCTET STRING
      MAX-ACCESS  read-only
      STATUS      current
      DESCRIPTION "Return all tags on this Configuration MBean "
      ::= { lifecycleManagerEndPointEntry 9  }
   
   
   mailSessionOverrideTable OBJECT-TYPE
      SYNTAX      SEQUENCE OF MailSessionOverrideEntry
      MAX-ACCESS  not-accessible
      STATUS      current
      DESCRIPTION "Defines partition-specific mail session attribute overrides of a mail session referenced by a partition resource group definition. "
      ::= { wls 2125  }
      
   
   mailSessionOverrideEntry OBJECT-TYPE
      SYNTAX      MailSessionOverrideEntry
      MAX-ACCESS  not-accessible
      STATUS      current
      DESCRIPTION "Generated SNMP Table Entry."
      INDEX { mailSessionOverrideIndex}
      ::= { mailSessionOverrideTable 1 }
      
   MailSessionOverrideEntry ::=
      SEQUENCE
      {
         mailSessionOverrideIndex OCTET STRING,
         mailSessionOverrideObjectName OCTET STRING,
         mailSessionOverrideName OCTET STRING,
         mailSessionOverrideSessionUsername OCTET STRING,
         mailSessionOverrideType OCTET STRING,
         mailSessionOverrideTags OCTET STRING
      }
      
   
   mailSessionOverrideIndex OBJECT-TYPE
      SYNTAX      OCTET STRING
      MAX-ACCESS  not-accessible
      STATUS      current
      DESCRIPTION "Index column"
      ::= { mailSessionOverrideEntry 1  }
   
   
   mailSessionOverrideObjectName OBJECT-TYPE
      SYNTAX      OCTET STRING
      MAX-ACCESS  read-only
      STATUS      current
      DESCRIPTION "ObjectName column"
      ::= { mailSessionOverrideEntry 2  }
   
   
   mailSessionOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { mailSessionOverrideEntry 3  }
   
   
   mailSessionOverrideSessionUsername OBJECT-TYPE
      SYNTAX      OCTET STRING
      MAX-ACCESS  read-only
      STATUS      current
      DESCRIPTION "The username to be used to create an authenticated JavaMail Session, using a JavaMail Authenticator instance. "
      ::= { mailSessionOverrideEntry 4  }
   
   
   mailSessionOverrideType OBJECT-TYPE
      SYNTAX      OCTET STRING
      MAX-ACCESS  read-only
      STATUS      current
      DESCRIPTION "Returns the type of the MBean. "
      ::= { mailSessionOverrideEntry 5  }
   
   
   mailSessionOverrideTags OBJECT-TYPE
      SYNTAX      OCTET STRING
      MAX-ACCESS  read-only
      STATUS      current
      DESCRIPTION "Return all tags on this Configuration MBean "
      ::= { mailSessionOverrideEntry 6  }
   
   
   managedExecutorServiceTable OBJECT-TYPE
      SYNTAX      SEQUENCE OF ManagedExecutorServiceEntry
      MAX-ACCESS  not-accessible
      STATUS      current
      DESCRIPTION "Configuration MBean representing parameters of partition level ManagedExecutorService. "
      ::= { wls 2130  }
      
   
   managedExecutorServiceEntry OBJECT-TYPE
      SYNTAX      ManagedExecutorServiceEntry
      MAX-ACCESS  not-accessible
      STATUS      current
      DESCRIPTION "Generated SNMP Table Entry."
      INDEX { managedExecutorServiceIndex}
      ::= { managedExecutorServiceTable 1 }
      
   ManagedExecutorServiceEntry ::=
      SEQUENCE
      {
         managedExecutorServiceIndex OCTET STRING,
         managedExecutorServiceObjectName OCTET STRING,
         managedExecutorServiceDispatchPolicy OCTET STRING,
         managedExecutorServiceName OCTET STRING,
         managedExecutorServiceType OCTET STRING,
         managedExecutorServiceMaxConcurrentLongRunningRequests Integer32,
         managedExecutorServiceLongRunningPriority Integer32,
         managedExecutorServiceDeploymentOrder Integer32,
         managedExecutorServiceTags OCTET STRING
      }
      
   
   managedExecutorServiceIndex OBJECT-TYPE
      SYNTAX      OCTET STRING
      MAX-ACCESS  not-accessible
      STATUS      current
      DESCRIPTION "Index column"
      ::= { managedExecutorServiceEntry 1  }
   
   
   managedExecutorServiceObjectName OBJECT-TYPE
      SYNTAX      OCTET STRING
      MAX-ACCESS  read-only
      STATUS      current
      DESCRIPTION "ObjectName column"
      ::= { managedExecutorServiceEntry 2  }
   
   
   managedExecutorServiceDispatchPolicy OBJECT-TYPE
      SYNTAX      OCTET STRING
      MAX-ACCESS  read-only
      STATUS      current
      DESCRIPTION " The name of the Work Manager to use for this Concurrent Managed Ojbect (CMO). If a Work Manager is not specified, the default one is used.  "
      ::= { managedExecutorServiceEntry 3  }
   
   
   managedExecutorServiceName OBJECT-TYPE
      SYNTAX      OCTET STRING
      MAX-ACCESS  read-only
      STATUS      current
      DESCRIPTION "The user-specified name of this MBean instance.  This name is included as one of the key properties in the MBean's javax.management.ObjectName:  Name=user-specified-name "
      ::= { managedExecutorServiceEntry 4  }
   
   
   managedExecutorServiceType OBJECT-TYPE
      SYNTAX      OCTET STRING
      MAX-ACCESS  read-only
      STATUS      current
      DESCRIPTION "Returns the type of the MBean. "
      ::= { managedExecutorServiceEntry 5  }
   
   
   managedExecutorServiceMaxConcurrentLongRunningRequests OBJECT-TYPE
      SYNTAX      Integer32
      MAX-ACCESS  read-only
      STATUS      current
      DESCRIPTION " The maximum number of running long-running tasks submitted to this CMO.  "
      ::= { managedExecutorServiceEntry 6  }
   
   
   managedExecutorServiceLongRunningPriority OBJECT-TYPE
      SYNTAX      Integer32
      MAX-ACCESS  read-only
      STATUS      current
      DESCRIPTION " An integer that specifies the long-running daemon thread's priority. If a value is specified, all long-running threads are affected.  "
      ::= { managedExecutorServiceEntry 7  }
   
   
   managedExecutorServiceDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { managedExecutorServiceEntry 8  }
   
   
   managedExecutorServiceTags OBJECT-TYPE
      SYNTAX      OCTET STRING
      MAX-ACCESS  read-only
      STATUS      current
      DESCRIPTION "Return all tags on this Configuration MBean "
      ::= { managedExecutorServiceEntry 9  }
   
   
   managedExecutorServiceTemplateTable OBJECT-TYPE
      SYNTAX      SEQUENCE OF ManagedExecutorServiceTemplateEntry
      MAX-ACCESS  not-accessible
      STATUS      current
      DESCRIPTION "Configuration MBean representing parameters of ManagedExecutorService template. "
      ::= { wls 2135  }
      
   
   managedExecutorServiceTemplateEntry OBJECT-TYPE
      SYNTAX      ManagedExecutorServiceTemplateEntry
      MAX-ACCESS  not-accessible
      STATUS      current
      DESCRIPTION "Generated SNMP Table Entry."
      INDEX { managedExecutorServiceTemplateIndex}
      ::= { managedExecutorServiceTemplateTable 1 }
      
   ManagedExecutorServiceTemplateEntry ::=
      SEQUENCE
      {
         managedExecutorServiceTemplateIndex OCTET STRING,
         managedExecutorServiceTemplateObjectName OCTET STRING,
         managedExecutorServiceTemplateDispatchPolicy OCTET STRING,
         managedExecutorServiceTemplateName OCTET STRING,
         managedExecutorServiceTemplateType OCTET STRING,
         managedExecutorServiceTemplateMaxConcurrentLongRunningRequests Integer32,
         managedExecutorServiceTemplateLongRunningPriority Integer32,
         managedExecutorServiceTemplateDeploymentOrder Integer32,
         managedExecutorServiceTemplateTags OCTET STRING
      }
      
   
   managedExecutorServiceTemplateIndex OBJECT-TYPE
      SYNTAX      OCTET STRING
      MAX-ACCESS  not-accessible
      STATUS      current
      DESCRIPTION "Index column"
      ::= { managedExecutorServiceTemplateEntry 1  }
   
   
   managedExecutorServiceTemplateObjectName OBJECT-TYPE
      SYNTAX      OCTET STRING
      MAX-ACCESS  read-only
      STATUS      current
      DESCRIPTION "ObjectName column"
      ::= { managedExecutorServiceTemplateEntry 2  }
   
   
   managedExecutorServiceTemplateDispatchPolicy OBJECT-TYPE
      SYNTAX      OCTET STRING
      MAX-ACCESS  read-only
      STATUS      current
      DESCRIPTION " The name of the Work Manager to use for this Concurrent Managed Ojbect (CMO). If a Work Manager is not specified, the default one is used.  "
      ::= { managedExecutorServiceTemplateEntry 3  }
   
   
   managedExecutorServiceTemplateName OBJECT-TYPE
      SYNTAX      OCTET STRING
      MAX-ACCESS  read-only
      STATUS      current
      DESCRIPTION "The user-specified name of this MBean instance.  This name is included as one of the key properties in the MBean's javax.management.ObjectName:  Name=user-specified-name "
      ::= { managedExecutorServiceTemplateEntry 4  }
   
   
   managedExecutorServiceTemplateType OBJECT-TYPE
      SYNTAX      OCTET STRING
      MAX-ACCESS  read-only
      STATUS      current
      DESCRIPTION "Returns the type of the MBean. "
      ::= { managedExecutorServiceTemplateEntry 5  }
   
   
   managedExecutorServiceTemplateMaxConcurrentLongRunningRequests OBJECT-TYPE
      SYNTAX      Integer32
      MAX-ACCESS  read-only
      STATUS      current
      DESCRIPTION " The maximum number of running long-running tasks submitted to this CMO.  "
      ::= { managedExecutorServiceTemplateEntry 6  }
   
   
   managedExecutorServiceTemplateLongRunningPriority OBJECT-TYPE
      SYNTAX      Integer32
      MAX-ACCESS  read-only
      STATUS      current
      DESCRIPTION " An integer that specifies the long-running daemon thread's priority. If a value is specified, all long-running threads are affected.  "
      ::= { managedExecutorServiceTemplateEntry 7  }
   
   
   managedExecutorServiceTemplateDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { managedExecutorServiceTemplateEntry 8  }
   
   
   managedExecutorServiceTemplateTags OBJECT-TYPE
      SYNTAX      OCTET STRING
      MAX-ACCESS  read-only
      STATUS      current
      DESCRIPTION "Return all tags on this Configuration MBean "
      ::= { managedExecutorServiceTemplateEntry 9  }
   
   
   managedScheduledExecutorServiceTable OBJECT-TYPE
      SYNTAX      SEQUENCE OF ManagedScheduledExecutorServiceEntry
      MAX-ACCESS  not-accessible
      STATUS      current
      DESCRIPTION "Configuration MBean representing parameters of partition level ManagedScheduledExecutorService. "
      ::= { wls 2140  }
      
   
   managedScheduledExecutorServiceEntry OBJECT-TYPE
      SYNTAX      ManagedScheduledExecutorServiceEntry
      MAX-ACCESS  not-accessible
      STATUS      current
      DESCRIPTION "Generated SNMP Table Entry."
      INDEX { managedScheduledExecutorServiceIndex}
      ::= { managedScheduledExecutorServiceTable 1 }
      
   ManagedScheduledExecutorServiceEntry ::=
      SEQUENCE
      {
         managedScheduledExecutorServiceIndex OCTET STRING,
         managedScheduledExecutorServiceObjectName OCTET STRING,
         managedScheduledExecutorServiceDispatchPolicy OCTET STRING,
         managedScheduledExecutorServiceName OCTET STRING,
         managedScheduledExecutorServiceType OCTET STRING,
         managedScheduledExecutorServiceMaxConcurrentLongRunningRequests Integer32,
         managedScheduledExecutorServiceLongRunningPriority Integer32,
         managedScheduledExecutorServiceDeploymentOrder Integer32,
         managedScheduledExecutorServiceTags OCTET STRING
      }
      
   
   managedScheduledExecutorServiceIndex OBJECT-TYPE
      SYNTAX      OCTET STRING
      MAX-ACCESS  not-accessible
      STATUS      current
      DESCRIPTION "Index column"
      ::= { managedScheduledExecutorServiceEntry 1  }
   
   
   managedScheduledExecutorServiceObjectName OBJECT-TYPE
      SYNTAX      OCTET STRING
      MAX-ACCESS  read-only
      STATUS      current
      DESCRIPTION "ObjectName column"
      ::= { managedScheduledExecutorServiceEntry 2  }
   
   
   managedScheduledExecutorServiceDispatchPolicy OBJECT-TYPE
      SYNTAX      OCTET STRING
      MAX-ACCESS  read-only
      STATUS      current
      DESCRIPTION " The name of the Work Manager to use for this Concurrent Managed Ojbect (CMO). If a Work Manager is not specified, the default one is used.  "
      ::= { managedScheduledExecutorServiceEntry 3  }
   
   
   managedScheduledExecutorServiceName OBJECT-TYPE
      SYNTAX      OCTET STRING
      MAX-ACCESS  read-only
      STATUS      current
      DESCRIPTION "The user-specified name of this MBean instance.  This name is included as one of the key properties in the MBean's javax.management.ObjectName:  Name=user-specified-name "
      ::= { managedScheduledExecutorServiceEntry 4  }
   
   
   managedScheduledExecutorServiceType OBJECT-TYPE
      SYNTAX      OCTET STRING
      MAX-ACCESS  read-only
      STATUS      current
      DESCRIPTION "Returns the type of the MBean. "
      ::= { managedScheduledExecutorServiceEntry 5  }
   
   
   managedScheduledExecutorServiceMaxConcurrentLongRunningRequests OBJECT-TYPE
      SYNTAX      Integer32
      MAX-ACCESS  read-only
      STATUS      current
      DESCRIPTION " The maximum number of running long-running tasks submitted to this CMO.  "
      ::= { managedScheduledExecutorServiceEntry 6  }
   
   
   managedScheduledExecutorServiceLongRunningPriority OBJECT-TYPE
      SYNTAX      Integer32
      MAX-ACCESS  read-only
      STATUS      current
      DESCRIPTION " An integer that specifies the long-running daemon thread's priority. If a value is specified, all long-running threads are affected.  "
      ::= { managedScheduledExecutorServiceEntry 7  }
   
   
   managedScheduledExecutorServiceDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { managedScheduledExecutorServiceEntry 8  }
   
   
   managedScheduledExecutorServiceTags OBJECT-TYPE
      SYNTAX      OCTET STRING
      MAX-ACCESS  read-only
      STATUS      current
      DESCRIPTION "Return all tags on this Configuration MBean "
      ::= { managedScheduledExecutorServiceEntry 9  }
   
   
   managedScheduledExecutorServiceTemplateTable OBJECT-TYPE
      SYNTAX      SEQUENCE OF ManagedScheduledExecutorServiceTemplateEntry
      MAX-ACCESS  not-accessible
      STATUS      current
      DESCRIPTION "Configuration MBean representing parameters of ManagedScheduledExecutorService template. "
      ::= { wls 2145  }
      
   
   managedScheduledExecutorServiceTemplateEntry OBJECT-TYPE
      SYNTAX      ManagedScheduledExecutorServiceTemplateEntry
      MAX-ACCESS  not-accessible
      STATUS      current
      DESCRIPTION "Generated SNMP Table Entry."
      INDEX { managedScheduledExecutorServiceTemplateIndex}
      ::= { managedScheduledExecutorServiceTemplateTable 1 }
      
   ManagedScheduledExecutorServiceTemplateEntry ::=
      SEQUENCE
      {
         managedScheduledExecutorServiceTemplateIndex OCTET STRING,
         managedScheduledExecutorServiceTemplateObjectName OCTET STRING,
         managedScheduledExecutorServiceTemplateDispatchPolicy OCTET STRING,
         managedScheduledExecutorServiceTemplateName OCTET STRING,
         managedScheduledExecutorServiceTemplateType OCTET STRING,
         managedScheduledExecutorServiceTemplateMaxConcurrentLongRunningRequests Integer32,
         managedScheduledExecutorServiceTemplateLongRunningPriority Integer32,
         managedScheduledExecutorServiceTemplateDeploymentOrder Integer32,
         managedScheduledExecutorServiceTemplateTags OCTET STRING
      }
      
   
   managedScheduledExecutorServiceTemplateIndex OBJECT-TYPE
      SYNTAX      OCTET STRING
      MAX-ACCESS  not-accessible
      STATUS      current
      DESCRIPTION "Index column"
      ::= { managedScheduledExecutorServiceTemplateEntry 1  }
   
   
   managedScheduledExecutorServiceTemplateObjectName OBJECT-TYPE
      SYNTAX      OCTET STRING
      MAX-ACCESS  read-only
      STATUS      current
      DESCRIPTION "ObjectName column"
      ::= { managedScheduledExecutorServiceTemplateEntry 2  }
   
   
   managedScheduledExecutorServiceTemplateDispatchPolicy OBJECT-TYPE
      SYNTAX      OCTET STRING
      MAX-ACCESS  read-only
      STATUS      current
      DESCRIPTION " The name of the Work Manager to use for this Concurrent Managed Ojbect (CMO). If a Work Manager is not specified, the default one is used.  "
      ::= { managedScheduledExecutorServiceTemplateEntry 3  }
   
   
   managedScheduledExecutorServiceTemplateName OBJECT-TYPE
      SYNTAX      OCTET STRING
      MAX-ACCESS  read-only
      STATUS      current
      DESCRIPTION "The user-specified name of this MBean instance.  This name is included as one of the key properties in the MBean's javax.management.ObjectName:  Name=user-specified-name "
      ::= { managedScheduledExecutorServiceTemplateEntry 4  }
   
   
   managedScheduledExecutorServiceTemplateType OBJECT-TYPE
      SYNTAX      OCTET STRING
      MAX-ACCESS  read-only
      STATUS      current
      DESCRIPTION "Returns the type of the MBean. "
      ::= { managedScheduledExecutorServiceTemplateEntry 5  }
   
   
   managedScheduledExecutorServiceTemplateMaxConcurrentLongRunningRequests OBJECT-TYPE
      SYNTAX      Integer32
      MAX-ACCESS  read-only
      STATUS      current
      DESCRIPTION "The maximum number of running long-running tasks submitted to this CMO."
      ::= { managedScheduledExecutorServiceTemplateEntry 6  }
   
   
   managedScheduledExecutorServiceTemplateLongRunningPriority OBJECT-TYPE
      SYNTAX      Integer32
      MAX-ACCESS  read-only
      STATUS      current
      DESCRIPTION " An integer that specifies the long-running daemon thread's priority. If a value is specified, all long-running threads are affected.  "
      ::= { managedScheduledExecutorServiceTemplateEntry 7  }
   
   
   managedScheduledExecutorServiceTemplateDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { managedScheduledExecutorServiceTemplateEntry 8  }
   
   
   managedScheduledExecutorServiceTemplateTags OBJECT-TYPE
      SYNTAX      OCTET STRING
      MAX-ACCESS  read-only
      STATUS      current
      DESCRIPTION "Return all tags on this Configuration MBean "
      ::= { managedScheduledExecutorServiceTemplateEntry 9  }
   
   
   managedThreadFactoryTable OBJECT-TYPE
      SYNTAX      SEQUENCE OF ManagedThreadFactoryEntry
      MAX-ACCESS  not-accessible
      STATUS      current
      DESCRIPTION "Configuration MBean representing parameters of partition level ManagedThreadFactory. "
      ::= { wls 2150  }
      
   
   managedThreadFactoryEntry OBJECT-TYPE
      SYNTAX      ManagedThreadFactoryEntry
      MAX-ACCESS  not-accessible
      STATUS      current
      DESCRIPTION "Generated SNMP Table Entry."
      INDEX { managedThreadFactoryIndex}
      ::= { managedThreadFactoryTable 1 }
      
   ManagedThreadFactoryEntry ::=
      SEQUENCE
      {
         managedThreadFactoryIndex OCTET STRING,
         managedThreadFactoryObjectName OCTET STRING,
         managedThreadFactoryPriority Integer32,
         managedThreadFactoryName OCTET STRING,
         managedThreadFactoryMaxConcurrentNewThreads Integer32,
         managedThreadFactoryType OCTET STRING,
         managedThreadFactoryDeploymentOrder Integer32,
         managedThreadFactoryTags OCTET STRING
      }
      
   
   managedThreadFactoryIndex OBJECT-TYPE
      SYNTAX      OCTET STRING
      MAX-ACCESS  not-accessible
      STATUS      current
      DESCRIPTION "Index column"
      ::= { managedThreadFactoryEntry 1  }
   
   
   managedThreadFactoryObjectName OBJECT-TYPE
      SYNTAX      OCTET STRING
      MAX-ACCESS  read-only
      STATUS      current
      DESCRIPTION "ObjectName column"
      ::= { managedThreadFactoryEntry 2  }
   
   
   managedThreadFactoryPriority OBJECT-TYPE
      SYNTAX      Integer32
      MAX-ACCESS  read-only
      STATUS      current
      DESCRIPTION " An integer that specifies the daemon thread's priority. If a value is specified, all concurrent new threads created by this MTF are affected.  "
      ::= { managedThreadFactoryEntry 3  }
   
   
   managedThreadFactoryName OBJECT-TYPE
      SYNTAX      OCTET STRING
      MAX-ACCESS  read-only
      STATUS      current
      DESCRIPTION "The user-specified name of this MBean instance.  This name is included as one of the key properties in the MBean's javax.management.ObjectName:  Name=user-specified-name "
      ::= { managedThreadFactoryEntry 4  }
   
   
   managedThreadFactoryMaxConcurrentNewThreads OBJECT-TYPE
      SYNTAX      Integer32
      MAX-ACCESS  read-only
      STATUS      current
      DESCRIPTION " The maximum number of concurrent new threads that can be created by this Managed Thread Factory (MTF).  "
      ::= { managedThreadFactoryEntry 5  }
   
   
   managedThreadFactoryType OBJECT-TYPE
      SYNTAX      OCTET STRING
      MAX-ACCESS  read-only
      STATUS      current
      DESCRIPTION "Returns the type of the MBean. "
      ::= { managedThreadFactoryEntry 6  }
   
   
   managedThreadFactoryDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { managedThreadFactoryEntry 7  }
   
   
   managedThreadFactoryTags OBJECT-TYPE
      SYNTAX      OCTET STRING
      MAX-ACCESS  read-only
      STATUS      current
      DESCRIPTION "Return all tags on this Configuration MBean "
      ::= { managedThreadFactoryEntry 8  }
   
   
   managedThreadFactoryTemplateTable OBJECT-TYPE
      SYNTAX      SEQUENCE OF ManagedThreadFactoryTemplateEntry
      MAX-ACCESS  not-accessible
      STATUS      current
      DESCRIPTION "Configuration MBean representing common parameters of ManagedThreadFactory template. "
      ::= { wls 2155  }
      
   
   managedThreadFactoryTemplateEntry OBJECT-TYPE
      SYNTAX      ManagedThreadFactoryTemplateEntry
      MAX-ACCESS  not-accessible
      STATUS      current
      DESCRIPTION "Generated SNMP Table Entry."
      INDEX { managedThreadFactoryTemplateIndex}
      ::= { managedThreadFactoryTemplateTable 1 }
      
   ManagedThreadFactoryTemplateEntry ::=
      SEQUENCE
      {
         managedThreadFactoryTemplateIndex OCTET STRING,
         managedThreadFactoryTemplateObjectName OCTET STRING,
         managedThreadFactoryTemplatePriority Integer32,
         managedThreadFactoryTemplateName OCTET STRING,
         managedThreadFactoryTemplateMaxConcurrentNewThreads Integer32,
         managedThreadFactoryTemplateType OCTET STRING,
         managedThreadFactoryTemplateDeploymentOrder Integer32,
         managedThreadFactoryTemplateTags OCTET STRING
      }
      
   
   managedThreadFactoryTemplateIndex OBJECT-TYPE
      SYNTAX      OCTET STRING
      MAX-ACCESS  not-accessible
      STATUS      current
      DESCRIPTION "Index column"
      ::= { managedThreadFactoryTemplateEntry 1  }
   
   
   managedThreadFactoryTemplateObjectName OBJECT-TYPE
      SYNTAX      OCTET STRING
      MAX-ACCESS  read-only
      STATUS      current
      DESCRIPTION "ObjectName column"
      ::= { managedThreadFactoryTemplateEntry 2  }
   
   
   managedThreadFactoryTemplatePriority OBJECT-TYPE
      SYNTAX      Integer32
      MAX-ACCESS  read-only
      STATUS      current
      DESCRIPTION " An integer that specifies the daemon thread's priority. If a value is specified, all concurrent new threads created by this MTF are affected.  "
      ::= { managedThreadFactoryTemplateEntry 3  }
   
   
   managedThreadFactoryTemplateName OBJECT-TYPE
      SYNTAX      OCTET STRING
      MAX-ACCESS  read-only
      STATUS      current
      DESCRIPTION "The user-specified name of this MBean instance.  This name is included as one of the key properties in the MBean's javax.management.ObjectName:  Name=user-specified-name "
      ::= { managedThreadFactoryTemplateEntry 4  }
   
   
   managedThreadFactoryTemplateMaxConcurrentNewThreads OBJECT-TYPE
      SYNTAX      Integer32
      MAX-ACCESS  read-only
      STATUS      current
      DESCRIPTION " The maximum number of concurrent new threads that can be created by this Managed Thread Factory (MTF).  "
      ::= { managedThreadFactoryTemplateEntry 5  }
   
   
   managedThreadFactoryTemplateType OBJECT-TYPE
      SYNTAX      OCTET STRING
      MAX-ACCESS  read-only
      STATUS      current
      DESCRIPTION "Returns the type of the MBean. "
      ::= { managedThreadFactoryTemplateEntry 6  }
   
   
   managedThreadFactoryTemplateDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { managedThreadFactoryTemplateEntry 7  }
   
   
   managedThreadFactoryTemplateTags OBJECT-TYPE
      SYNTAX      OCTET STRING
      MAX-ACCESS  read-only
      STATUS      current
      DESCRIPTION "Return all tags on this Configuration MBean "
      ::= { managedThreadFactoryTemplateEntry 8  }
   
   
   optionalFeatureDeploymentTable OBJECT-TYPE
      SYNTAX      SEQUENCE OF OptionalFeatureDeploymentEntry
      MAX-ACCESS  not-accessible
      STATUS      current
      DESCRIPTION "Control panel for all optional features, e.g. WSAT, ASYNC_RESPONSE etc. The mbean is designed to be managed by domain and to extend for partition if needed in future.  "
      ::= { wls 2160  }
      
   
   optionalFeatureDeploymentEntry OBJECT-TYPE
      SYNTAX      OptionalFeatureDeploymentEntry
      MAX-ACCESS  not-accessible
      STATUS      current
      DESCRIPTION "Generated SNMP Table Entry."
      INDEX { optionalFeatureDeploymentIndex}
      ::= { optionalFeatureDeploymentTable 1 }
      
   OptionalFeatureDeploymentEntry ::=
      SEQUENCE
      {
         optionalFeatureDeploymentIndex OCTET STRING,
         optionalFeatureDeploymentObjectName OCTET STRING,
         optionalFeatureDeploymentName OCTET STRING,
         optionalFeatureDeploymentType OCTET STRING,
         optionalFeatureDeploymentTags OCTET STRING
      }
      
   
   optionalFeatureDeploymentIndex OBJECT-TYPE
      SYNTAX      OCTET STRING
      MAX-ACCESS  not-accessible
      STATUS      current
      DESCRIPTION "Index column"
      ::= { optionalFeatureDeploymentEntry 1  }
   
   
   optionalFeatureDeploymentObjectName OBJECT-TYPE
      SYNTAX      OCTET STRING
      MAX-ACCESS  read-only
      STATUS      current
      DESCRIPTION "ObjectName column"
      ::= { optionalFeatureDeploymentEntry 2  }
   
   
   optionalFeatureDeploymentName OBJECT-TYPE
      SYNTAX      OCTET STRING
      MAX-ACCESS  read-only
      STATUS      current
      DESCRIPTION "The user-specified name of this MBean instance.  This name is included as one of the key properties in the MBean's javax.management.ObjectName:  Name=user-specified-name "
      ::= { optionalFeatureDeploymentEntry 3  }
   
   
   optionalFeatureDeploymentType OBJECT-TYPE
      SYNTAX      OCTET STRING
      MAX-ACCESS  read-only
      STATUS      current
      DESCRIPTION "Returns the type of the MBean. "
      ::= { optionalFeatureDeploymentEntry 4  }
   
   
   optionalFeatureDeploymentTags OBJECT-TYPE
      SYNTAX      OCTET STRING
      MAX-ACCESS  read-only
      STATUS      current
      DESCRIPTION "Return all tags on this Configuration MBean "
      ::= { optionalFeatureDeploymentEntry 5  }
   
   
   optionalFeatureTable OBJECT-TYPE
      SYNTAX      SEQUENCE OF OptionalFeatureEntry
      MAX-ACCESS  not-accessible
      STATUS      current
      DESCRIPTION "Controls the configuration of an optional feature. "
      ::= { wls 2165  }
      
   
   optionalFeatureEntry OBJECT-TYPE
      SYNTAX      OptionalFeatureEntry
      MAX-ACCESS  not-accessible
      STATUS      current
      DESCRIPTION "Generated SNMP Table Entry."
      INDEX { optionalFeatureIndex}
      ::= { optionalFeatureTable 1 }
      
   OptionalFeatureEntry ::=
      SEQUENCE
      {
         optionalFeatureIndex OCTET STRING,
         optionalFeatureObjectName OCTET STRING,
         optionalFeatureEnabled OCTET STRING,
         optionalFeatureName  OCTET STRING,
         optionalFeatureType  OCTET STRING,
         optionalFeatureTags  OCTET STRING
      }
      
   
   optionalFeatureIndex OBJECT-TYPE
      SYNTAX      OCTET STRING
      MAX-ACCESS  not-accessible
      STATUS      current
      DESCRIPTION "Index column"
      ::= { optionalFeatureEntry 1  }
   
   
   optionalFeatureObjectName OBJECT-TYPE
      SYNTAX      OCTET STRING
      MAX-ACCESS  read-only
      STATUS      current
      DESCRIPTION "ObjectName column"
      ::= { optionalFeatureEntry 2  }
   
   
   optionalFeatureEnabled OBJECT-TYPE
      SYNTAX      OCTET STRING
      MAX-ACCESS  read-only
      STATUS      current
      DESCRIPTION "Identifies whether the WebLogic Server automatically deploys the internal app in the current domain/partition. "
      ::= { optionalFeatureEntry 3  }
   
   
   optionalFeatureName OBJECT-TYPE
      SYNTAX      OCTET STRING
      MAX-ACCESS  read-only
      STATUS      current
      DESCRIPTION "The user-specified name of this MBean instance.  This name is included as one of the key properties in the MBean's javax.management.ObjectName:  Name=user-specified-name "
      ::= { optionalFeatureEntry 4  }
   
   
   optionalFeatureType OBJECT-TYPE
      SYNTAX      OCTET STRING
      MAX-ACCESS  read-only
      STATUS      current
      DESCRIPTION "Returns the type of the MBean. "
      ::= { optionalFeatureEntry 5  }
   
   
   optionalFeatureTags OBJECT-TYPE
      SYNTAX      OCTET STRING
      MAX-ACCESS  read-only
      STATUS      current
      DESCRIPTION "Return all tags on this Configuration MBean "
      ::= { optionalFeatureEntry 6  }
   
   
   partitionFileSystemTable OBJECT-TYPE
      SYNTAX      SEQUENCE OF PartitionFileSystemEntry
      MAX-ACCESS  not-accessible
      STATUS      current
      DESCRIPTION "Defines the partition file system configuration. "
      ::= { wls 2170  }
      
   
   partitionFileSystemEntry OBJECT-TYPE
      SYNTAX      PartitionFileSystemEntry
      MAX-ACCESS  not-accessible
      STATUS      current
      DESCRIPTION "Generated SNMP Table Entry."
      INDEX { partitionFileSystemIndex}
      ::= { partitionFileSystemTable 1 }
      
   PartitionFileSystemEntry ::=
      SEQUENCE
      {
         partitionFileSystemIndex OCTET STRING,
         partitionFileSystemObjectName OCTET STRING,
         partitionFileSystemRoot OCTET STRING,
         partitionFileSystemName OCTET STRING,
         partitionFileSystemType OCTET STRING,
         partitionFileSystemPreserved OCTET STRING,
         partitionFileSystemCreateOnDemand OCTET STRING,
         partitionFileSystemTags OCTET STRING
      }
      
   
   partitionFileSystemIndex OBJECT-TYPE
      SYNTAX      OCTET STRING
      MAX-ACCESS  not-accessible
      STATUS      current
      DESCRIPTION "Index column"
      ::= { partitionFileSystemEntry 1  }
   
   
   partitionFileSystemObjectName OBJECT-TYPE
      SYNTAX      OCTET STRING
      MAX-ACCESS  read-only
      STATUS      current
      DESCRIPTION "ObjectName column"
      ::= { partitionFileSystemEntry 2  }
   
   
   partitionFileSystemRoot OBJECT-TYPE
      SYNTAX      OCTET STRING
      MAX-ACCESS  read-only
      STATUS      current
      DESCRIPTION "The full path to the root of this file subsystem of the partition. "
      ::= { partitionFileSystemEntry 3  }
   
   
   partitionFileSystemName OBJECT-TYPE
      SYNTAX      OCTET STRING
      MAX-ACCESS  read-only
      STATUS      current
      DESCRIPTION "The user-specified name of this MBean instance.  This name is included as one of the key properties in the MBean's javax.management.ObjectName:  Name=user-specified-name "
      ::= { partitionFileSystemEntry 4  }
   
   
   partitionFileSystemType OBJECT-TYPE
      SYNTAX      OCTET STRING
      MAX-ACCESS  read-only
      STATUS      current
      DESCRIPTION "Returns the type of the MBean. "
      ::= { partitionFileSystemEntry 5  }
   
   
   partitionFileSystemPreserved OBJECT-TYPE
      SYNTAX      OCTET STRING
      MAX-ACCESS  read-only
      STATUS      current
      DESCRIPTION "Specifies whether the file system should be preserved when the partition is deleted. "
      ::= { partitionFileSystemEntry 6  }
   
   
   partitionFileSystemCreateOnDemand OBJECT-TYPE
      SYNTAX      OCTET STRING
      MAX-ACCESS  read-only
      STATUS      current
      DESCRIPTION "Specifies whether the file system should be created on-demand when the partition is first started. "
      ::= { partitionFileSystemEntry 7  }
   
   
   partitionFileSystemTags OBJECT-TYPE
      SYNTAX      OCTET STRING
      MAX-ACCESS  read-only
      STATUS      current
      DESCRIPTION "Return all tags on this Configuration MBean "
      ::= { partitionFileSystemEntry 8  }
   
   
   partitionLogTable OBJECT-TYPE
      SYNTAX      SEQUENCE OF PartitionLogEntry
      MAX-ACCESS  not-accessible
      STATUS      current
      DESCRIPTION "Partition scoped logging configuration. "
      ::= { wls 2175  }
      
   
   partitionLogEntry OBJECT-TYPE
      SYNTAX      PartitionLogEntry
      MAX-ACCESS  not-accessible
      STATUS      current
      DESCRIPTION "Generated SNMP Table Entry."
      INDEX { partitionLogIndex}
      ::= { partitionLogTable 1 }
      
   PartitionLogEntry ::=
      SEQUENCE
      {
         partitionLogIndex    OCTET STRING,
         partitionLogObjectName OCTET STRING,
         partitionLogEnabledServerDebugAttributes OCTET STRING,
         partitionLogName     OCTET STRING,
         partitionLogType     OCTET STRING,
         partitionLogTags     OCTET STRING
      }
      
   
   partitionLogIndex OBJECT-TYPE
      SYNTAX      OCTET STRING
      MAX-ACCESS  not-accessible
      STATUS      current
      DESCRIPTION "Index column"
      ::= { partitionLogEntry 1  }
   
   
   partitionLogObjectName OBJECT-TYPE
      SYNTAX      OCTET STRING
      MAX-ACCESS  read-only
      STATUS      current
      DESCRIPTION "ObjectName column"
      ::= { partitionLogEntry 2  }
   
   
   partitionLogEnabledServerDebugAttributes OBJECT-TYPE
      SYNTAX      OCTET STRING
      MAX-ACCESS  read-only
      STATUS      current
      DESCRIPTION "List of attributes from the WebLogic ServerDebugMBean that are enabled for the given partition. Note: Server level debug for a partition should be carefully enabled in consultation with a WebLogic system administrator only for a short period to capture additional debug output when troubleshooting a server problem. "
      ::= { partitionLogEntry 3  }
   
   
   partitionLogName OBJECT-TYPE
      SYNTAX      OCTET STRING
      MAX-ACCESS  read-only
      STATUS      current
      DESCRIPTION "The user-specified name of this MBean instance.  This name is included as one of the key properties in the MBean's javax.management.ObjectName:  Name=user-specified-name "
      ::= { partitionLogEntry 4  }
   
   
   partitionLogType OBJECT-TYPE
      SYNTAX      OCTET STRING
      MAX-ACCESS  read-only
      STATUS      current
      DESCRIPTION "Returns the type of the MBean. "
      ::= { partitionLogEntry 5  }
   
   
   partitionLogTags OBJECT-TYPE
      SYNTAX      OCTET STRING
      MAX-ACCESS  read-only
      STATUS      current
      DESCRIPTION "Return all tags on this Configuration MBean "
      ::= { partitionLogEntry 6  }
   
   
   partitionPropertyTable OBJECT-TYPE
      SYNTAX      SEQUENCE OF PartitionPropertyEntry
      MAX-ACCESS  not-accessible
      STATUS      current
      DESCRIPTION "The PartitionPropertyMBean is used when performing macro substitution from elements in the ResourceGroupTemplateMBean. If a macro is encountered in the ResourceGroupTemplate attribute, then the macro name will be used to locate the corresponding PartitionPropertyMBean and the value will be substituted accordingly.  Note that ConfigurationMBean contains getName/setName "
      ::= { wls 2180  }
      
   
   partitionPropertyEntry OBJECT-TYPE
      SYNTAX      PartitionPropertyEntry
      MAX-ACCESS  not-accessible
      STATUS      current
      DESCRIPTION "Generated SNMP Table Entry."
      INDEX { partitionPropertyIndex}
      ::= { partitionPropertyTable 1 }
      
   PartitionPropertyEntry ::=
      SEQUENCE
      {
         partitionPropertyIndex OCTET STRING,
         partitionPropertyObjectName OCTET STRING,
         partitionPropertyName OCTET STRING,
         partitionPropertyType OCTET STRING,
         partitionPropertyValue OCTET STRING,
         partitionPropertyTags OCTET STRING
      }
      
   
   partitionPropertyIndex OBJECT-TYPE
      SYNTAX      OCTET STRING
      MAX-ACCESS  not-accessible
      STATUS      current
      DESCRIPTION "Index column"
      ::= { partitionPropertyEntry 1  }
   
   
   partitionPropertyObjectName OBJECT-TYPE
      SYNTAX      OCTET STRING
      MAX-ACCESS  read-only
      STATUS      current
      DESCRIPTION "ObjectName column"
      ::= { partitionPropertyEntry 2  }
   
   
   partitionPropertyName OBJECT-TYPE
      SYNTAX      OCTET STRING
      MAX-ACCESS  read-only
      STATUS      current
      DESCRIPTION "The user-specified name of this MBean instance.  This name is included as one of the key properties in the MBean's javax.management.ObjectName:  Name=user-specified-name "
      ::= { partitionPropertyEntry 3  }
   
   
   partitionPropertyType OBJECT-TYPE
      SYNTAX      OCTET STRING
      MAX-ACCESS  read-only
      STATUS      current
      DESCRIPTION "Returns the type of the MBean. "
      ::= { partitionPropertyEntry 4  }
   
   
   partitionPropertyValue OBJECT-TYPE
      SYNTAX      OCTET STRING
      MAX-ACCESS  read-only
      STATUS      current
      DESCRIPTION "Get the value for the given macro "
      ::= { partitionPropertyEntry 5  }
   
   
   partitionPropertyTags OBJECT-TYPE
      SYNTAX      OCTET STRING
      MAX-ACCESS  read-only
      STATUS      current
      DESCRIPTION "Return all tags on this Configuration MBean "
      ::= { partitionPropertyEntry 6  }
   
   
   partitionWorkManagerTable OBJECT-TYPE
      SYNTAX      SEQUENCE OF PartitionWorkManagerEntry
      MAX-ACCESS  not-accessible
      STATUS      current
      DESCRIPTION "Specifies partition-level work manager policies that are configured by domain system administrators. "
      ::= { wls 2185  }
      
   
   partitionWorkManagerEntry OBJECT-TYPE
      SYNTAX      PartitionWorkManagerEntry
      MAX-ACCESS  not-accessible
      STATUS      current
      DESCRIPTION "Generated SNMP Table Entry."
      INDEX { partitionWorkManagerIndex}
      ::= { partitionWorkManagerTable 1 }
      
   PartitionWorkManagerEntry ::=
      SEQUENCE
      {
         partitionWorkManagerIndex OCTET STRING,
         partitionWorkManagerObjectName OCTET STRING,
         partitionWorkManagerMinThreadsConstraintCap Integer32,
         partitionWorkManagerName OCTET STRING,
         partitionWorkManagerMaxThreadsConstraint Integer32,
         partitionWorkManagerSharedCapacityPercent Integer32,
         partitionWorkManagerType OCTET STRING,
         partitionWorkManagerFairShare Integer32,
         partitionWorkManagerMaxThreadsConstraintQueueSize Integer32,
         partitionWorkManagerTags OCTET STRING
      }
      
   
   partitionWorkManagerIndex OBJECT-TYPE
      SYNTAX      OCTET STRING
      MAX-ACCESS  not-accessible
      STATUS      current
      DESCRIPTION "Index column"
      ::= { partitionWorkManagerEntry 1  }
   
   
   partitionWorkManagerObjectName OBJECT-TYPE
      SYNTAX      OCTET STRING
      MAX-ACCESS  read-only
      STATUS      current
      DESCRIPTION "ObjectName column"
      ::= { partitionWorkManagerEntry 2  }
   
   
   partitionWorkManagerMinThreadsConstraintCap OBJECT-TYPE
      SYNTAX      Integer32
      MAX-ACCESS  read-only
      STATUS      current
      DESCRIPTION "This imposes an upper limit on the number of standby threads that can be created for satisfying the minimum threads constraints configured in a partition. If the sum of the configured values of all minimum threads constraints in a partition exceeds this configured value, a warning message will be logged and WLS will limit the number of threads the self-tuning thread pool will allocate to the partition to satisfy its minimum threads constraints. A value of 0 means no limit is imposed on the partition. "
      ::= { partitionWorkManagerEntry 3  }
   
   
   partitionWorkManagerName OBJECT-TYPE
      SYNTAX      OCTET STRING
      MAX-ACCESS  read-only
      STATUS      current
      DESCRIPTION "The user-specified name of this MBean instance.  This name is included as one of the key properties in the MBean's javax.management.ObjectName:  Name=user-specified-name "
      ::= { partitionWorkManagerEntry 4  }
   
   
   partitionWorkManagerMaxThreadsConstraint OBJECT-TYPE
      SYNTAX      Integer32
      MAX-ACCESS  read-only
      STATUS      current
      DESCRIPTION "The maximum number of concurrent requests that the self-tuning thread pool can be processing on behalf of a partition at any given time. The default value of -1 means that this is only limited by the size of the self-tuning thread pool. "
      ::= { partitionWorkManagerEntry 5  }
   
   
   partitionWorkManagerSharedCapacityPercent OBJECT-TYPE
      SYNTAX      Integer32
      MAX-ACCESS  read-only
      STATUS      current
      DESCRIPTION "The total number of requests that can be present in the server for a partition, as a percentage of the sharedCapacityForWorkManagers attribute value in OverloadProtection MBean. This includes requests that are enqueued and those under execution. "
      ::= { partitionWorkManagerEntry 6  }
   
   
   partitionWorkManagerType OBJECT-TYPE
      SYNTAX      OCTET STRING
      MAX-ACCESS  read-only
      STATUS      current
      DESCRIPTION "Returns the type of the MBean. "
      ::= { partitionWorkManagerEntry 7  }
   
   
   partitionWorkManagerFairShare OBJECT-TYPE
      SYNTAX      Integer32
      MAX-ACCESS  read-only
      STATUS      current
      DESCRIPTION "A desired percentage of thread usage by a partition compared to the thread usage by all partitions. It is recommended that the sum of this value for all the partitions running in a WLS domain add up to 100, but it is not strictly enforced. When they do not add up to 100, WLS assigns thread-usage times to different partitions based on their relative values. "
      ::= { partitionWorkManagerEntry 8  }
   
   
   partitionWorkManagerMaxThreadsConstraintQueueSize OBJECT-TYPE
      SYNTAX      Integer32
      MAX-ACCESS  read-only
      STATUS      current
      DESCRIPTION "Desired size of the Partition MaxThreadsConstraint queue for requests pending execution. "
      ::= { partitionWorkManagerEntry 9  }
   
   
   partitionWorkManagerTags OBJECT-TYPE
      SYNTAX      OCTET STRING
      MAX-ACCESS  read-only
      STATUS      current
      DESCRIPTION "Return all tags on this Configuration MBean "
      ::= { partitionWorkManagerEntry 10  }
   
   
   postProcessorScriptTable OBJECT-TYPE
      SYNTAX      SEQUENCE OF PostProcessorScriptEntry
      MAX-ACCESS  not-accessible
      STATUS      current
      DESCRIPTION "This interface provides configuration for a post-processor script "
      ::= { wls 2190  }
      
   
   postProcessorScriptEntry OBJECT-TYPE
      SYNTAX      PostProcessorScriptEntry
      MAX-ACCESS  not-accessible
      STATUS      current
      DESCRIPTION "Generated SNMP Table Entry."
      INDEX { postProcessorScriptIndex}
      ::= { postProcessorScriptTable 1 }
      
   PostProcessorScriptEntry ::=
      SEQUENCE
      {
         postProcessorScriptIndex OCTET STRING,
         postProcessorScriptObjectName OCTET STRING,
         postProcessorScriptWorkingDirectory OCTET STRING,
         postProcessorScriptTimeoutInSeconds Integer32,
         postProcessorScriptArguments OCTET STRING,
         postProcessorScriptNumberOfRetriesAllowed Integer32,
         postProcessorScriptRetryDelayInMillis Counter64,
         postProcessorScriptPathToScript OCTET STRING,
         postProcessorScriptName OCTET STRING,
         postProcessorScriptType OCTET STRING,
         postProcessorScriptIgnoreFailures OCTET STRING,
         postProcessorScriptPathToErrorHandlerScript OCTET STRING,
         postProcessorScriptTags OCTET STRING
      }
      
   
   postProcessorScriptIndex OBJECT-TYPE
      SYNTAX      OCTET STRING
      MAX-ACCESS  not-accessible
      STATUS      current
      DESCRIPTION "Index column"
      ::= { postProcessorScriptEntry 1  }
   
   
   postProcessorScriptObjectName OBJECT-TYPE
      SYNTAX      OCTET STRING
      MAX-ACCESS  read-only
      STATUS      current
      DESCRIPTION "ObjectName column"
      ::= { postProcessorScriptEntry 2  }
   
   
   postProcessorScriptWorkingDirectory OBJECT-TYPE
      SYNTAX      OCTET STRING
      MAX-ACCESS  read-only
      STATUS      current
      DESCRIPTION " "
      ::= { postProcessorScriptEntry 3  }
   
   
   postProcessorScriptTimeoutInSeconds OBJECT-TYPE
      SYNTAX      Integer32
      MAX-ACCESS  read-only
      STATUS      current
      DESCRIPTION "Returns the timeout interval for script execution in seconds. A zero or negative timeout will imply no timeout. "
      ::= { postProcessorScriptEntry 4  }
   
   
   postProcessorScriptArguments OBJECT-TYPE
      SYNTAX      OCTET STRING
      MAX-ACCESS  read-only
      STATUS      current
      DESCRIPTION "The arguments to the command script as well as for the error-handler script "
      ::= { postProcessorScriptEntry 5  }
   
   
   postProcessorScriptNumberOfRetriesAllowed OBJECT-TYPE
      SYNTAX      Integer32
      MAX-ACCESS  read-only
      STATUS      current
      DESCRIPTION " "
      ::= { postProcessorScriptEntry 6  }
   
   
   postProcessorScriptRetryDelayInMillis OBJECT-TYPE
      SYNTAX      Counter64
      MAX-ACCESS  read-only
      STATUS      current
      DESCRIPTION " "
      ::= { postProcessorScriptEntry 7  }
   
   
   postProcessorScriptPathToScript OBJECT-TYPE
      SYNTAX      OCTET STRING
      MAX-ACCESS  read-only
      STATUS      current
      DESCRIPTION "Returns the path to the script to be executed. If null or empty, the script will not be executed. The value should be the path to the script program. If the command is not set, the script is effectively disabled. When specified as a relative path, it will be relative to DomainDir/bin/scripts directory. When specified as an absolute path, the script must be under DomainDir/bin/scripts directory. "
      ::= { postProcessorScriptEntry 8  }
   
   
   postProcessorScriptName OBJECT-TYPE
      SYNTAX      OCTET STRING
      MAX-ACCESS  read-only
      STATUS      current
      DESCRIPTION "The user-specified name of this MBean instance.  This name is included as one of the key properties in the MBean's javax.management.ObjectName:  Name=user-specified-name "
      ::= { postProcessorScriptEntry 9  }
   
   
   postProcessorScriptType OBJECT-TYPE
      SYNTAX      OCTET STRING
      MAX-ACCESS  read-only
      STATUS      current
      DESCRIPTION "Returns the type of the MBean. "
      ::= { postProcessorScriptEntry 10  }
   
   
   postProcessorScriptIgnoreFailures OBJECT-TYPE
      SYNTAX      OCTET STRING
      MAX-ACCESS  read-only
      STATUS      current
      DESCRIPTION " "
      ::= { postProcessorScriptEntry 11  }
   
   
   postProcessorScriptPathToErrorHandlerScript OBJECT-TYPE
      SYNTAX      OCTET STRING
      MAX-ACCESS  read-only
      STATUS      current
      DESCRIPTION "Returns the path to the error handler script to be executed. If null or empty, the script will not be executed. The value should be the path to the script program. If the command is not set, the error handler is effectively disabled. Note that the error handler script is executed using the same arguments and and environment as the command script. When specified as a relative path, it will be relative to DomainDir/bin/scripts directory. When specified as an absolute path, the script must be under DomainDir/bin/scripts directory. "
      ::= { postProcessorScriptEntry 12  }
   
   
   postProcessorScriptTags OBJECT-TYPE
      SYNTAX      OCTET STRING
      MAX-ACCESS  read-only
      STATUS      current
      DESCRIPTION "Return all tags on this Configuration MBean "
      ::= { postProcessorScriptEntry 13  }
   
   
   preProcessorScriptTable OBJECT-TYPE
      SYNTAX      SEQUENCE OF PreProcessorScriptEntry
      MAX-ACCESS  not-accessible
      STATUS      current
      DESCRIPTION "This interface provides configuration for a pre-processor script "
      ::= { wls 2195  }
      
   
   preProcessorScriptEntry OBJECT-TYPE
      SYNTAX      PreProcessorScriptEntry
      MAX-ACCESS  not-accessible
      STATUS      current
      DESCRIPTION "Generated SNMP Table Entry."
      INDEX { preProcessorScriptIndex}
      ::= { preProcessorScriptTable 1 }
      
   PreProcessorScriptEntry ::=
      SEQUENCE
      {
         preProcessorScriptIndex OCTET STRING,
         preProcessorScriptObjectName OCTET STRING,
         preProcessorScriptWorkingDirectory OCTET STRING,
         preProcessorScriptTimeoutInSeconds Integer32,
         preProcessorScriptArguments OCTET STRING,
         preProcessorScriptNumberOfRetriesAllowed Integer32,
         preProcessorScriptRetryDelayInMillis Counter64,
         preProcessorScriptPathToScript OCTET STRING,
         preProcessorScriptName OCTET STRING,
         preProcessorScriptType OCTET STRING,
         preProcessorScriptIgnoreFailures OCTET STRING,
         preProcessorScriptPathToErrorHandlerScript OCTET STRING,
         preProcessorScriptTags OCTET STRING
      }
      
   
   preProcessorScriptIndex OBJECT-TYPE
      SYNTAX      OCTET STRING
      MAX-ACCESS  not-accessible
      STATUS      current
      DESCRIPTION "Index column"
      ::= { preProcessorScriptEntry 1  }
   
   
   preProcessorScriptObjectName OBJECT-TYPE
      SYNTAX      OCTET STRING
      MAX-ACCESS  read-only
      STATUS      current
      DESCRIPTION "ObjectName column"
      ::= { preProcessorScriptEntry 2  }
   
   
   preProcessorScriptWorkingDirectory OBJECT-TYPE
      SYNTAX      OCTET STRING
      MAX-ACCESS  read-only
      STATUS      current
      DESCRIPTION " "
      ::= { preProcessorScriptEntry 3  }
   
   
   preProcessorScriptTimeoutInSeconds OBJECT-TYPE
      SYNTAX      Integer32
      MAX-ACCESS  read-only
      STATUS      current
      DESCRIPTION "Returns the timeout interval for script execution in seconds. A zero or negative timeout will imply no timeout. "
      ::= { preProcessorScriptEntry 4  }
   
   
   preProcessorScriptArguments OBJECT-TYPE
      SYNTAX      OCTET STRING
      MAX-ACCESS  read-only
      STATUS      current
      DESCRIPTION "The arguments to the command script as well as for the error-handler script "
      ::= { preProcessorScriptEntry 5  }
   
   
   preProcessorScriptNumberOfRetriesAllowed OBJECT-TYPE
      SYNTAX      Integer32
      MAX-ACCESS  read-only
      STATUS      current
      DESCRIPTION " "
      ::= { preProcessorScriptEntry 6  }
   
   
   preProcessorScriptRetryDelayInMillis OBJECT-TYPE
      SYNTAX      Counter64
      MAX-ACCESS  read-only
      STATUS      current
      DESCRIPTION " "
      ::= { preProcessorScriptEntry 7  }
   
   
   preProcessorScriptPathToScript OBJECT-TYPE
      SYNTAX      OCTET STRING
      MAX-ACCESS  read-only
      STATUS      current
      DESCRIPTION "Returns the path to the script to be executed. If null or empty, the script will not be executed. The value should be the path to the script program. If the command is not set, the script is effectively disabled. When specified as a relative path, it will be relative to DomainDir/bin/scripts directory. When specified as an absolute path, the script must be under DomainDir/bin/scripts directory. "
      ::= { preProcessorScriptEntry 8  }
   
   
   preProcessorScriptName OBJECT-TYPE
      SYNTAX      OCTET STRING
      MAX-ACCESS  read-only
      STATUS      current
      DESCRIPTION "The user-specified name of this MBean instance.  This name is included as one of the key properties in the MBean's javax.management.ObjectName:  Name=user-specified-name "
      ::= { preProcessorScriptEntry 9  }
   
   
   preProcessorScriptType OBJECT-TYPE
      SYNTAX      OCTET STRING
      MAX-ACCESS  read-only
      STATUS      current
      DESCRIPTION "Returns the type of the MBean. "
      ::= { preProcessorScriptEntry 10  }
   
   
   preProcessorScriptIgnoreFailures OBJECT-TYPE
      SYNTAX      OCTET STRING
      MAX-ACCESS  read-only
      STATUS      current
      DESCRIPTION " "
      ::= { preProcessorScriptEntry 11  }
   
   
   preProcessorScriptPathToErrorHandlerScript OBJECT-TYPE
      SYNTAX      OCTET STRING
      MAX-ACCESS  read-only
      STATUS      current
      DESCRIPTION "Returns the path to the error handler script to be executed. If null or empty, the script will not be executed. The value should be the path to the script program. If the command is not set, the error handler is effectively disabled. Note that the error handler script is executed using the same arguments and and environment as the command script. When specified as a relative path, it will be relative to DomainDir/bin/scripts directory. When specified as an absolute path, the script must be under DomainDir/bin/scripts directory. "
      ::= { preProcessorScriptEntry 12  }
   
   
   preProcessorScriptTags OBJECT-TYPE
      SYNTAX      OCTET STRING
      MAX-ACCESS  read-only
      STATUS      current
      DESCRIPTION "Return all tags on this Configuration MBean "
      ::= { preProcessorScriptEntry 13  }
   
   
   resourceGroupTable OBJECT-TYPE
      SYNTAX      SEQUENCE OF ResourceGroupEntry
      MAX-ACCESS  not-accessible
      STATUS      current
      DESCRIPTION "A resource group is a named collection of deployable resources. Typically the resources in a given resource group are related in some way, for example in that they make up a single application suite. "
      ::= { wls 2200  }
      
   
   resourceGroupEntry OBJECT-TYPE
      SYNTAX      ResourceGroupEntry
      MAX-ACCESS  not-accessible
      STATUS      current
      DESCRIPTION "Generated SNMP Table Entry."
      INDEX { resourceGroupIndex}
      ::= { resourceGroupTable 1 }
      
   ResourceGroupEntry ::=
      SEQUENCE
      {
         resourceGroupIndex   OCTET STRING,
         resourceGroupObjectName OCTET STRING,
         resourceGroupUploadDirectoryName OCTET STRING,
         resourceGroupName    OCTET STRING,
         resourceGroupUseDefaultTarget OCTET STRING,
         resourceGroupTags    OCTET STRING,
         resourceGroupType    OCTET STRING,
         resourceGroupAdministrative OCTET STRING,
         resourceGroupAutoTargetAdminServer OCTET STRING
      }
      
   
   resourceGroupIndex OBJECT-TYPE
      SYNTAX      OCTET STRING
      MAX-ACCESS  not-accessible
      STATUS      current
      DESCRIPTION "Index column"
      ::= { resourceGroupEntry 1  }
   
   
   resourceGroupObjectName OBJECT-TYPE
      SYNTAX      OCTET STRING
      MAX-ACCESS  read-only
      STATUS      current
      DESCRIPTION "ObjectName column"
      ::= { resourceGroupEntry 2  }
   
   
   resourceGroupUploadDirectoryName OBJECT-TYPE
      SYNTAX      OCTET STRING
      MAX-ACCESS  read-only
      STATUS      current
      DESCRIPTION "The directory path on the Administration Server where the uploaded applications for this resource group template are placed. "
      ::= { resourceGroupEntry 3  }
   
   
   resourceGroupName OBJECT-TYPE
      SYNTAX      OCTET STRING
      MAX-ACCESS  read-only
      STATUS      current
      DESCRIPTION "The user-specified name of this MBean instance.  This name is included as one of the key properties in the MBean's javax.management.ObjectName:  Name=user-specified-name "
      ::= { resourceGroupEntry 4  }
   
   
   resourceGroupUseDefaultTarget OBJECT-TYPE
      SYNTAX      OCTET STRING
      MAX-ACCESS  read-only
      STATUS      current
      DESCRIPTION "Checks whether this resource group uses the default target from the partition that contains the resource group. "
      ::= { resourceGroupEntry 5  }
   
   
   resourceGroupTags OBJECT-TYPE
      SYNTAX      OCTET STRING
      MAX-ACCESS  read-only
      STATUS      current
      DESCRIPTION "Return all tags on this Configuration MBean "
      ::= { resourceGroupEntry 6  }
   
   
   resourceGroupType OBJECT-TYPE
      SYNTAX      OCTET STRING
      MAX-ACCESS  read-only
      STATUS      current
      DESCRIPTION "Returns the type of the MBean. "
      ::= { resourceGroupEntry 7  }
   
   
   resourceGroupAdministrative OBJECT-TYPE
      SYNTAX      OCTET STRING
      MAX-ACCESS  read-only
      STATUS      current
      DESCRIPTION "Does this resource group contain administrative applications and resources? If true, then this is considered an administrative resource group and will be handled differently by the partition lifecycle. Specifically, an administrative resource group will be left running when a partition is shut down (it will be shut down only when the partition is halted).  Note that this Boolean is independent of the targeting of the resource group and works independently of the autoTargetAdminServer Boolean. "
      ::= { resourceGroupEntry 8  }
   
   
   resourceGroupAutoTargetAdminServer OBJECT-TYPE
      SYNTAX      OCTET STRING
      MAX-ACCESS  read-only
      STATUS      current
      DESCRIPTION "Should this resource group always be targeted to the Administration Server? If true, then this resource group will be targeted to the domain's Administration Server using the partition's administrative virtual target (AdminVT) in addition to any targets explicitly set on the resource group. Functionally, this is similar to getting the partition's administrative virtual target and explicitly adding it to the list of resource group targets. "
      ::= { resourceGroupEntry 9  }
   
   
   resourceManagementTable OBJECT-TYPE
      SYNTAX      SEQUENCE OF ResourceManagementEntry
      MAX-ACCESS  not-accessible
      STATUS      current
      DESCRIPTION "This MBean is used to create and edit resource management policy configurations (Resource Managers) for the domain.  Partition-scoped resource managers can be created under {@code PartitionMBean}. "
      ::= { wls 2205  }
      
   
   resourceManagementEntry OBJECT-TYPE
      SYNTAX      ResourceManagementEntry
      MAX-ACCESS  not-accessible
      STATUS      current
      DESCRIPTION "Generated SNMP Table Entry."
      INDEX { resourceManagementIndex}
      ::= { resourceManagementTable 1 }
      
   ResourceManagementEntry ::=
      SEQUENCE
      {
         resourceManagementIndex OCTET STRING,
         resourceManagementObjectName OCTET STRING,
         resourceManagementName OCTET STRING,
         resourceManagementType OCTET STRING,
         resourceManagementTags OCTET STRING
      }
      
   
   resourceManagementIndex OBJECT-TYPE
      SYNTAX      OCTET STRING
      MAX-ACCESS  not-accessible
      STATUS      current
      DESCRIPTION "Index column"
      ::= { resourceManagementEntry 1  }
   
   
   resourceManagementObjectName OBJECT-TYPE
      SYNTAX      OCTET STRING
      MAX-ACCESS  read-only
      STATUS      current
      DESCRIPTION "ObjectName column"
      ::= { resourceManagementEntry 2  }
   
   
   resourceManagementName OBJECT-TYPE
      SYNTAX      OCTET STRING
      MAX-ACCESS  read-only
      STATUS      current
      DESCRIPTION "The user-specified name of this MBean instance.  This name is included as one of the key properties in the MBean's javax.management.ObjectName:  Name=user-specified-name "
      ::= { resourceManagementEntry 3  }
   
   
   resourceManagementType OBJECT-TYPE
      SYNTAX      OCTET STRING
      MAX-ACCESS  read-only
      STATUS      current
      DESCRIPTION "Returns the type of the MBean. "
      ::= { resourceManagementEntry 4  }
   
   
   resourceManagementTags OBJECT-TYPE
      SYNTAX      OCTET STRING
      MAX-ACCESS  read-only
      STATUS      current
      DESCRIPTION "Return all tags on this Configuration MBean "
      ::= { resourceManagementEntry 5  }
   
   
   resourceManagerTable OBJECT-TYPE
      SYNTAX      SEQUENCE OF ResourceManagerEntry
      MAX-ACCESS  not-accessible
      STATUS      current
      DESCRIPTION " A {@code ResourceManagerMBean} represents a resource consumption management policy. A policy controls and governs the use of shared resources in a Server runtime, by a Partition that the policy is attached to. A resource manager holds information on constraints and recourse actions for different resources in a Server instance.   A system administrator defines a resource manager and configures child MBeans that represent particular combinations of shares and usage limits of various resources in the Server runtime.   The system administrator may then assign the resource manager to one or more Partitions to ensure fair allocation of shared resources to collocated Domain Partitions, and to ensure that one Partition doesn't exhaust shared resources (potentially affecting other collocated Partitions).   The set of resources on which resource management policies can be assigned to, and the child MBeans through which they can be configured are:   File Open: {@link FileOpenMBean} Heap Retained: {@link HeapRetainedMBean} CPU Utilization: {@link CpuUtilizationMBean}  "
      ::= { wls 2210  }
      
   
   resourceManagerEntry OBJECT-TYPE
      SYNTAX      ResourceManagerEntry
      MAX-ACCESS  not-accessible
      STATUS      current
      DESCRIPTION "Generated SNMP Table Entry."
      INDEX { resourceManagerIndex}
      ::= { resourceManagerTable 1 }
      
   ResourceManagerEntry ::=
      SEQUENCE
      {
         resourceManagerIndex OCTET STRING,
         resourceManagerObjectName OCTET STRING,
         resourceManagerName  OCTET STRING,
         resourceManagerType  OCTET STRING,
         resourceManagerTags  OCTET STRING
      }
      
   
   resourceManagerIndex OBJECT-TYPE
      SYNTAX      OCTET STRING
      MAX-ACCESS  not-accessible
      STATUS      current
      DESCRIPTION "Index column"
      ::= { resourceManagerEntry 1  }
   
   
   resourceManagerObjectName OBJECT-TYPE
      SYNTAX      OCTET STRING
      MAX-ACCESS  read-only
      STATUS      current
      DESCRIPTION "ObjectName column"
      ::= { resourceManagerEntry 2  }
   
   
   resourceManagerName OBJECT-TYPE
      SYNTAX      OCTET STRING
      MAX-ACCESS  read-only
      STATUS      current
      DESCRIPTION "The user-specified name of this MBean instance.  This name is included as one of the key properties in the MBean's javax.management.ObjectName:  Name=user-specified-name "
      ::= { resourceManagerEntry 3  }
   
   
   resourceManagerType OBJECT-TYPE
      SYNTAX      OCTET STRING
      MAX-ACCESS  read-only
      STATUS      current
      DESCRIPTION "Returns the type of the MBean. "
      ::= { resourceManagerEntry 4  }
   
   
   resourceManagerTags OBJECT-TYPE
      SYNTAX      OCTET STRING
      MAX-ACCESS  read-only
      STATUS      current
      DESCRIPTION "Return all tags on this Configuration MBean "
      ::= { resourceManagerEntry 5  }
   
   
   runawayThreadsTable OBJECT-TYPE
      SYNTAX      SEQUENCE OF RunawayThreadsEntry
      MAX-ACCESS  not-accessible
      STATUS      current
      DESCRIPTION "This mbean is used to configure Runaway Threads Resource for Resource Consumption Management. "
      ::= { wls 2215  }
      
   
   runawayThreadsEntry OBJECT-TYPE
      SYNTAX      RunawayThreadsEntry
      MAX-ACCESS  not-accessible
      STATUS      current
      DESCRIPTION "Generated SNMP Table Entry."
      INDEX { runawayThreadsIndex}
      ::= { runawayThreadsTable 1 }
      
   RunawayThreadsEntry ::=
      SEQUENCE
      {
         runawayThreadsIndex  OCTET STRING,
         runawayThreadsObjectName OCTET STRING,
         runawayThreadsName   OCTET STRING,
         runawayThreadsType   OCTET STRING,
         runawayThreadsTags   OCTET STRING
      }
      
   
   runawayThreadsIndex OBJECT-TYPE
      SYNTAX      OCTET STRING
      MAX-ACCESS  not-accessible
      STATUS      current
      DESCRIPTION "Index column"
      ::= { runawayThreadsEntry 1  }
   
   
   runawayThreadsObjectName OBJECT-TYPE
      SYNTAX      OCTET STRING
      MAX-ACCESS  read-only
      STATUS      current
      DESCRIPTION "ObjectName column"
      ::= { runawayThreadsEntry 2  }
   
   
   runawayThreadsName OBJECT-TYPE
      SYNTAX      OCTET STRING
      MAX-ACCESS  read-only
      STATUS      current
      DESCRIPTION "The user-specified name of this MBean instance.  This name is included as one of the key properties in the MBean's javax.management.ObjectName:  Name=user-specified-name "
      ::= { runawayThreadsEntry 3  }
   
   
   runawayThreadsType OBJECT-TYPE
      SYNTAX      OCTET STRING
      MAX-ACCESS  read-only
      STATUS      current
      DESCRIPTION "Returns the type of the MBean. "
      ::= { runawayThreadsEntry 4  }
   
   
   runawayThreadsTags OBJECT-TYPE
      SYNTAX      OCTET STRING
      MAX-ACCESS  read-only
      STATUS      current
      DESCRIPTION "Return all tags on this Configuration MBean "
      ::= { runawayThreadsEntry 5  }
   
   
   scriptInterceptorTable OBJECT-TYPE
      SYNTAX      SEQUENCE OF ScriptInterceptorEntry
      MAX-ACCESS  not-accessible
      STATUS      current
      DESCRIPTION "This interface provides configuration for a script interceptor. "
      ::= { wls 2220  }
      
   
   scriptInterceptorEntry OBJECT-TYPE
      SYNTAX      ScriptInterceptorEntry
      MAX-ACCESS  not-accessible
      STATUS      current
      DESCRIPTION "Generated SNMP Table Entry."
      INDEX { scriptInterceptorIndex}
      ::= { scriptInterceptorTable 1 }
      
   ScriptInterceptorEntry ::=
      SEQUENCE
      {
         scriptInterceptorIndex OCTET STRING,
         scriptInterceptorObjectName OCTET STRING,
         scriptInterceptorInterceptorTypeName OCTET STRING,
         scriptInterceptorPriority Integer32,
         scriptInterceptorInterceptedOperationNames OCTET STRING,
         scriptInterceptorApplicableClusterNames OCTET STRING,
         scriptInterceptorName OCTET STRING,
         scriptInterceptorInterceptedTargetKey OCTET STRING,
         scriptInterceptorDependsOn OCTET STRING,
         scriptInterceptorType OCTET STRING,
         scriptInterceptorTags OCTET STRING
      }
      
   
   scriptInterceptorIndex OBJECT-TYPE
      SYNTAX      OCTET STRING
      MAX-ACCESS  not-accessible
      STATUS      current
      DESCRIPTION "Index column"
      ::= { scriptInterceptorEntry 1  }
   
   
   scriptInterceptorObjectName OBJECT-TYPE
      SYNTAX      OCTET STRING
      MAX-ACCESS  read-only
      STATUS      current
      DESCRIPTION "ObjectName column"
      ::= { scriptInterceptorEntry 2  }
   
   
   scriptInterceptorInterceptorTypeName OBJECT-TYPE
      SYNTAX      OCTET STRING
      MAX-ACCESS  read-only
      STATUS      current
      DESCRIPTION "The HK2 name of the interceptor class. "
      ::= { scriptInterceptorEntry 3  }
   
   
   scriptInterceptorPriority OBJECT-TYPE
      SYNTAX      Integer32
      MAX-ACCESS  read-only
      STATUS      current
      DESCRIPTION "The priority of this intercepted method in the interceptor chain. An interceptor with a higher priority will be executed earlier than an interceptor with a lower priority. Note:  1073741823 is actually Integer.MAX_VALUE / 2 as defined in InterceptorPriorities. "
      ::= { scriptInterceptorEntry 4  }
   
   
   scriptInterceptorInterceptedOperationNames OBJECT-TYPE
      SYNTAX      OCTET STRING
      MAX-ACCESS  read-only
      STATUS      current
      DESCRIPTION "The name of the operation / method that needs to intercepted by this interceptor's method. If the return value is null or '*' then all operations are intercepted by this interceptor. "
      ::= { scriptInterceptorEntry 5  }
   
   
   scriptInterceptorApplicableClusterNames OBJECT-TYPE
      SYNTAX      OCTET STRING
      MAX-ACCESS  read-only
      STATUS      current
      DESCRIPTION " "
      ::= { scriptInterceptorEntry 6  }
   
   
   scriptInterceptorName OBJECT-TYPE
      SYNTAX      OCTET STRING
      MAX-ACCESS  read-only
      STATUS      current
      DESCRIPTION "The user-specified name of this MBean instance.  This name is included as one of the key properties in the MBean's javax.management.ObjectName:  Name=user-specified-name "
      ::= { scriptInterceptorEntry 7  }
   
   
   scriptInterceptorInterceptedTargetKey OBJECT-TYPE
      SYNTAX      OCTET STRING
      MAX-ACCESS  read-only
      STATUS      current
      DESCRIPTION "The key associated with the intercepted target. This is the value that would have been specified in the @InterceptedTargetKey annotation. If this is null then this Interceptor is ignored. "
      ::= { scriptInterceptorEntry 8  }
   
   
   scriptInterceptorDependsOn OBJECT-TYPE
      SYNTAX      OCTET STRING
      MAX-ACCESS  read-only
      STATUS      current
      DESCRIPTION "The set of interceptor names this interceptor depends on. The specified interceptors will appear before this interceptor in the invocation chain. "
      ::= { scriptInterceptorEntry 9  }
   
   
   scriptInterceptorType OBJECT-TYPE
      SYNTAX      OCTET STRING
      MAX-ACCESS  read-only
      STATUS      current
      DESCRIPTION "Returns the type of the MBean. "
      ::= { scriptInterceptorEntry 10  }
   
   
   scriptInterceptorTags OBJECT-TYPE
      SYNTAX      OCTET STRING
      MAX-ACCESS  read-only
      STATUS      current
      DESCRIPTION "Return all tags on this Configuration MBean "
      ::= { scriptInterceptorEntry 11  }
   
   
   systemComponentConfigurationTable OBJECT-TYPE
      SYNTAX      SEQUENCE OF SystemComponentConfigurationEntry
      MAX-ACCESS  not-accessible
      STATUS      current
      DESCRIPTION "A System Component Configuration MBean allows configuration to be shared between one or more System Components. "
      ::= { wls 2225  }
      
   
   systemComponentConfigurationEntry OBJECT-TYPE
      SYNTAX      SystemComponentConfigurationEntry
      MAX-ACCESS  not-accessible
      STATUS      current
      DESCRIPTION "Generated SNMP Table Entry."
      INDEX { systemComponentConfigurationIndex}
      ::= { systemComponentConfigurationTable 1 }
      
   SystemComponentConfigurationEntry ::=
      SEQUENCE
      {
         systemComponentConfigurationIndex OCTET STRING,
         systemComponentConfigurationObjectName OCTET STRING,
         systemComponentConfigurationComponentType OCTET STRING,
         systemComponentConfigurationName OCTET STRING,
         systemComponentConfigurationSourcePath OCTET STRING,
         systemComponentConfigurationType OCTET STRING,
         systemComponentConfigurationTags OCTET STRING
      }
      
   
   systemComponentConfigurationIndex OBJECT-TYPE
      SYNTAX      OCTET STRING
      MAX-ACCESS  not-accessible
      STATUS      current
      DESCRIPTION "Index column"
      ::= { systemComponentConfigurationEntry 1  }
   
   
   systemComponentConfigurationObjectName OBJECT-TYPE
      SYNTAX      OCTET STRING
      MAX-ACCESS  read-only
      STATUS      current
      DESCRIPTION "ObjectName column"
      ::= { systemComponentConfigurationEntry 2  }
   
   
   systemComponentConfigurationComponentType OBJECT-TYPE
      SYNTAX      OCTET STRING
      MAX-ACCESS  read-only
      STATUS      current
      DESCRIPTION "Get the system component type Examples of types may include 'OHS', 'Coherence'. New System Components may be added in the future so the list of types is not static. "
      ::= { systemComponentConfigurationEntry 3  }
   
   
   systemComponentConfigurationName OBJECT-TYPE
      SYNTAX      OCTET STRING
      MAX-ACCESS  read-only
      STATUS      current
      DESCRIPTION "The user-specified name of this MBean instance.  This name is included as one of the key properties in the MBean's javax.management.ObjectName:  Name=user-specified-name "
      ::= { systemComponentConfigurationEntry 4  }
   
   
   systemComponentConfigurationSourcePath OBJECT-TYPE
      SYNTAX      OCTET STRING
      MAX-ACCESS  read-only
      STATUS      current
      DESCRIPTION "Get the source path for configuration files Note: if you use a SystemComponentConfiguration, then the files for the SystemComponents directory are not used so there is no chance of conflict. "
      ::= { systemComponentConfigurationEntry 5  }
   
   
   systemComponentConfigurationType OBJECT-TYPE
      SYNTAX      OCTET STRING
      MAX-ACCESS  read-only
      STATUS      current
      DESCRIPTION "Returns the type of the MBean. "
      ::= { systemComponentConfigurationEntry 6  }
   
   
   systemComponentConfigurationTags OBJECT-TYPE
      SYNTAX      OCTET STRING
      MAX-ACCESS  read-only
      STATUS      current
      DESCRIPTION "Return all tags on this Configuration MBean "
      ::= { systemComponentConfigurationEntry 7  }
   
   
   threadRunningTable OBJECT-TYPE
      SYNTAX      SEQUENCE OF ThreadRunningEntry
      MAX-ACCESS  not-accessible
      STATUS      current
      DESCRIPTION "This mbean is used to configure Number of Thread Resource for Resource Consumption Management. "
      ::= { wls 2230  }
      
   
   threadRunningEntry OBJECT-TYPE
      SYNTAX      ThreadRunningEntry
      MAX-ACCESS  not-accessible
      STATUS      current
      DESCRIPTION "Generated SNMP Table Entry."
      INDEX { threadRunningIndex}
      ::= { threadRunningTable 1 }
      
   ThreadRunningEntry ::=
      SEQUENCE
      {
         threadRunningIndex   OCTET STRING,
         threadRunningObjectName OCTET STRING,
         threadRunningName    OCTET STRING,
         threadRunningType    OCTET STRING,
         threadRunningTags    OCTET STRING
      }
      
   
   threadRunningIndex OBJECT-TYPE
      SYNTAX      OCTET STRING
      MAX-ACCESS  not-accessible
      STATUS      current
      DESCRIPTION "Index column"
      ::= { threadRunningEntry 1  }
   
   
   threadRunningObjectName OBJECT-TYPE
      SYNTAX      OCTET STRING
      MAX-ACCESS  read-only
      STATUS      current
      DESCRIPTION "ObjectName column"
      ::= { threadRunningEntry 2  }
   
   
   threadRunningName OBJECT-TYPE
      SYNTAX      OCTET STRING
      MAX-ACCESS  read-only
      STATUS      current
      DESCRIPTION "The user-specified name of this MBean instance.  This name is included as one of the key properties in the MBean's javax.management.ObjectName:  Name=user-specified-name "
      ::= { threadRunningEntry 3  }
   
   
   threadRunningType OBJECT-TYPE
      SYNTAX      OCTET STRING
      MAX-ACCESS  read-only
      STATUS      current
      DESCRIPTION "Returns the type of the MBean. "
      ::= { threadRunningEntry 4  }
   
   
   threadRunningTags OBJECT-TYPE
      SYNTAX      OCTET STRING
      MAX-ACCESS  read-only
      STATUS      current
      DESCRIPTION "Return all tags on this Configuration MBean "
      ::= { threadRunningEntry 5  }
   
   
   triggerTable OBJECT-TYPE
      SYNTAX      SEQUENCE OF TriggerEntry
      MAX-ACCESS  not-accessible
      STATUS      current
      DESCRIPTION "This mbean is used to configure a Trigger (Usage limit) based policy for a resource type. "
      ::= { wls 2235  }
      
   
   triggerEntry OBJECT-TYPE
      SYNTAX      TriggerEntry
      MAX-ACCESS  not-accessible
      STATUS      current
      DESCRIPTION "Generated SNMP Table Entry."
      INDEX { triggerIndex}
      ::= { triggerTable 1 }
      
   TriggerEntry ::=
      SEQUENCE
      {
         triggerIndex         OCTET STRING,
         triggerObjectName    OCTET STRING,
         triggerAction        OCTET STRING,
         triggerName          OCTET STRING,
         triggerType          OCTET STRING,
         triggerValue         Counter64,
         triggerTags          OCTET STRING
      }
      
   
   triggerIndex OBJECT-TYPE
      SYNTAX      OCTET STRING
      MAX-ACCESS  not-accessible
      STATUS      current
      DESCRIPTION "Index column"
      ::= { triggerEntry 1  }
   
   
   triggerObjectName OBJECT-TYPE
      SYNTAX      OCTET STRING
      MAX-ACCESS  read-only
      STATUS      current
      DESCRIPTION "ObjectName column"
      ::= { triggerEntry 2  }
   
   
   triggerAction OBJECT-TYPE
      SYNTAX      OCTET STRING
      MAX-ACCESS  read-only
      STATUS      current
      DESCRIPTION "Gets the configured recourse action that needs to be taken when the usage of resource crosses the value specified in {@link #getValue()}. "
      ::= { triggerEntry 3  }
   
   
   triggerName OBJECT-TYPE
      SYNTAX      OCTET STRING
      MAX-ACCESS  read-only
      STATUS      current
      DESCRIPTION "The user-specified name of this MBean instance.  This name is included as one of the key properties in the MBean's javax.management.ObjectName:  Name=user-specified-name "
      ::= { triggerEntry 4  }
   
   
   triggerType OBJECT-TYPE
      SYNTAX      OCTET STRING
      MAX-ACCESS  read-only
      STATUS      current
      DESCRIPTION "Returns the type of the MBean. "
      ::= { triggerEntry 5  }
   
   
   triggerValue OBJECT-TYPE
      SYNTAX      Counter64
      MAX-ACCESS  read-only
      STATUS      current
      DESCRIPTION "Gets the upper-limit value of the resource assigned to the Trigger configuration. "
      ::= { triggerEntry 6  }
   
   
   triggerTags OBJECT-TYPE
      SYNTAX      OCTET STRING
      MAX-ACCESS  read-only
      STATUS      current
      DESCRIPTION "Return all tags on this Configuration MBean "
      ::= { triggerEntry 7  }
   
   
   virtualTargetTable OBJECT-TYPE
      SYNTAX      SEQUENCE OF VirtualTargetEntry
      MAX-ACCESS  not-accessible
      STATUS      current
      DESCRIPTION "This bean represents a target for a resource group in a partition. It defines access point to resources, i.e. hostname, port, partition uri path. Moreover, it provide configurations for each protocol, for example, http, t3, ssl, iiop etc. "
      ::= { wls 2240  }
      
   
   virtualTargetEntry OBJECT-TYPE
      SYNTAX      VirtualTargetEntry
      MAX-ACCESS  not-accessible
      STATUS      current
      DESCRIPTION "Generated SNMP Table Entry."
      INDEX { virtualTargetIndex}
      ::= { virtualTargetTable 1 }
      
   VirtualTargetEntry ::=
      SEQUENCE
      {
         virtualTargetIndex   OCTET STRING,
         virtualTargetObjectName OCTET STRING,
         virtualTargetPortOffset Integer32,
         virtualTargetName    OCTET STRING,
         virtualTargetType    OCTET STRING,
         virtualTargetPartitionChannel OCTET STRING,
         virtualTargetUriPrefix OCTET STRING,
         virtualTargetHostNames OCTET STRING,
         virtualTargetExplicitPort Integer32,
         virtualTargetDeploymentOrder Integer32,
         virtualTargetTags    OCTET STRING
      }
      
   
   virtualTargetIndex OBJECT-TYPE
      SYNTAX      OCTET STRING
      MAX-ACCESS  not-accessible
      STATUS      current
      DESCRIPTION "Index column"
      ::= { virtualTargetEntry 1  }
   
   
   virtualTargetObjectName OBJECT-TYPE
      SYNTAX      OCTET STRING
      MAX-ACCESS  read-only
      STATUS      current
      DESCRIPTION "ObjectName column"
      ::= { virtualTargetEntry 2  }
   
   
   virtualTargetPortOffset OBJECT-TYPE
      SYNTAX      Integer32
      MAX-ACCESS  read-only
      STATUS      current
      DESCRIPTION "The port offset for this virtual target. If set to the minimum value, the port offset is not set. "
      ::= { virtualTargetEntry 3  }
   
   
   virtualTargetName OBJECT-TYPE
      SYNTAX      OCTET STRING
      MAX-ACCESS  read-only
      STATUS      current
      DESCRIPTION "The user-specified name of this MBean instance.  This name is included as one of the key properties in the MBean's javax.management.ObjectName:  Name=user-specified-name "
      ::= { virtualTargetEntry 4  }
   
   
   virtualTargetType OBJECT-TYPE
      SYNTAX      OCTET STRING
      MAX-ACCESS  read-only
      STATUS      current
      DESCRIPTION "Returns the type of the MBean. "
      ::= { virtualTargetEntry 5  }
   
   
   virtualTargetPartitionChannel OBJECT-TYPE
      SYNTAX      OCTET STRING
      MAX-ACCESS  read-only
      STATUS      current
      DESCRIPTION "The channel name to be used as a reference for creating a partition specific channel. "
      ::= { virtualTargetEntry 6  }
   
   
   virtualTargetUriPrefix OBJECT-TYPE
      SYNTAX      OCTET STRING
      MAX-ACCESS  read-only
      STATUS      current
      DESCRIPTION "The URI prefix for this virtual target. "
      ::= { virtualTargetEntry 7  }
   
   
   virtualTargetHostNames OBJECT-TYPE
      SYNTAX      OCTET STRING
      MAX-ACCESS  read-only
      STATUS      current
      DESCRIPTION "Host names, separated by line breaks, for which this virtual target will serve requests. "
      ::= { virtualTargetEntry 8  }
   
   
   virtualTargetExplicitPort OBJECT-TYPE
      SYNTAX      Integer32
      MAX-ACCESS  read-only
      STATUS      current
      DESCRIPTION "Get the explicit port for this virtual target. "
      ::= { virtualTargetEntry 9  }
   
   
   virtualTargetDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { virtualTargetEntry 10  }
   
   
   virtualTargetTags OBJECT-TYPE
      SYNTAX      OCTET STRING
      MAX-ACCESS  read-only
      STATUS      current
      DESCRIPTION "Return all tags on this Configuration MBean "
      ::= { virtualTargetEntry 11  }
   
   
   batchJobRepositoryRuntimeTable OBJECT-TYPE
      SYNTAX      SEQUENCE OF BatchJobRepositoryRuntimeEntry
      MAX-ACCESS  not-accessible
      STATUS      current
      DESCRIPTION " "
      ::= { wls 2245  }
      
   
   batchJobRepositoryRuntimeEntry OBJECT-TYPE
      SYNTAX      BatchJobRepositoryRuntimeEntry
      MAX-ACCESS  not-accessible
      STATUS      current
      DESCRIPTION "Generated SNMP Table Entry."
      INDEX { batchJobRepositoryRuntimeIndex}
      ::= { batchJobRepositoryRuntimeTable 1 }
      
   BatchJobRepositoryRuntimeEntry ::=
      SEQUENCE
      {
         batchJobRepositoryRuntimeIndex OCTET STRING,
         batchJobRepositoryRuntimeObjectName OCTET STRING,
         batchJobRepositoryRuntimeName OCTET STRING,
         batchJobRepositoryRuntimeType OCTET STRING
      }
      
   
   batchJobRepositoryRuntimeIndex OBJECT-TYPE
      SYNTAX      OCTET STRING
      MAX-ACCESS  not-accessible
      STATUS      current
      DESCRIPTION "Index column"
      ::= { batchJobRepositoryRuntimeEntry 1  }
   
   
   batchJobRepositoryRuntimeObjectName OBJECT-TYPE
      SYNTAX      OCTET STRING
      MAX-ACCESS  read-only
      STATUS      current
      DESCRIPTION "ObjectName column"
      ::= { batchJobRepositoryRuntimeEntry 2  }
   
   
   batchJobRepositoryRuntimeName OBJECT-TYPE
      SYNTAX      OCTET STRING
      MAX-ACCESS  read-only
      STATUS      current
      DESCRIPTION "The name of this configuration. WebLogic Server uses an MBean to implement and persist the configuration. "
      ::= { batchJobRepositoryRuntimeEntry 3  }
   
   
   batchJobRepositoryRuntimeType OBJECT-TYPE
      SYNTAX      OCTET STRING
      MAX-ACCESS  read-only
      STATUS      current
      DESCRIPTION "Returns the type of the MBean. "
      ::= { batchJobRepositoryRuntimeEntry 4  }
   
   
   capacityRuntimeTable OBJECT-TYPE
      SYNTAX      SEQUENCE OF CapacityRuntimeEntry
      MAX-ACCESS  not-accessible
      STATUS      current
      DESCRIPTION "Monitoring information for Capacity which defines the maximum number of requests that can be enqueued by all the work managers that share it. "
      ::= { wls 2250  }
      
   
   capacityRuntimeEntry OBJECT-TYPE
      SYNTAX      CapacityRuntimeEntry
      MAX-ACCESS  not-accessible
      STATUS      current
      DESCRIPTION "Generated SNMP Table Entry."
      INDEX { capacityRuntimeIndex}
      ::= { capacityRuntimeTable 1 }
      
   CapacityRuntimeEntry ::=
      SEQUENCE
      {
         capacityRuntimeIndex OCTET STRING,
         capacityRuntimeObjectName OCTET STRING,
         capacityRuntimeCount Integer32,
         capacityRuntimeName  OCTET STRING,
         capacityRuntimeType  OCTET STRING
      }
      
   
   capacityRuntimeIndex OBJECT-TYPE
      SYNTAX      OCTET STRING
      MAX-ACCESS  not-accessible
      STATUS      current
      DESCRIPTION "Index column"
      ::= { capacityRuntimeEntry 1  }
   
   
   capacityRuntimeObjectName OBJECT-TYPE
      SYNTAX      OCTET STRING
      MAX-ACCESS  read-only
      STATUS      current
      DESCRIPTION "ObjectName column"
      ::= { capacityRuntimeEntry 2  }
   
   
   capacityRuntimeCount OBJECT-TYPE
      SYNTAX      Integer32
      MAX-ACCESS  read-only
      STATUS      current
      DESCRIPTION "Total number of requests that can be enqueued. "
      ::= { capacityRuntimeEntry 3  }
   
   
   capacityRuntimeName OBJECT-TYPE
      SYNTAX      OCTET STRING
      MAX-ACCESS  read-only
      STATUS      current
      DESCRIPTION "The name of this configuration. WebLogic Server uses an MBean to implement and persist the configuration. "
      ::= { capacityRuntimeEntry 4  }
   
   
   capacityRuntimeType OBJECT-TYPE
      SYNTAX      OCTET STRING
      MAX-ACCESS  read-only
      STATUS      current
      DESCRIPTION "Returns the type of the MBean. "
      ::= { capacityRuntimeEntry 5  }
   
   
   classLoaderRuntimeTable OBJECT-TYPE
      SYNTAX      SEQUENCE OF ClassLoaderRuntimeEntry
      MAX-ACCESS  not-accessible
      STATUS      current
      DESCRIPTION "Provides methods for retrieving runtime information about class loading "
      ::= { wls 2255  }
      
   
   classLoaderRuntimeEntry OBJECT-TYPE
      SYNTAX      ClassLoaderRuntimeEntry
      MAX-ACCESS  not-accessible
      STATUS      current
      DESCRIPTION "Generated SNMP Table Entry."
      INDEX { classLoaderRuntimeIndex}
      ::= { classLoaderRuntimeTable 1 }
      
   ClassLoaderRuntimeEntry ::=
      SEQUENCE
      {
         classLoaderRuntimeIndex OCTET STRING,
         classLoaderRuntimeObjectName OCTET STRING,
         classLoaderRuntimeBeforeIndexingFindClassCount Counter64,
         classLoaderRuntimeDefineClassCount Counter64,
         classLoaderRuntimeDuringIndexingResourceCount Counter64,
         classLoaderRuntimeDuringIndexingFindClassTime Counter64,
         classLoaderRuntimeBeforeIndexingResourceCount Counter64,
         classLoaderRuntimeAfterIndexingFindClassCount Counter64,
         classLoaderRuntimeAfterIndexingLoadClassTime Counter64,
         classLoaderRuntimeFindClassTime Counter64,
         classLoaderRuntimeName OCTET STRING,
         classLoaderRuntimeBeforeIndexingLoadClassCount Counter64,
         classLoaderRuntimeBeforeIndexingResourceTime Counter64,
         classLoaderRuntimeDuringIndexingResourceTime Counter64,
         classLoaderRuntimeBeforeIndexingLoadClassTime Counter64,
         classLoaderRuntimeLoadClassCount Counter64,
         classLoaderRuntimeAfterIndexingResourceTime Counter64,
         classLoaderRuntimeDuringIndexingFindClassCount Counter64,
         classLoaderRuntimeLoadClassTime Counter64,
         classLoaderRuntimeAfterIndexingLoadClassCount Counter64,
         classLoaderRuntimeAfterIndexingFindClassTime Counter64,
         classLoaderRuntimeAfterIndexingResourceCount Counter64,
         classLoaderRuntimeDuringIndexingLoadClassTime Counter64,
         classLoaderRuntimeParentDelegationTime Counter64,
         classLoaderRuntimeType OCTET STRING,
         classLoaderRuntimeDuringIndexingLoadClassCount Counter64,
         classLoaderRuntimeBeforeIndexingFindClassTime Counter64,
         classLoaderRuntimeFindClassCount Counter64,
         classLoaderRuntimeParentDelegationCount Counter64,
         classLoaderRuntimeResourceCount Counter64,
         classLoaderRuntimeResourceTime Counter64,
         classLoaderRuntimeDefineClassTime Counter64,
         classLoaderRuntimeIndexingTime Counter64
      }
      
   
   classLoaderRuntimeIndex OBJECT-TYPE
      SYNTAX      OCTET STRING
      MAX-ACCESS  not-accessible
      STATUS      current
      DESCRIPTION "Index column"
      ::= { classLoaderRuntimeEntry 1  }
   
   
   classLoaderRuntimeObjectName OBJECT-TYPE
      SYNTAX      OCTET STRING
      MAX-ACCESS  read-only
      STATUS      current
      DESCRIPTION "ObjectName column"
      ::= { classLoaderRuntimeEntry 2  }
   
   
   classLoaderRuntimeBeforeIndexingFindClassCount OBJECT-TYPE
      SYNTAX      Counter64
      MAX-ACCESS  read-only
      STATUS      current
      DESCRIPTION " "
      ::= { classLoaderRuntimeEntry 3  }
   
   
   classLoaderRuntimeDefineClassCount OBJECT-TYPE
      SYNTAX      Counter64
      MAX-ACCESS  read-only
      STATUS      current
      DESCRIPTION " "
      ::= { classLoaderRuntimeEntry 4  }
   
   
   classLoaderRuntimeDuringIndexingResourceCount OBJECT-TYPE
      SYNTAX      Counter64
      MAX-ACCESS  read-only
      STATUS      current
      DESCRIPTION " "
      ::= { classLoaderRuntimeEntry 5  }
   
   
   classLoaderRuntimeDuringIndexingFindClassTime OBJECT-TYPE
      SYNTAX      Counter64
      MAX-ACCESS  read-only
      STATUS      current
      DESCRIPTION " "
      ::= { classLoaderRuntimeEntry 6  }
   
   
   classLoaderRuntimeBeforeIndexingResourceCount OBJECT-TYPE
      SYNTAX      Counter64
      MAX-ACCESS  read-only
      STATUS      current
      DESCRIPTION " "
      ::= { classLoaderRuntimeEntry 7  }
   
   
   classLoaderRuntimeAfterIndexingFindClassCount OBJECT-TYPE
      SYNTAX      Counter64
      MAX-ACCESS  read-only
      STATUS      current
      DESCRIPTION " "
      ::= { classLoaderRuntimeEntry 8  }
   
   
   classLoaderRuntimeAfterIndexingLoadClassTime OBJECT-TYPE
      SYNTAX      Counter64
      MAX-ACCESS  read-only
      STATUS      current
      DESCRIPTION " "
      ::= { classLoaderRuntimeEntry 9  }
   
   
   classLoaderRuntimeFindClassTime OBJECT-TYPE
      SYNTAX      Counter64
      MAX-ACCESS  read-only
      STATUS      current
      DESCRIPTION " "
      ::= { classLoaderRuntimeEntry 10  }
   
   
   classLoaderRuntimeName OBJECT-TYPE
      SYNTAX      OCTET STRING
      MAX-ACCESS  read-only
      STATUS      current
      DESCRIPTION "The name of this configuration. WebLogic Server uses an MBean to implement and persist the configuration. "
      ::= { classLoaderRuntimeEntry 11  }
   
   
   classLoaderRuntimeBeforeIndexingLoadClassCount OBJECT-TYPE
      SYNTAX      Counter64
      MAX-ACCESS  read-only
      STATUS      current
      DESCRIPTION " "
      ::= { classLoaderRuntimeEntry 12  }
   
   
   classLoaderRuntimeBeforeIndexingResourceTime OBJECT-TYPE
      SYNTAX      Counter64
      MAX-ACCESS  read-only
      STATUS      current
      DESCRIPTION " "
      ::= { classLoaderRuntimeEntry 13  }
   
   
   classLoaderRuntimeDuringIndexingResourceTime OBJECT-TYPE
      SYNTAX      Counter64
      MAX-ACCESS  read-only
      STATUS      current
      DESCRIPTION " "
      ::= { classLoaderRuntimeEntry 14  }
   
   
   classLoaderRuntimeBeforeIndexingLoadClassTime OBJECT-TYPE
      SYNTAX      Counter64
      MAX-ACCESS  read-only
      STATUS      current
      DESCRIPTION " "
      ::= { classLoaderRuntimeEntry 15  }
   
   
   classLoaderRuntimeLoadClassCount OBJECT-TYPE
      SYNTAX      Counter64
      MAX-ACCESS  read-only
      STATUS      current
      DESCRIPTION " "
      ::= { classLoaderRuntimeEntry 16  }
   
   
   classLoaderRuntimeAfterIndexingResourceTime OBJECT-TYPE
      SYNTAX      Counter64
      MAX-ACCESS  read-only
      STATUS      current
      DESCRIPTION " "
      ::= { classLoaderRuntimeEntry 17  }
   
   
   classLoaderRuntimeDuringIndexingFindClassCount OBJECT-TYPE
      SYNTAX      Counter64
      MAX-ACCESS  read-only
      STATUS      current
      DESCRIPTION " "
      ::= { classLoaderRuntimeEntry 18  }
   
   
   classLoaderRuntimeLoadClassTime OBJECT-TYPE
      SYNTAX      Counter64
      MAX-ACCESS  read-only
      STATUS      current
      DESCRIPTION " "
      ::= { classLoaderRuntimeEntry 19  }
   
   
   classLoaderRuntimeAfterIndexingLoadClassCount OBJECT-TYPE
      SYNTAX      Counter64
      MAX-ACCESS  read-only
      STATUS      current
      DESCRIPTION " "
      ::= { classLoaderRuntimeEntry 20  }
   
   
   classLoaderRuntimeAfterIndexingFindClassTime OBJECT-TYPE
      SYNTAX      Counter64
      MAX-ACCESS  read-only
      STATUS      current
      DESCRIPTION " "
      ::= { classLoaderRuntimeEntry 21  }
   
   
   classLoaderRuntimeAfterIndexingResourceCount OBJECT-TYPE
      SYNTAX      Counter64
      MAX-ACCESS  read-only
      STATUS      current
      DESCRIPTION " "
      ::= { classLoaderRuntimeEntry 22  }
   
   
   classLoaderRuntimeDuringIndexingLoadClassTime OBJECT-TYPE
      SYNTAX      Counter64
      MAX-ACCESS  read-only
      STATUS      current
      DESCRIPTION " "
      ::= { classLoaderRuntimeEntry 23  }
   
   
   classLoaderRuntimeParentDelegationTime OBJECT-TYPE
      SYNTAX      Counter64
      MAX-ACCESS  read-only
      STATUS      current
      DESCRIPTION " "
      ::= { classLoaderRuntimeEntry 24  }
   
   
   classLoaderRuntimeType OBJECT-TYPE
      SYNTAX      OCTET STRING
      MAX-ACCESS  read-only
      STATUS      current
      DESCRIPTION "Returns the type of the MBean. "
      ::= { classLoaderRuntimeEntry 25  }
   
   
   classLoaderRuntimeDuringIndexingLoadClassCount OBJECT-TYPE
      SYNTAX      Counter64
      MAX-ACCESS  read-only
      STATUS      current
      DESCRIPTION " "
      ::= { classLoaderRuntimeEntry 26  }
   
   
   classLoaderRuntimeBeforeIndexingFindClassTime OBJECT-TYPE
      SYNTAX      Counter64
      MAX-ACCESS  read-only
      STATUS      current
      DESCRIPTION " "
      ::= { classLoaderRuntimeEntry 27  }
   
   
   classLoaderRuntimeFindClassCount OBJECT-TYPE
      SYNTAX      Counter64
      MAX-ACCESS  read-only
      STATUS      current
      DESCRIPTION " "
      ::= { classLoaderRuntimeEntry 28  }
   
   
   classLoaderRuntimeParentDelegationCount OBJECT-TYPE
      SYNTAX      Counter64
      MAX-ACCESS  read-only
      STATUS      current
      DESCRIPTION " "
      ::= { classLoaderRuntimeEntry 29  }
   
   
   classLoaderRuntimeResourceCount OBJECT-TYPE
      SYNTAX      Counter64
      MAX-ACCESS  read-only
      STATUS      current
      DESCRIPTION " "
      ::= { classLoaderRuntimeEntry 30  }
   
   
   classLoaderRuntimeResourceTime OBJECT-TYPE
      SYNTAX      Counter64
      MAX-ACCESS  read-only
      STATUS      current
      DESCRIPTION " "
      ::= { classLoaderRuntimeEntry 31  }
   
   
   classLoaderRuntimeDefineClassTime OBJECT-TYPE
      SYNTAX      Counter64
      MAX-ACCESS  read-only
      STATUS      current
      DESCRIPTION " "
      ::= { classLoaderRuntimeEntry 32  }
   
   
   classLoaderRuntimeIndexingTime OBJECT-TYPE
      SYNTAX      Counter64
      MAX-ACCESS  read-only
      STATUS      current
      DESCRIPTION " "
      ::= { classLoaderRuntimeEntry 33  }
   
   
   concurrentManagedObjectsRuntimeTable OBJECT-TYPE
      SYNTAX      SEQUENCE OF ConcurrentManagedObjectsRuntimeEntry
      MAX-ACCESS  not-accessible
      STATUS      current
      DESCRIPTION "Concurrent Managed Objects Runtime information for the global/domain partition or a common partition. "
      ::= { wls 2260  }
      
   
   concurrentManagedObjectsRuntimeEntry OBJECT-TYPE
      SYNTAX      ConcurrentManagedObjectsRuntimeEntry
      MAX-ACCESS  not-accessible
      STATUS      current
      DESCRIPTION "Generated SNMP Table Entry."
      INDEX { concurrentManagedObjectsRuntimeIndex}
      ::= { concurrentManagedObjectsRuntimeTable 1 }
      
   ConcurrentManagedObjectsRuntimeEntry ::=
      SEQUENCE
      {
         concurrentManagedObjectsRuntimeIndex OCTET STRING,
         concurrentManagedObjectsRuntimeObjectName OCTET STRING,
         concurrentManagedObjectsRuntimeRejectedLongRunningRequests Counter64,
         concurrentManagedObjectsRuntimeName OCTET STRING,
         concurrentManagedObjectsRuntimeRunningThreadsCount Integer32,
         concurrentManagedObjectsRuntimeType OCTET STRING,
         concurrentManagedObjectsRuntimeRunningLongRunningRequests Integer32,
         concurrentManagedObjectsRuntimeRejectedNewThreadRequests Counter64
      }
      
   
   concurrentManagedObjectsRuntimeIndex OBJECT-TYPE
      SYNTAX      OCTET STRING
      MAX-ACCESS  not-accessible
      STATUS      current
      DESCRIPTION "Index column"
      ::= { concurrentManagedObjectsRuntimeEntry 1  }
   
   
   concurrentManagedObjectsRuntimeObjectName OBJECT-TYPE
      SYNTAX      OCTET STRING
      MAX-ACCESS  read-only
      STATUS      current
      DESCRIPTION "ObjectName column"
      ::= { concurrentManagedObjectsRuntimeEntry 2  }
   
   
   concurrentManagedObjectsRuntimeRejectedLongRunningRequests OBJECT-TYPE
      SYNTAX      Counter64
      MAX-ACCESS  read-only
      STATUS      current
      DESCRIPTION "The number of long-running requests that have been rejected by managed executor services and managed scheduled executor services in this partition on the current server. "
      ::= { concurrentManagedObjectsRuntimeEntry 3  }
   
   
   concurrentManagedObjectsRuntimeName OBJECT-TYPE
      SYNTAX      OCTET STRING
      MAX-ACCESS  read-only
      STATUS      current
      DESCRIPTION "The name of this configuration. WebLogic Server uses an MBean to implement and persist the configuration. "
      ::= { concurrentManagedObjectsRuntimeEntry 4  }
   
   
   concurrentManagedObjectsRuntimeRunningThreadsCount OBJECT-TYPE
      SYNTAX      Integer32
      MAX-ACCESS  read-only
      STATUS      current
      DESCRIPTION "The number of running threads created by managed thread factories in this partition on the current server. "
      ::= { concurrentManagedObjectsRuntimeEntry 5  }
   
   
   concurrentManagedObjectsRuntimeType OBJECT-TYPE
      SYNTAX      OCTET STRING
      MAX-ACCESS  read-only
      STATUS      current
      DESCRIPTION "Returns the type of the MBean. "
      ::= { concurrentManagedObjectsRuntimeEntry 6  }
   
   
   concurrentManagedObjectsRuntimeRunningLongRunningRequests OBJECT-TYPE
      SYNTAX      Integer32
      MAX-ACCESS  read-only
      STATUS      current
      DESCRIPTION "The number of running long-running requests submitted to managed executor services and managed scheduled executor services in this partition on the current server. "
      ::= { concurrentManagedObjectsRuntimeEntry 7  }
   
   
   concurrentManagedObjectsRuntimeRejectedNewThreadRequests OBJECT-TYPE
      SYNTAX      Counter64
      MAX-ACCESS  read-only
      STATUS      current
      DESCRIPTION "The number of newThread method invocations that have been rejected by managed thread factories in this partition on the current server. "
      ::= { concurrentManagedObjectsRuntimeEntry 8  }
   
   
   domainPartitionRuntimeTable OBJECT-TYPE
      SYNTAX      SEQUENCE OF DomainPartitionRuntimeEntry
      MAX-ACCESS  not-accessible
      STATUS      current
      DESCRIPTION "This class is used for domain level partition handling.  "
      ::= { wls 2265  }
      
   
   domainPartitionRuntimeEntry OBJECT-TYPE
      SYNTAX      DomainPartitionRuntimeEntry
      MAX-ACCESS  not-accessible
      STATUS      current
      DESCRIPTION "Generated SNMP Table Entry."
      INDEX { domainPartitionRuntimeIndex}
      ::= { domainPartitionRuntimeTable 1 }
      
   DomainPartitionRuntimeEntry ::=
      SEQUENCE
      {
         domainPartitionRuntimeIndex OCTET STRING,
         domainPartitionRuntimeObjectName OCTET STRING,
         domainPartitionRuntimePartitionID OCTET STRING,
         domainPartitionRuntimeName OCTET STRING,
         domainPartitionRuntimeType OCTET STRING
      }
      
   
   domainPartitionRuntimeIndex OBJECT-TYPE
      SYNTAX      OCTET STRING
      MAX-ACCESS  not-accessible
      STATUS      current
      DESCRIPTION "Index column"
      ::= { domainPartitionRuntimeEntry 1  }
   
   
   domainPartitionRuntimeObjectName OBJECT-TYPE
      SYNTAX      OCTET STRING
      MAX-ACCESS  read-only
      STATUS      current
      DESCRIPTION "ObjectName column"
      ::= { domainPartitionRuntimeEntry 2  }
   
   
   domainPartitionRuntimePartitionID OBJECT-TYPE
      SYNTAX      OCTET STRING
      MAX-ACCESS  read-only
      STATUS      current
      DESCRIPTION "Returns partition ID value for corresponding partition. "
      ::= { domainPartitionRuntimeEntry 3  }
   
   
   domainPartitionRuntimeName OBJECT-TYPE
      SYNTAX      OCTET STRING
      MAX-ACCESS  read-only
      STATUS      current
      DESCRIPTION "The name of this configuration. WebLogic Server uses an MBean to implement and persist the configuration. "
      ::= { domainPartitionRuntimeEntry 4  }
   
   
   domainPartitionRuntimeType OBJECT-TYPE
      SYNTAX      OCTET STRING
      MAX-ACCESS  read-only
      STATUS      current
      DESCRIPTION "Returns the type of the MBean. "
      ::= { domainPartitionRuntimeEntry 5  }
   
   
   editSessionConfigurationManagerTable OBJECT-TYPE
      SYNTAX      SEQUENCE OF EditSessionConfigurationManagerEntry
      MAX-ACCESS  not-accessible
      STATUS      current
      DESCRIPTION " "
      ::= { wls 2270  }
      
   
   editSessionConfigurationManagerEntry OBJECT-TYPE
      SYNTAX      EditSessionConfigurationManagerEntry
      MAX-ACCESS  not-accessible
      STATUS      current
      DESCRIPTION "Generated SNMP Table Entry."
      INDEX { editSessionConfigurationManagerIndex}
      ::= { editSessionConfigurationManagerTable 1 }
      
   EditSessionConfigurationManagerEntry ::=
      SEQUENCE
      {
         editSessionConfigurationManagerIndex OCTET STRING,
         editSessionConfigurationManagerObjectName OCTET STRING,
         editSessionConfigurationManagerName OCTET STRING,
         editSessionConfigurationManagerType OCTET STRING
      }
      
   
   editSessionConfigurationManagerIndex OBJECT-TYPE
      SYNTAX      OCTET STRING
      MAX-ACCESS  not-accessible
      STATUS      current
      DESCRIPTION "Index column"
      ::= { editSessionConfigurationManagerEntry 1  }
   
   
   editSessionConfigurationManagerObjectName OBJECT-TYPE
      SYNTAX      OCTET STRING
      MAX-ACCESS  read-only
      STATUS      current
      DESCRIPTION "ObjectName column"
      ::= { editSessionConfigurationManagerEntry 2  }
   
   
   editSessionConfigurationManagerName OBJECT-TYPE
      SYNTAX      OCTET STRING
      MAX-ACCESS  read-only
      STATUS      current
      DESCRIPTION "The name of this configuration. WebLogic Server uses an MBean to implement and persist the configuration. "
      ::= { editSessionConfigurationManagerEntry 3  }
   
   
   editSessionConfigurationManagerType OBJECT-TYPE
      SYNTAX      OCTET STRING
      MAX-ACCESS  read-only
      STATUS      current
      DESCRIPTION "Returns the type of the MBean. "
      ::= { editSessionConfigurationManagerEntry 4  }
   
   
   editSessionConfigurationRuntimeTable OBJECT-TYPE
      SYNTAX      SEQUENCE OF EditSessionConfigurationRuntimeEntry
      MAX-ACCESS  not-accessible
      STATUS      current
      DESCRIPTION " "
      ::= { wls 2275  }
      
   
   editSessionConfigurationRuntimeEntry OBJECT-TYPE
      SYNTAX      EditSessionConfigurationRuntimeEntry
      MAX-ACCESS  not-accessible
      STATUS      current
      DESCRIPTION "Generated SNMP Table Entry."
      INDEX { editSessionConfigurationRuntimeIndex}
      ::= { editSessionConfigurationRuntimeTable 1 }
      
   EditSessionConfigurationRuntimeEntry ::=
      SEQUENCE
      {
         editSessionConfigurationRuntimeIndex OCTET STRING,
         editSessionConfigurationRuntimeObjectName OCTET STRING,
         editSessionConfigurationRuntimeDescription OCTET STRING,
         editSessionConfigurationRuntimeEditSessionName OCTET STRING,
         editSessionConfigurationRuntimeCurrentEditor OCTET STRING,
         editSessionConfigurationRuntimeCreator OCTET STRING,
         editSessionConfigurationRuntimeMergeNeeded OCTET STRING,
         editSessionConfigurationRuntimeName OCTET STRING,
         editSessionConfigurationRuntimePartitionName OCTET STRING,
         editSessionConfigurationRuntimeType OCTET STRING,
         editSessionConfigurationRuntimeEditSessionServerJndi OCTET STRING
      }
      
   
   editSessionConfigurationRuntimeIndex OBJECT-TYPE
      SYNTAX      OCTET STRING
      MAX-ACCESS  not-accessible
      STATUS      current
      DESCRIPTION "Index column"
      ::= { editSessionConfigurationRuntimeEntry 1  }
   
   
   editSessionConfigurationRuntimeObjectName OBJECT-TYPE
      SYNTAX      OCTET STRING
      MAX-ACCESS  read-only
      STATUS      current
      DESCRIPTION "ObjectName column"
      ::= { editSessionConfigurationRuntimeEntry 2  }
   
   
   editSessionConfigurationRuntimeDescription OBJECT-TYPE
      SYNTAX      OCTET STRING
      MAX-ACCESS  read-only
      STATUS      current
      DESCRIPTION "The description of the edit session configuration. "
      ::= { editSessionConfigurationRuntimeEntry 3  }
   
   
   editSessionConfigurationRuntimeEditSessionName OBJECT-TYPE
      SYNTAX      OCTET STRING
      MAX-ACCESS  read-only
      STATUS      current
      DESCRIPTION "The name of the edit session configuration. "
      ::= { editSessionConfigurationRuntimeEntry 4  }
   
   
   editSessionConfigurationRuntimeCurrentEditor OBJECT-TYPE
      SYNTAX      OCTET STRING
      MAX-ACCESS  read-only
      STATUS      current
      DESCRIPTION "The current editor of the edit session. The editor owns the lock. "
      ::= { editSessionConfigurationRuntimeEntry 5  }
   
   
   editSessionConfigurationRuntimeCreator OBJECT-TYPE
      SYNTAX      OCTET STRING
      MAX-ACCESS  read-only
      STATUS      current
      DESCRIPTION "The original creator of the edit session. "
      ::= { editSessionConfigurationRuntimeEntry 6  }
   
   
   editSessionConfigurationRuntimeMergeNeeded OBJECT-TYPE
      SYNTAX      OCTET STRING
      MAX-ACCESS  read-only
      STATUS      current
      DESCRIPTION "Returns true if another edit session activates its changes after the last activation of this edit session or after its creation but before this edit session was ever activated.  It indicates that this edit session configuration is probably not the actual runtime configuration. Use the resolve method to merge changes to this configuration.  If this edit session configuration was also modified then there can be conflicts between this session and the runtime configuration. Use the resolve method to remove possible inconsistencies. "
      ::= { editSessionConfigurationRuntimeEntry 7  }
   
   
   editSessionConfigurationRuntimeName OBJECT-TYPE
      SYNTAX      OCTET STRING
      MAX-ACCESS  read-only
      STATUS      current
      DESCRIPTION "The name of this configuration. WebLogic Server uses an MBean to implement and persist the configuration. "
      ::= { editSessionConfigurationRuntimeEntry 8  }
   
   
   editSessionConfigurationRuntimePartitionName OBJECT-TYPE
      SYNTAX      OCTET STRING
      MAX-ACCESS  read-only
      STATUS      current
      DESCRIPTION "The partition name to which this edit session belongs. "
      ::= { editSessionConfigurationRuntimeEntry 9  }
   
   
   editSessionConfigurationRuntimeType OBJECT-TYPE
      SYNTAX      OCTET STRING
      MAX-ACCESS  read-only
      STATUS      current
      DESCRIPTION "Returns the type of the MBean. "
      ::= { editSessionConfigurationRuntimeEntry 10  }
   
   
   editSessionConfigurationRuntimeEditSessionServerJndi OBJECT-TYPE
      SYNTAX      OCTET STRING
      MAX-ACCESS  read-only
      STATUS      current
      DESCRIPTION "The JNDI name of the related EditSessionServer. "
      ::= { editSessionConfigurationRuntimeEntry 11  }
   
   
   elasticServiceManagerRuntimeTable OBJECT-TYPE
      SYNTAX      SEQUENCE OF ElasticServiceManagerRuntimeEntry
      MAX-ACCESS  not-accessible
      STATUS      current
      DESCRIPTION " "
      ::= { wls 2280  }
      
   
   elasticServiceManagerRuntimeEntry OBJECT-TYPE
      SYNTAX      ElasticServiceManagerRuntimeEntry
      MAX-ACCESS  not-accessible
      STATUS      current
      DESCRIPTION "Generated SNMP Table Entry."
      INDEX { elasticServiceManagerRuntimeIndex}
      ::= { elasticServiceManagerRuntimeTable 1 }
      
   ElasticServiceManagerRuntimeEntry ::=
      SEQUENCE
      {
         elasticServiceManagerRuntimeIndex OCTET STRING,
         elasticServiceManagerRuntimeObjectName OCTET STRING,
         elasticServiceManagerRuntimeName OCTET STRING,
         elasticServiceManagerRuntimeType OCTET STRING
      }
      
   
   elasticServiceManagerRuntimeIndex OBJECT-TYPE
      SYNTAX      OCTET STRING
      MAX-ACCESS  not-accessible
      STATUS      current
      DESCRIPTION "Index column"
      ::= { elasticServiceManagerRuntimeEntry 1  }
   
   
   elasticServiceManagerRuntimeObjectName OBJECT-TYPE
      SYNTAX      OCTET STRING
      MAX-ACCESS  read-only
      STATUS      current
      DESCRIPTION "ObjectName column"
      ::= { elasticServiceManagerRuntimeEntry 2  }
   
   
   elasticServiceManagerRuntimeName OBJECT-TYPE
      SYNTAX      OCTET STRING
      MAX-ACCESS  read-only
      STATUS      current
      DESCRIPTION "The name of this configuration. WebLogic Server uses an MBean to implement and persist the configuration. "
      ::= { elasticServiceManagerRuntimeEntry 3  }
   
   
   elasticServiceManagerRuntimeType OBJECT-TYPE
      SYNTAX      OCTET STRING
      MAX-ACCESS  read-only
      STATUS      current
      DESCRIPTION "Returns the type of the MBean. "
      ::= { elasticServiceManagerRuntimeEntry 4  }
   
   
   fairShareConstraintRuntimeTable OBJECT-TYPE
      SYNTAX      SEQUENCE OF FairShareConstraintRuntimeEntry
      MAX-ACCESS  not-accessible
      STATUS      current
      DESCRIPTION " "
      ::= { wls 2285  }
      
   
   fairShareConstraintRuntimeEntry OBJECT-TYPE
      SYNTAX      FairShareConstraintRuntimeEntry
      MAX-ACCESS  not-accessible
      STATUS      current
      DESCRIPTION "Generated SNMP Table Entry."
      INDEX { fairShareConstraintRuntimeIndex}
      ::= { fairShareConstraintRuntimeTable 1 }
      
   FairShareConstraintRuntimeEntry ::=
      SEQUENCE
      {
         fairShareConstraintRuntimeIndex OCTET STRING,
         fairShareConstraintRuntimeObjectName OCTET STRING,
         fairShareConstraintRuntimeName OCTET STRING,
         fairShareConstraintRuntimeActivated OCTET STRING,
         fairShareConstraintRuntimeInitiated OCTET STRING,
         fairShareConstraintRuntimeType OCTET STRING,
         fairShareConstraintRuntimeLastTimeExecuted OCTET STRING
      }
      
   
   fairShareConstraintRuntimeIndex OBJECT-TYPE
      SYNTAX      OCTET STRING
      MAX-ACCESS  not-accessible
      STATUS      current
      DESCRIPTION "Index column"
      ::= { fairShareConstraintRuntimeEntry 1  }
   
   
   fairShareConstraintRuntimeObjectName OBJECT-TYPE
      SYNTAX      OCTET STRING
      MAX-ACCESS  read-only
      STATUS      current
      DESCRIPTION "ObjectName column"
      ::= { fairShareConstraintRuntimeEntry 2  }
   
   
   fairShareConstraintRuntimeName OBJECT-TYPE
      SYNTAX      OCTET STRING
      MAX-ACCESS  read-only
      STATUS      current
      DESCRIPTION "Return name of the Resource. "
      ::= { fairShareConstraintRuntimeEntry 3  }
   
   
   fairShareConstraintRuntimeActivated OBJECT-TYPE
      SYNTAX      OCTET STRING
      MAX-ACCESS  read-only
      STATUS      current
      DESCRIPTION "Returns true if trigger was successfully executed. "
      ::= { fairShareConstraintRuntimeEntry 4  }
   
   
   fairShareConstraintRuntimeInitiated OBJECT-TYPE
      SYNTAX      OCTET STRING
      MAX-ACCESS  read-only
      STATUS      current
      DESCRIPTION "Returns true if trigger execution has begun. "
      ::= { fairShareConstraintRuntimeEntry 5  }
   
   
   fairShareConstraintRuntimeType OBJECT-TYPE
      SYNTAX      OCTET STRING
      MAX-ACCESS  read-only
      STATUS      current
      DESCRIPTION "Returns the type of the MBean. "
      ::= { fairShareConstraintRuntimeEntry 6  }
   
   
   fairShareConstraintRuntimeLastTimeExecuted OBJECT-TYPE
      SYNTAX      OCTET STRING
      MAX-ACCESS  read-only
      STATUS      current
      DESCRIPTION "Return last trigger execution date and time. "
      ::= { fairShareConstraintRuntimeEntry 7  }
   
   
   jdbcAbstractDataSourceRuntimeTable OBJECT-TYPE
      SYNTAX      SEQUENCE OF JdbcAbstractDataSourceRuntimeEntry
      MAX-ACCESS  not-accessible
      STATUS      current
      DESCRIPTION "Runtime MBean that represents a Abstract JDBC data source. "
      ::= { wls 2290  }
      
   
   jdbcAbstractDataSourceRuntimeEntry OBJECT-TYPE
      SYNTAX      JdbcAbstractDataSourceRuntimeEntry
      MAX-ACCESS  not-accessible
      STATUS      current
      DESCRIPTION "Generated SNMP Table Entry."
      INDEX { jdbcAbstractDataSourceRuntimeIndex}
      ::= { jdbcAbstractDataSourceRuntimeTable 1 }
      
   JdbcAbstractDataSourceRuntimeEntry ::=
      SEQUENCE
      {
         jdbcAbstractDataSourceRuntimeIndex OCTET STRING,
         jdbcAbstractDataSourceRuntimeObjectName OCTET STRING,
         jdbcAbstractDataSourceRuntimeDatabaseProductName OCTET STRING,
         jdbcAbstractDataSourceRuntimePrepStmtCacheAccessCount Counter64,
         jdbcAbstractDataSourceRuntimeConnectionsTotalCount Integer32,
         jdbcAbstractDataSourceRuntimeDriverName OCTET STRING,
         jdbcAbstractDataSourceRuntimeHighestNumUnavailable Integer32,
         jdbcAbstractDataSourceRuntimeDatabaseProductVersion OCTET STRING,
         jdbcAbstractDataSourceRuntimeHighestNumAvailable Integer32,
         jdbcAbstractDataSourceRuntimeWaitSecondsHighCount Integer32,
         jdbcAbstractDataSourceRuntimeWaitingForConnectionHighCount Integer32,
         jdbcAbstractDataSourceRuntimeVersionJDBCDriver OCTET STRING,
         jdbcAbstractDataSourceRuntimeName OCTET STRING,
         jdbcAbstractDataSourceRuntimeWaitingForConnectionTotal Counter64,
         jdbcAbstractDataSourceRuntimeCurrCapacityHighCount Integer32,
         jdbcAbstractDataSourceRuntimeModuleId OCTET STRING,
         jdbcAbstractDataSourceRuntimeNumUnavailable Integer32,
         jdbcAbstractDataSourceRuntimePrepStmtCacheHitCount Integer32,
         jdbcAbstractDataSourceRuntimeFailedReserveRequestCount Counter64,
         jdbcAbstractDataSourceRuntimeWaitingForConnectionCurrentCount Integer32,
         jdbcAbstractDataSourceRuntimeConnectionDelayTime Integer32,
         jdbcAbstractDataSourceRuntimeWaitingForConnectionFailureTotal Counter64,
         jdbcAbstractDataSourceRuntimeNumAvailable Integer32,
         jdbcAbstractDataSourceRuntimePrepStmtCacheAddCount Counter64,
         jdbcAbstractDataSourceRuntimeActiveConnectionsAverageCount Integer32,
         jdbcAbstractDataSourceRuntimeLeakedConnectionCount Integer32,
         jdbcAbstractDataSourceRuntimeDeploymentState Integer32,
         jdbcAbstractDataSourceRuntimePrepStmtCacheCurrentSize Integer32,
         jdbcAbstractDataSourceRuntimeActiveConnectionsCurrentCount Integer32,
         jdbcAbstractDataSourceRuntimeEnabled OCTET STRING,
         jdbcAbstractDataSourceRuntimeActiveConnectionsHighCount Integer32,
         jdbcAbstractDataSourceRuntimeCurrCapacity Integer32,
         jdbcAbstractDataSourceRuntimeFailuresToReconnectCount Integer32,
         jdbcAbstractDataSourceRuntimeWaitingForConnectionSuccessTotal Counter64,
         jdbcAbstractDataSourceRuntimeType OCTET STRING,
         jdbcAbstractDataSourceRuntimeDriverVersion OCTET STRING,
         jdbcAbstractDataSourceRuntimeState OCTET STRING,
         jdbcAbstractDataSourceRuntimeReserveRequestCount Counter64,
         jdbcAbstractDataSourceRuntimePrepStmtCacheMissCount Integer32,
         jdbcAbstractDataSourceRuntimePrepStmtCacheDeleteCount Counter64,
         jdbcAbstractDataSourceRuntimeRepurposeCount Counter64,
         jdbcAbstractDataSourceRuntimeUnresolvedTotalCount Counter64,
         jdbcAbstractDataSourceRuntimeResolvedAsCommittedTotalCount Counter64,
         jdbcAbstractDataSourceRuntimeCommitOutcomeRetryTotalCount Counter64,
         jdbcAbstractDataSourceRuntimeResolvedAsNotCommittedTotalCount Counter64,
         jdbcAbstractDataSourceRuntimeFailedRepurposeCount Counter64
      }
      
   
   jdbcAbstractDataSourceRuntimeIndex OBJECT-TYPE
      SYNTAX      OCTET STRING
      MAX-ACCESS  not-accessible
      STATUS      current
      DESCRIPTION "Index column"
      ::= { jdbcAbstractDataSourceRuntimeEntry 1  }
   
   
   jdbcAbstractDataSourceRuntimeObjectName OBJECT-TYPE
      SYNTAX      OCTET STRING
      MAX-ACCESS  read-only
      STATUS      current
      DESCRIPTION "ObjectName column"
      ::= { jdbcAbstractDataSourceRuntimeEntry 2  }
   
   
   jdbcAbstractDataSourceRuntimeDatabaseProductName OBJECT-TYPE
      SYNTAX      OCTET STRING
      MAX-ACCESS  read-only
      STATUS      current
      DESCRIPTION " The product name of the database that this data source is connected to.  "
      ::= { jdbcAbstractDataSourceRuntimeEntry 3  }
   
   
   jdbcAbstractDataSourceRuntimePrepStmtCacheAccessCount OBJECT-TYPE
      SYNTAX      Counter64
      MAX-ACCESS  read-only
      STATUS      current
      DESCRIPTION "The cumulative, running count of the number of times that the statement cache was accessed. "
      ::= { jdbcAbstractDataSourceRuntimeEntry 4  }
   
   
   jdbcAbstractDataSourceRuntimeConnectionsTotalCount OBJECT-TYPE
      SYNTAX      Integer32
      MAX-ACCESS  read-only
      STATUS      current
      DESCRIPTION "The cumulative total number of database connections created in this data source since the data source was deployed. "
      ::= { jdbcAbstractDataSourceRuntimeEntry 5  }
   
   
   jdbcAbstractDataSourceRuntimeDriverName OBJECT-TYPE
      SYNTAX      OCTET STRING
      MAX-ACCESS  read-only
      STATUS      current
      DESCRIPTION " The product name of the JDBC driver that this data source is configured to use.  "
      ::= { jdbcAbstractDataSourceRuntimeEntry 6  }
   
   
   jdbcAbstractDataSourceRuntimeHighestNumUnavailable OBJECT-TYPE
      SYNTAX      Integer32
      MAX-ACCESS  read-only
      STATUS      current
      DESCRIPTION "Highest number of database connections that were in use by applications or being tested by the system in this instance of the data source since the data source was deployed. "
      ::= { jdbcAbstractDataSourceRuntimeEntry 7  }
   
   
   jdbcAbstractDataSourceRuntimeDatabaseProductVersion OBJECT-TYPE
      SYNTAX      OCTET STRING
      MAX-ACCESS  read-only
      STATUS      current
      DESCRIPTION " The product version of the database that this data source is connected to.  "
      ::= { jdbcAbstractDataSourceRuntimeEntry 8  }
   
   
   jdbcAbstractDataSourceRuntimeHighestNumAvailable OBJECT-TYPE
      SYNTAX      Integer32
      MAX-ACCESS  read-only
      STATUS      current
      DESCRIPTION "Highest number of database connections that were idle and available to be used by an application at any time in this instance of the data source since the data source was deployed. "
      ::= { jdbcAbstractDataSourceRuntimeEntry 9  }
   
   
   jdbcAbstractDataSourceRuntimeWaitSecondsHighCount OBJECT-TYPE
      SYNTAX      Integer32
      MAX-ACCESS  read-only
      STATUS      current
      DESCRIPTION "The highest number of seconds that an application waited for a connection (the longest connection reserve wait time) from this instance of the connection pool since the connection pool was instantiated. This value is updated when a completed getConnection request takes longer to return a connection than any previous request. "
      ::= { jdbcAbstractDataSourceRuntimeEntry 10  }
   
   
   jdbcAbstractDataSourceRuntimeWaitingForConnectionHighCount OBJECT-TYPE
      SYNTAX      Integer32
      MAX-ACCESS  read-only
      STATUS      current
      DESCRIPTION "Highest number of application requests concurrently waiting for a connection from this instance of the data source. "
      ::= { jdbcAbstractDataSourceRuntimeEntry 11  }
   
   
   jdbcAbstractDataSourceRuntimeVersionJDBCDriver OBJECT-TYPE
      SYNTAX      OCTET STRING
      MAX-ACCESS  read-only
      STATUS      current
      DESCRIPTION "The driver class name of the JDBC driver used to create database connections.  "
      ::= { jdbcAbstractDataSourceRuntimeEntry 12  }
   
   
   jdbcAbstractDataSourceRuntimeName OBJECT-TYPE
      SYNTAX      OCTET STRING
      MAX-ACCESS  read-only
      STATUS      current
      DESCRIPTION "The name of this configuration. WebLogic Server uses an MBean to implement and persist the configuration. "
      ::= { jdbcAbstractDataSourceRuntimeEntry 13  }
   
   
   jdbcAbstractDataSourceRuntimeWaitingForConnectionTotal OBJECT-TYPE
      SYNTAX      Counter64
      MAX-ACCESS  read-only
      STATUS      current
      DESCRIPTION "The cumulative, running count of requests for a connection from this data source that had to wait before getting a connection, including those that eventually got a connection and those that did not get a connection. "
      ::= { jdbcAbstractDataSourceRuntimeEntry 14  }
   
   
   jdbcAbstractDataSourceRuntimeCurrCapacityHighCount OBJECT-TYPE
      SYNTAX      Integer32
      MAX-ACCESS  read-only
      STATUS      current
      DESCRIPTION "Highest number of database connections available or in use (current capacity) in this instance of the data source since the data source was deployed. "
      ::= { jdbcAbstractDataSourceRuntimeEntry 15  }
   
   
   jdbcAbstractDataSourceRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { jdbcAbstractDataSourceRuntimeEntry 16  }
   
   
   jdbcAbstractDataSourceRuntimeNumUnavailable OBJECT-TYPE
      SYNTAX      Integer32
      MAX-ACCESS  read-only
      STATUS      current
      DESCRIPTION "The number of connections currently in use by applications or being tested in this instance of the data source. "
      ::= { jdbcAbstractDataSourceRuntimeEntry 17  }
   
   
   jdbcAbstractDataSourceRuntimePrepStmtCacheHitCount OBJECT-TYPE
      SYNTAX      Integer32
      MAX-ACCESS  read-only
      STATUS      current
      DESCRIPTION "The cumulative, running count of the number of times that statements from the cache were used. "
      ::= { jdbcAbstractDataSourceRuntimeEntry 18  }
   
   
   jdbcAbstractDataSourceRuntimeFailedReserveRequestCount OBJECT-TYPE
      SYNTAX      Counter64
      MAX-ACCESS  read-only
      STATUS      current
      DESCRIPTION "The cumulative, running count of requests for a connection from this data source that could not be fulfilled. "
      ::= { jdbcAbstractDataSourceRuntimeEntry 19  }
   
   
   jdbcAbstractDataSourceRuntimeWaitingForConnectionCurrentCount OBJECT-TYPE
      SYNTAX      Integer32
      MAX-ACCESS  read-only
      STATUS      current
      DESCRIPTION "The number of connection requests waiting for a database connection. "
      ::= { jdbcAbstractDataSourceRuntimeEntry 20  }
   
   
   jdbcAbstractDataSourceRuntimeConnectionDelayTime OBJECT-TYPE
      SYNTAX      Integer32
      MAX-ACCESS  read-only
      STATUS      current
      DESCRIPTION "The average amount of time, in milliseconds, that it takes to create a physical connection to the database.  The value is calculated as summary of all times to connect divided by the total number of connections. "
      ::= { jdbcAbstractDataSourceRuntimeEntry 21  }
   
   
   jdbcAbstractDataSourceRuntimeWaitingForConnectionFailureTotal OBJECT-TYPE
      SYNTAX      Counter64
      MAX-ACCESS  read-only
      STATUS      current
      DESCRIPTION "The cumulative, running count of requests for a connection from this data source that had to wait before getting a connection and eventually failed to get a connection.  Waiting connection requests can fail for a variety of reasons, including waiting for longer than the ConnectionReserveTimeoutSeconds. "
      ::= { jdbcAbstractDataSourceRuntimeEntry 22  }
   
   
   jdbcAbstractDataSourceRuntimeNumAvailable OBJECT-TYPE
      SYNTAX      Integer32
      MAX-ACCESS  read-only
      STATUS      current
      DESCRIPTION "The number of database connections that are currently idle and  available to be used by applications in this instance of the data source. "
      ::= { jdbcAbstractDataSourceRuntimeEntry 23  }
   
   
   jdbcAbstractDataSourceRuntimePrepStmtCacheAddCount OBJECT-TYPE
      SYNTAX      Counter64
      MAX-ACCESS  read-only
      STATUS      current
      DESCRIPTION "The cumulative, running count of the number of statements added to the statement cache.  Each connection in the connection pool has its own cache of statements. This number is the sum of the number of statements added to the caches for all connections in the connection pool. "
      ::= { jdbcAbstractDataSourceRuntimeEntry 24  }
   
   
   jdbcAbstractDataSourceRuntimeActiveConnectionsAverageCount OBJECT-TYPE
      SYNTAX      Integer32
      MAX-ACCESS  read-only
      STATUS      current
      DESCRIPTION "Average number of active connections in this instance of the data source.  Active connections are connections in use by an application.  This value is only valid if the resource is configured to allow shrinking. "
      ::= { jdbcAbstractDataSourceRuntimeEntry 25  }
   
   
   jdbcAbstractDataSourceRuntimeLeakedConnectionCount OBJECT-TYPE
      SYNTAX      Integer32
      MAX-ACCESS  read-only
      STATUS      current
      DESCRIPTION "The number of leaked connections. A leaked connection is a connection that was reserved from the data source but was not returned to the data source by calling close(). "
      ::= { jdbcAbstractDataSourceRuntimeEntry 26  }
   
   
   jdbcAbstractDataSourceRuntimeDeploymentState OBJECT-TYPE
      SYNTAX      Integer32
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jdbcAbstractDataSourceRuntimeEntry 27  }
   
   
   jdbcAbstractDataSourceRuntimePrepStmtCacheCurrentSize OBJECT-TYPE
      SYNTAX      Integer32
      MAX-ACCESS  read-only
      STATUS      current
      DESCRIPTION "The number of prepared and callable statements currently cached in the statement cache.  Each connection in the connection pool has its own cache of statements. This number is the sum of the number of statements in the caches for all connections in the connection pool. "
      ::= { jdbcAbstractDataSourceRuntimeEntry 28  }
   
   
   jdbcAbstractDataSourceRuntimeActiveConnectionsCurrentCount OBJECT-TYPE
      SYNTAX      Integer32
      MAX-ACCESS  read-only
      STATUS      current
      DESCRIPTION "The number of connections currently in use by applications. "
      ::= { jdbcAbstractDataSourceRuntimeEntry 29  }
   
   
   jdbcAbstractDataSourceRuntimeEnabled OBJECT-TYPE
      SYNTAX      OCTET STRING
      MAX-ACCESS  read-only
      STATUS      current
      DESCRIPTION "Indicates whether the data source is enabled or disabled:   true if the data source is enabled. false if the data source is disabled.  "
      ::= { jdbcAbstractDataSourceRuntimeEntry 30  }
   
   
   jdbcAbstractDataSourceRuntimeActiveConnectionsHighCount OBJECT-TYPE
      SYNTAX      Integer32
      MAX-ACCESS  read-only
      STATUS      current
      DESCRIPTION "Highest number of active database connections in this instance of the data source since the data source was instantiated.   Active connections are connections in use by an application. "
      ::= { jdbcAbstractDataSourceRuntimeEntry 31  }
   
   
   jdbcAbstractDataSourceRuntimeCurrCapacity OBJECT-TYPE
      SYNTAX      Integer32
      MAX-ACCESS  read-only
      STATUS      current
      DESCRIPTION "The current count of JDBC connections in the connection pool in the data source. "
      ::= { jdbcAbstractDataSourceRuntimeEntry 32  }
   
   
   jdbcAbstractDataSourceRuntimeFailuresToReconnectCount OBJECT-TYPE
      SYNTAX      Integer32
      MAX-ACCESS  read-only
      STATUS      current
      DESCRIPTION "The number of times that the data source attempted to refresh a database connection and failed.  Failures may occur when the database is unavailable or when the network connection to the database is interrupted. "
      ::= { jdbcAbstractDataSourceRuntimeEntry 33  }
   
   
   jdbcAbstractDataSourceRuntimeWaitingForConnectionSuccessTotal OBJECT-TYPE
      SYNTAX      Counter64
      MAX-ACCESS  read-only
      STATUS      current
      DESCRIPTION "The cumulative, running count of requests for a connection from this data source that had to wait before getting a connection and eventually succeeded in getting a connection. "
      ::= { jdbcAbstractDataSourceRuntimeEntry 34  }
   
   
   jdbcAbstractDataSourceRuntimeType OBJECT-TYPE
      SYNTAX      OCTET STRING
      MAX-ACCESS  read-only
      STATUS      current
      DESCRIPTION "Returns the type of the MBean. "
      ::= { jdbcAbstractDataSourceRuntimeEntry 35  }
   
   
   jdbcAbstractDataSourceRuntimeDriverVersion OBJECT-TYPE
      SYNTAX      OCTET STRING
      MAX-ACCESS  read-only
      STATUS      current
      DESCRIPTION " The version of the JDBC driver that this data source is configured to use.  "
      ::= { jdbcAbstractDataSourceRuntimeEntry 36  }
   
   
   jdbcAbstractDataSourceRuntimeState OBJECT-TYPE
      SYNTAX      OCTET STRING
      MAX-ACCESS  read-only
      STATUS      current
      DESCRIPTION "The current state of the data source. Possible states are: Running - the data source is enabled (deployed and not Suspended). This is the normal state of the data source. This state includes conditions when the database server is not available and the data source is created (creation retry must be enabled) or when all connections have failed connection tests (on creation, on reserve, or periodic testing). Suspended - the data source has been disabled. Shutdown - the data source is shutdown and all database connections have been closed. Overloaded - all resources in pool are in use. Unknown - the data source state is unknown. "
      ::= { jdbcAbstractDataSourceRuntimeEntry 37  }
   
   
   jdbcAbstractDataSourceRuntimeReserveRequestCount OBJECT-TYPE
      SYNTAX      Counter64
      MAX-ACCESS  read-only
      STATUS      current
      DESCRIPTION "The cumulative, running count of requests for a connection from this data source. "
      ::= { jdbcAbstractDataSourceRuntimeEntry 38  }
   
   
   jdbcAbstractDataSourceRuntimePrepStmtCacheMissCount OBJECT-TYPE
      SYNTAX      Integer32
      MAX-ACCESS  read-only
      STATUS      current
      DESCRIPTION "The number of times that a statement request could not be satisfied with a statement from the cache. "
      ::= { jdbcAbstractDataSourceRuntimeEntry 39  }
   
   
   jdbcAbstractDataSourceRuntimePrepStmtCacheDeleteCount OBJECT-TYPE
      SYNTAX      Counter64
      MAX-ACCESS  read-only
      STATUS      current
      DESCRIPTION "The cumulative, running count of statements discarded from the cache.  Each connection in the connection pool has its own cache of statements. This number is the sum of the number of statements that were discarded from the caches for all connections in the connection pool. "
      ::= { jdbcAbstractDataSourceRuntimeEntry 40  }
   
   
   jdbcAbstractDataSourceRuntimeRepurposeCount OBJECT-TYPE
      SYNTAX      Counter64
      MAX-ACCESS  read-only
      STATUS      current
      DESCRIPTION "The number of times connections have been repurposed since the datasource was deployed. "
      ::= { jdbcAbstractDataSourceRuntimeEntry 41  }
   
   
   jdbcAbstractDataSourceRuntimeUnresolvedTotalCount OBJECT-TYPE
      SYNTAX      Counter64
      MAX-ACCESS  read-only
      STATUS      current
      DESCRIPTION "The cumulative total number of commit outcomes unsuccessfully resolved in this data source since the data source was deployed. This does not refer to the number of outcome query retries used to resolve the outcomes. "
      ::= { jdbcAbstractDataSourceRuntimeEntry 42  }
   
   
   jdbcAbstractDataSourceRuntimeResolvedAsCommittedTotalCount OBJECT-TYPE
      SYNTAX      Counter64
      MAX-ACCESS  read-only
      STATUS      current
      DESCRIPTION "The cumulative total number of commit outcomes successfully resolved as committed in this data source since the data source was deployed. This does not refer to the number of outcome query retries used to resolve the outcomes. "
      ::= { jdbcAbstractDataSourceRuntimeEntry 43  }
   
   
   jdbcAbstractDataSourceRuntimeCommitOutcomeRetryTotalCount OBJECT-TYPE
      SYNTAX      Counter64
      MAX-ACCESS  read-only
      STATUS      current
      DESCRIPTION "The cumulative total number of commit outcome query retries conducted before resolving the outcome or exceeding the retry seconds in this data source since the data source was deployed. "
      ::= { jdbcAbstractDataSourceRuntimeEntry 44  }
   
   
   jdbcAbstractDataSourceRuntimeResolvedAsNotCommittedTotalCount OBJECT-TYPE
      SYNTAX      Counter64
      MAX-ACCESS  read-only
      STATUS      current
      DESCRIPTION "The cumulative total number of commit outcomes successfully resolved as not committed in this data source since the data source was deployed. This does not refer to the number of outcome query retries used to resolve the outcomes. "
      ::= { jdbcAbstractDataSourceRuntimeEntry 45  }
   
   
   jdbcAbstractDataSourceRuntimeFailedRepurposeCount OBJECT-TYPE
      SYNTAX      Counter64
      MAX-ACCESS  read-only
      STATUS      current
      DESCRIPTION "The number of repurpose errors that have occurred since the datasource was deployed. "
      ::= { jdbcAbstractDataSourceRuntimeEntry 46  }
   
   
   jdbcPartitionRuntimeTable OBJECT-TYPE
      SYNTAX      SEQUENCE OF JdbcPartitionRuntimeEntry
      MAX-ACCESS  not-accessible
      STATUS      current
      DESCRIPTION "Partition monitoring of WebLogic JDBC resources "
      ::= { wls 2295  }
      
   
   jdbcPartitionRuntimeEntry OBJECT-TYPE
      SYNTAX      JdbcPartitionRuntimeEntry
      MAX-ACCESS  not-accessible
      STATUS      current
      DESCRIPTION "Generated SNMP Table Entry."
      INDEX { jdbcPartitionRuntimeIndex}
      ::= { jdbcPartitionRuntimeTable 1 }
      
   JdbcPartitionRuntimeEntry ::=
      SEQUENCE
      {
         jdbcPartitionRuntimeIndex OCTET STRING,
         jdbcPartitionRuntimeObjectName OCTET STRING,
         jdbcPartitionRuntimeName OCTET STRING,
         jdbcPartitionRuntimeType OCTET STRING
      }
      
   
   jdbcPartitionRuntimeIndex OBJECT-TYPE
      SYNTAX      OCTET STRING
      MAX-ACCESS  not-accessible
      STATUS      current
      DESCRIPTION "Index column"
      ::= { jdbcPartitionRuntimeEntry 1  }
   
   
   jdbcPartitionRuntimeObjectName OBJECT-TYPE
      SYNTAX      OCTET STRING
      MAX-ACCESS  read-only
      STATUS      current
      DESCRIPTION "ObjectName column"
      ::= { jdbcPartitionRuntimeEntry 2  }
   
   
   jdbcPartitionRuntimeName OBJECT-TYPE
      SYNTAX      OCTET STRING
      MAX-ACCESS  read-only
      STATUS      current
      DESCRIPTION "The name of this configuration. WebLogic Server uses an MBean to implement and persist the configuration. "
      ::= { jdbcPartitionRuntimeEntry 3  }
   
   
   jdbcPartitionRuntimeType OBJECT-TYPE
      SYNTAX      OCTET STRING
      MAX-ACCESS  read-only
      STATUS      current
      DESCRIPTION "Returns the type of the MBean. "
      ::= { jdbcPartitionRuntimeEntry 4  }
   
   
   jdbcProxyDataSourceRuntimeTable OBJECT-TYPE
      SYNTAX      SEQUENCE OF JdbcProxyDataSourceRuntimeEntry
      MAX-ACCESS  not-accessible
      STATUS      current
      DESCRIPTION "Runtime MBean that represents a Proxy JDBC data source. "
      ::= { wls 2300  }
      
   
   jdbcProxyDataSourceRuntimeEntry OBJECT-TYPE
      SYNTAX      JdbcProxyDataSourceRuntimeEntry
      MAX-ACCESS  not-accessible
      STATUS      current
      DESCRIPTION "Generated SNMP Table Entry."
      INDEX { jdbcProxyDataSourceRuntimeIndex}
      ::= { jdbcProxyDataSourceRuntimeTable 1 }
      
   JdbcProxyDataSourceRuntimeEntry ::=
      SEQUENCE
      {
         jdbcProxyDataSourceRuntimeIndex OCTET STRING,
         jdbcProxyDataSourceRuntimeObjectName OCTET STRING,
         jdbcProxyDataSourceRuntimeDatabaseProductName OCTET STRING,
         jdbcProxyDataSourceRuntimePrepStmtCacheAccessCount Counter64,
         jdbcProxyDataSourceRuntimeConnectionsTotalCount Integer32,
         jdbcProxyDataSourceRuntimeDriverName OCTET STRING,
         jdbcProxyDataSourceRuntimeHighestNumUnavailable Integer32,
         jdbcProxyDataSourceRuntimeDatabaseProductVersion OCTET STRING,
         jdbcProxyDataSourceRuntimeHighestNumAvailable Integer32,
         jdbcProxyDataSourceRuntimeWaitSecondsHighCount Integer32,
         jdbcProxyDataSourceRuntimeWaitingForConnectionHighCount Integer32,
         jdbcProxyDataSourceRuntimeVersionJDBCDriver OCTET STRING,
         jdbcProxyDataSourceRuntimeName OCTET STRING,
         jdbcProxyDataSourceRuntimeWaitingForConnectionTotal Counter64,
         jdbcProxyDataSourceRuntimeCurrCapacityHighCount Integer32,
         jdbcProxyDataSourceRuntimeModuleId OCTET STRING,
         jdbcProxyDataSourceRuntimeNumUnavailable Integer32,
         jdbcProxyDataSourceRuntimePrepStmtCacheHitCount Integer32,
         jdbcProxyDataSourceRuntimeFailedReserveRequestCount Counter64,
         jdbcProxyDataSourceRuntimeWaitingForConnectionCurrentCount Integer32,
         jdbcProxyDataSourceRuntimeConnectionDelayTime Integer32,
         jdbcProxyDataSourceRuntimeWaitingForConnectionFailureTotal Counter64,
         jdbcProxyDataSourceRuntimeNumAvailable Integer32,
         jdbcProxyDataSourceRuntimePrepStmtCacheAddCount Counter64,
         jdbcProxyDataSourceRuntimeActiveConnectionsAverageCount Integer32,
         jdbcProxyDataSourceRuntimeLeakedConnectionCount Integer32,
         jdbcProxyDataSourceRuntimeDeploymentState Integer32,
         jdbcProxyDataSourceRuntimePrepStmtCacheCurrentSize Integer32,
         jdbcProxyDataSourceRuntimeActiveConnectionsCurrentCount Integer32,
         jdbcProxyDataSourceRuntimeEnabled OCTET STRING,
         jdbcProxyDataSourceRuntimeActiveConnectionsHighCount Integer32,
         jdbcProxyDataSourceRuntimeCurrCapacity Integer32,
         jdbcProxyDataSourceRuntimeFailuresToReconnectCount Integer32,
         jdbcProxyDataSourceRuntimeWaitingForConnectionSuccessTotal Counter64,
         jdbcProxyDataSourceRuntimeType OCTET STRING,
         jdbcProxyDataSourceRuntimeDriverVersion OCTET STRING,
         jdbcProxyDataSourceRuntimeState OCTET STRING,
         jdbcProxyDataSourceRuntimeReserveRequestCount Counter64,
         jdbcProxyDataSourceRuntimePrepStmtCacheMissCount Integer32,
         jdbcProxyDataSourceRuntimePrepStmtCacheDeleteCount Counter64,
         jdbcProxyDataSourceRuntimeRepurposeCount Counter64,
         jdbcProxyDataSourceRuntimeUnresolvedTotalCount Counter64,
         jdbcProxyDataSourceRuntimeResolvedAsCommittedTotalCount Counter64,
         jdbcProxyDataSourceRuntimeCommitOutcomeRetryTotalCount Counter64,
         jdbcProxyDataSourceRuntimeResolvedAsNotCommittedTotalCount Counter64,
         jdbcProxyDataSourceRuntimeFailedRepurposeCount Counter64
      }
      
   
   jdbcProxyDataSourceRuntimeIndex OBJECT-TYPE
      SYNTAX      OCTET STRING
      MAX-ACCESS  not-accessible
      STATUS      current
      DESCRIPTION "Index column"
      ::= { jdbcProxyDataSourceRuntimeEntry 1  }
   
   
   jdbcProxyDataSourceRuntimeObjectName OBJECT-TYPE
      SYNTAX      OCTET STRING
      MAX-ACCESS  read-only
      STATUS      current
      DESCRIPTION "ObjectName column"
      ::= { jdbcProxyDataSourceRuntimeEntry 2  }
   
   
   jdbcProxyDataSourceRuntimeDatabaseProductName OBJECT-TYPE
      SYNTAX      OCTET STRING
      MAX-ACCESS  read-only
      STATUS      current
      DESCRIPTION " The product name of the database that this data source is connected to.  "
      ::= { jdbcProxyDataSourceRuntimeEntry 3  }
   
   
   jdbcProxyDataSourceRuntimePrepStmtCacheAccessCount OBJECT-TYPE
      SYNTAX      Counter64
      MAX-ACCESS  read-only
      STATUS      current
      DESCRIPTION "The cumulative, running count of the number of times that the statement cache was accessed. "
      ::= { jdbcProxyDataSourceRuntimeEntry 4  }
   
   
   jdbcProxyDataSourceRuntimeConnectionsTotalCount OBJECT-TYPE
      SYNTAX      Integer32
      MAX-ACCESS  read-only
      STATUS      current
      DESCRIPTION "The cumulative total number of database connections created in this data source since the data source was deployed. "
      ::= { jdbcProxyDataSourceRuntimeEntry 5  }
   
   
   jdbcProxyDataSourceRuntimeDriverName OBJECT-TYPE
      SYNTAX      OCTET STRING
      MAX-ACCESS  read-only
      STATUS      current
      DESCRIPTION " The product name of the JDBC driver that this data source is configured to use.  "
      ::= { jdbcProxyDataSourceRuntimeEntry 6  }
   
   
   jdbcProxyDataSourceRuntimeHighestNumUnavailable OBJECT-TYPE
      SYNTAX      Integer32
      MAX-ACCESS  read-only
      STATUS      current
      DESCRIPTION "Highest number of database connections that were in use by applications or being tested by the system in this instance of the data source since the data source was deployed. "
      ::= { jdbcProxyDataSourceRuntimeEntry 7  }
   
   
   jdbcProxyDataSourceRuntimeDatabaseProductVersion OBJECT-TYPE
      SYNTAX      OCTET STRING
      MAX-ACCESS  read-only
      STATUS      current
      DESCRIPTION " The product version of the database that this data source is connected to.  "
      ::= { jdbcProxyDataSourceRuntimeEntry 8  }
   
   
   jdbcProxyDataSourceRuntimeHighestNumAvailable OBJECT-TYPE
      SYNTAX      Integer32
      MAX-ACCESS  read-only
      STATUS      current
      DESCRIPTION "Highest number of database connections that were idle and available to be used by an application at any time in this instance of the data source since the data source was deployed. "
      ::= { jdbcProxyDataSourceRuntimeEntry 9  }
   
   
   jdbcProxyDataSourceRuntimeWaitSecondsHighCount OBJECT-TYPE
      SYNTAX      Integer32
      MAX-ACCESS  read-only
      STATUS      current
      DESCRIPTION "The highest number of seconds that an application waited for a connection (the longest connection reserve wait time) from this instance of the connection pool since the connection pool was instantiated. This value is updated when a completed getConnection request takes longer to return a connection than any previous request. "
      ::= { jdbcProxyDataSourceRuntimeEntry 10  }
   
   
   jdbcProxyDataSourceRuntimeWaitingForConnectionHighCount OBJECT-TYPE
      SYNTAX      Integer32
      MAX-ACCESS  read-only
      STATUS      current
      DESCRIPTION "Highest number of application requests concurrently waiting for a connection from this instance of the data source. "
      ::= { jdbcProxyDataSourceRuntimeEntry 11  }
   
   
   jdbcProxyDataSourceRuntimeVersionJDBCDriver OBJECT-TYPE
      SYNTAX      OCTET STRING
      MAX-ACCESS  read-only
      STATUS      current
      DESCRIPTION "The driver class name of the JDBC driver used to create database connections.  "
      ::= { jdbcProxyDataSourceRuntimeEntry 12  }
   
   
   jdbcProxyDataSourceRuntimeName OBJECT-TYPE
      SYNTAX      OCTET STRING
      MAX-ACCESS  read-only
      STATUS      current
      DESCRIPTION "The name of this configuration. WebLogic Server uses an MBean to implement and persist the configuration. "
      ::= { jdbcProxyDataSourceRuntimeEntry 13  }
   
   
   jdbcProxyDataSourceRuntimeWaitingForConnectionTotal OBJECT-TYPE
      SYNTAX      Counter64
      MAX-ACCESS  read-only
      STATUS      current
      DESCRIPTION "The cumulative, running count of requests for a connection from this data source that had to wait before getting a connection, including those that eventually got a connection and those that did not get a connection. "
      ::= { jdbcProxyDataSourceRuntimeEntry 14  }
   
   
   jdbcProxyDataSourceRuntimeCurrCapacityHighCount OBJECT-TYPE
      SYNTAX      Integer32
      MAX-ACCESS  read-only
      STATUS      current
      DESCRIPTION "Highest number of database connections available or in use (current capacity) in this instance of the data source since the data source was deployed. "
      ::= { jdbcProxyDataSourceRuntimeEntry 15  }
   
   
   jdbcProxyDataSourceRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { jdbcProxyDataSourceRuntimeEntry 16  }
   
   
   jdbcProxyDataSourceRuntimeNumUnavailable OBJECT-TYPE
      SYNTAX      Integer32
      MAX-ACCESS  read-only
      STATUS      current
      DESCRIPTION "The number of connections currently in use by applications or being tested in this instance of the data source. "
      ::= { jdbcProxyDataSourceRuntimeEntry 17  }
   
   
   jdbcProxyDataSourceRuntimePrepStmtCacheHitCount OBJECT-TYPE
      SYNTAX      Integer32
      MAX-ACCESS  read-only
      STATUS      current
      DESCRIPTION "The cumulative, running count of the number of times that statements from the cache were used. "
      ::= { jdbcProxyDataSourceRuntimeEntry 18  }
   
   
   jdbcProxyDataSourceRuntimeFailedReserveRequestCount OBJECT-TYPE
      SYNTAX      Counter64
      MAX-ACCESS  read-only
      STATUS      current
      DESCRIPTION "The cumulative, running count of requests for a connection from this data source that could not be fulfilled. "
      ::= { jdbcProxyDataSourceRuntimeEntry 19  }
   
   
   jdbcProxyDataSourceRuntimeWaitingForConnectionCurrentCount OBJECT-TYPE
      SYNTAX      Integer32
      MAX-ACCESS  read-only
      STATUS      current
      DESCRIPTION "The number of connection requests waiting for a database connection. "
      ::= { jdbcProxyDataSourceRuntimeEntry 20  }
   
   
   jdbcProxyDataSourceRuntimeConnectionDelayTime OBJECT-TYPE
      SYNTAX      Integer32
      MAX-ACCESS  read-only
      STATUS      current
      DESCRIPTION "The average amount of time, in milliseconds, that it takes to create a physical connection to the database.  The value is calculated as summary of all times to connect divided by the total number of connections. "
      ::= { jdbcProxyDataSourceRuntimeEntry 21  }
   
   
   jdbcProxyDataSourceRuntimeWaitingForConnectionFailureTotal OBJECT-TYPE
      SYNTAX      Counter64
      MAX-ACCESS  read-only
      STATUS      current
      DESCRIPTION "The cumulative, running count of requests for a connection from this data source that had to wait before getting a connection and eventually failed to get a connection.  Waiting connection requests can fail for a variety of reasons, including waiting for longer than the ConnectionReserveTimeoutSeconds. "
      ::= { jdbcProxyDataSourceRuntimeEntry 22  }
   
   
   jdbcProxyDataSourceRuntimeNumAvailable OBJECT-TYPE
      SYNTAX      Integer32
      MAX-ACCESS  read-only
      STATUS      current
      DESCRIPTION "The number of database connections that are currently idle and  available to be used by applications in this instance of the data source. "
      ::= { jdbcProxyDataSourceRuntimeEntry 23  }
   
   
   jdbcProxyDataSourceRuntimePrepStmtCacheAddCount OBJECT-TYPE
      SYNTAX      Counter64
      MAX-ACCESS  read-only
      STATUS      current
      DESCRIPTION "The cumulative, running count of the number of statements added to the statement cache.  Each connection in the connection pool has its own cache of statements. This number is the sum of the number of statements added to the caches for all connections in the connection pool. "
      ::= { jdbcProxyDataSourceRuntimeEntry 24  }
   
   
   jdbcProxyDataSourceRuntimeActiveConnectionsAverageCount OBJECT-TYPE
      SYNTAX      Integer32
      MAX-ACCESS  read-only
      STATUS      current
      DESCRIPTION "Average number of active connections in this instance of the data source.  Active connections are connections in use by an application.  This value is only valid if the resource is configured to allow shrinking. "
      ::= { jdbcProxyDataSourceRuntimeEntry 25  }
   
   
   jdbcProxyDataSourceRuntimeLeakedConnectionCount OBJECT-TYPE
      SYNTAX      Integer32
      MAX-ACCESS  read-only
      STATUS      current
      DESCRIPTION "The number of leaked connections. A leaked connection is a connection that was reserved from the data source but was not returned to the data source by calling close(). "
      ::= { jdbcProxyDataSourceRuntimeEntry 26  }
   
   
   jdbcProxyDataSourceRuntimeDeploymentState OBJECT-TYPE
      SYNTAX      Integer32
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jdbcProxyDataSourceRuntimeEntry 27  }
   
   
   jdbcProxyDataSourceRuntimePrepStmtCacheCurrentSize OBJECT-TYPE
      SYNTAX      Integer32
      MAX-ACCESS  read-only
      STATUS      current
      DESCRIPTION "The number of prepared and callable statements currently cached in the statement cache.  Each connection in the connection pool has its own cache of statements. This number is the sum of the number of statements in the caches for all connections in the connection pool. "
      ::= { jdbcProxyDataSourceRuntimeEntry 28  }
   
   
   jdbcProxyDataSourceRuntimeActiveConnectionsCurrentCount OBJECT-TYPE
      SYNTAX      Integer32
      MAX-ACCESS  read-only
      STATUS      current
      DESCRIPTION "The number of connections currently in use by applications. "
      ::= { jdbcProxyDataSourceRuntimeEntry 29  }
   
   
   jdbcProxyDataSourceRuntimeEnabled OBJECT-TYPE
      SYNTAX      OCTET STRING
      MAX-ACCESS  read-only
      STATUS      current
      DESCRIPTION "Indicates whether the data source is enabled or disabled:   true if the data source is enabled. false if the data source is disabled.  "
      ::= { jdbcProxyDataSourceRuntimeEntry 30  }
   
   
   jdbcProxyDataSourceRuntimeActiveConnectionsHighCount OBJECT-TYPE
      SYNTAX      Integer32
      MAX-ACCESS  read-only
      STATUS      current
      DESCRIPTION "Highest number of active database connections in this instance of the data source since the data source was instantiated.   Active connections are connections in use by an application. "
      ::= { jdbcProxyDataSourceRuntimeEntry 31  }
   
   
   jdbcProxyDataSourceRuntimeCurrCapacity OBJECT-TYPE
      SYNTAX      Integer32
      MAX-ACCESS  read-only
      STATUS      current
      DESCRIPTION "The current count of JDBC connections in the connection pool in the data source. "
      ::= { jdbcProxyDataSourceRuntimeEntry 32  }
   
   
   jdbcProxyDataSourceRuntimeFailuresToReconnectCount OBJECT-TYPE
      SYNTAX      Integer32
      MAX-ACCESS  read-only
      STATUS      current
      DESCRIPTION "The number of times that the data source attempted to refresh a database connection and failed.  Failures may occur when the database is unavailable or when the network connection to the database is interrupted. "
      ::= { jdbcProxyDataSourceRuntimeEntry 33  }
   
   
   jdbcProxyDataSourceRuntimeWaitingForConnectionSuccessTotal OBJECT-TYPE
      SYNTAX      Counter64
      MAX-ACCESS  read-only
      STATUS      current
      DESCRIPTION "The cumulative, running count of requests for a connection from this data source that had to wait before getting a connection and eventually succeeded in getting a connection. "
      ::= { jdbcProxyDataSourceRuntimeEntry 34  }
   
   
   jdbcProxyDataSourceRuntimeType OBJECT-TYPE
      SYNTAX      OCTET STRING
      MAX-ACCESS  read-only
      STATUS      current
      DESCRIPTION "Returns the type of the MBean. "
      ::= { jdbcProxyDataSourceRuntimeEntry 35  }
   
   
   jdbcProxyDataSourceRuntimeDriverVersion OBJECT-TYPE
      SYNTAX      OCTET STRING
      MAX-ACCESS  read-only
      STATUS      current
      DESCRIPTION " The version of the JDBC driver that this data source is configured to use.  "
      ::= { jdbcProxyDataSourceRuntimeEntry 36  }
   
   
   jdbcProxyDataSourceRuntimeState OBJECT-TYPE
      SYNTAX      OCTET STRING
      MAX-ACCESS  read-only
      STATUS      current
      DESCRIPTION "The current state of the data source. Possible states are: Running - the data source is enabled (deployed and not Suspended). This is the normal state of the data source. This state includes conditions when the database server is not available and the data source is created (creation retry must be enabled) or when all connections have failed connection tests (on creation, on reserve, or periodic testing). Suspended - the data source has been disabled. Shutdown - the data source is shutdown and all database connections have been closed. Overloaded - all resources in pool are in use. Unknown - the data source state is unknown. "
      ::= { jdbcProxyDataSourceRuntimeEntry 37  }
   
   
   jdbcProxyDataSourceRuntimeReserveRequestCount OBJECT-TYPE
      SYNTAX      Counter64
      MAX-ACCESS  read-only
      STATUS      current
      DESCRIPTION "The cumulative, running count of requests for a connection from this data source. "
      ::= { jdbcProxyDataSourceRuntimeEntry 38  }
   
   
   jdbcProxyDataSourceRuntimePrepStmtCacheMissCount OBJECT-TYPE
      SYNTAX      Integer32
      MAX-ACCESS  read-only
      STATUS      current
      DESCRIPTION "The number of times that a statement request could not be satisfied with a statement from the cache. "
      ::= { jdbcProxyDataSourceRuntimeEntry 39  }
   
   
   jdbcProxyDataSourceRuntimePrepStmtCacheDeleteCount OBJECT-TYPE
      SYNTAX      Counter64
      MAX-ACCESS  read-only
      STATUS      current
      DESCRIPTION "The cumulative, running count of statements discarded from the cache.  Each connection in the connection pool has its own cache of statements. This number is the sum of the number of statements that were discarded from the caches for all connections in the connection pool. "
      ::= { jdbcProxyDataSourceRuntimeEntry 40  }
   
   
   jdbcProxyDataSourceRuntimeRepurposeCount OBJECT-TYPE
      SYNTAX      Counter64
      MAX-ACCESS  read-only
      STATUS      current
      DESCRIPTION "The number of times connections have been repurposed since the datasource was deployed. "
      ::= { jdbcProxyDataSourceRuntimeEntry 41  }
   
   
   jdbcProxyDataSourceRuntimeUnresolvedTotalCount OBJECT-TYPE
      SYNTAX      Counter64
      MAX-ACCESS  read-only
      STATUS      current
      DESCRIPTION "The cumulative total number of commit outcomes unsuccessfully resolved in this data source since the data source was deployed. This does not refer to the number of outcome query retries used to resolve the outcomes. "
      ::= { jdbcProxyDataSourceRuntimeEntry 42  }
   
   
   jdbcProxyDataSourceRuntimeResolvedAsCommittedTotalCount OBJECT-TYPE
      SYNTAX      Counter64
      MAX-ACCESS  read-only
      STATUS      current
      DESCRIPTION "The cumulative total number of commit outcomes successfully resolved as committed in this data source since the data source was deployed. This does not refer to the number of outcome query retries used to resolve the outcomes. "
      ::= { jdbcProxyDataSourceRuntimeEntry 43  }
   
   
   jdbcProxyDataSourceRuntimeCommitOutcomeRetryTotalCount OBJECT-TYPE
      SYNTAX      Counter64
      MAX-ACCESS  read-only
      STATUS      current
      DESCRIPTION "The cumulative total number of commit outcome query retries conducted before resolving the outcome or exceeding the retry seconds in this data source since the data source was deployed. "
      ::= { jdbcProxyDataSourceRuntimeEntry 44  }
   
   
   jdbcProxyDataSourceRuntimeResolvedAsNotCommittedTotalCount OBJECT-TYPE
      SYNTAX      Counter64
      MAX-ACCESS  read-only
      STATUS      current
      DESCRIPTION "The cumulative total number of commit outcomes successfully resolved as not committed in this data source since the data source was deployed. This does not refer to the number of outcome query retries used to resolve the outcomes. "
      ::= { jdbcProxyDataSourceRuntimeEntry 45  }
   
   
   jdbcProxyDataSourceRuntimeFailedRepurposeCount OBJECT-TYPE
      SYNTAX      Counter64
      MAX-ACCESS  read-only
      STATUS      current
      DESCRIPTION "The number of repurpose errors that have occurred since the datasource was deployed. "
      ::= { jdbcProxyDataSourceRuntimeEntry 46  }
   
   
   jdbcReplayStatisticsRuntimeTable OBJECT-TYPE
      SYNTAX      SEQUENCE OF JdbcReplayStatisticsRuntimeEntry
      MAX-ACCESS  not-accessible
      STATUS      current
      DESCRIPTION "This class is used to get replay statics for an Oracle replay datasource aggregated across all connections in the pool. "
      ::= { wls 2305  }
      
   
   jdbcReplayStatisticsRuntimeEntry OBJECT-TYPE
      SYNTAX      JdbcReplayStatisticsRuntimeEntry
      MAX-ACCESS  not-accessible
      STATUS      current
      DESCRIPTION "Generated SNMP Table Entry."
      INDEX { jdbcReplayStatisticsRuntimeIndex}
      ::= { jdbcReplayStatisticsRuntimeTable 1 }
      
   JdbcReplayStatisticsRuntimeEntry ::=
      SEQUENCE
      {
         jdbcReplayStatisticsRuntimeIndex OCTET STRING,
         jdbcReplayStatisticsRuntimeObjectName OCTET STRING,
         jdbcReplayStatisticsRuntimeDeploymentState Integer32,
         jdbcReplayStatisticsRuntimeTotalCalls Counter64,
         jdbcReplayStatisticsRuntimeTotalCompletedRequests Counter64,
         jdbcReplayStatisticsRuntimeFailedReplayCount Counter64,
         jdbcReplayStatisticsRuntimeTotalRequests Counter64,
         jdbcReplayStatisticsRuntimeName OCTET STRING,
         jdbcReplayStatisticsRuntimeModuleId OCTET STRING,
         jdbcReplayStatisticsRuntimeTotalCallsTriggeringReplay Counter64,
         jdbcReplayStatisticsRuntimeType OCTET STRING,
         jdbcReplayStatisticsRuntimeTotalReplayAttempts Counter64,
         jdbcReplayStatisticsRuntimeTotalProtectedCalls Counter64,
         jdbcReplayStatisticsRuntimeSuccessfulReplayCount Counter64,
         jdbcReplayStatisticsRuntimeTotalCallsAffectedByOutages Counter64,
         jdbcReplayStatisticsRuntimeTotalCallsAffectedByOutagesDuringReplay Counter64,
         jdbcReplayStatisticsRuntimeReplayDisablingCount Counter64
      }
      
   
   jdbcReplayStatisticsRuntimeIndex OBJECT-TYPE
      SYNTAX      OCTET STRING
      MAX-ACCESS  not-accessible
      STATUS      current
      DESCRIPTION "Index column"
      ::= { jdbcReplayStatisticsRuntimeEntry 1  }
   
   
   jdbcReplayStatisticsRuntimeObjectName OBJECT-TYPE
      SYNTAX      OCTET STRING
      MAX-ACCESS  read-only
      STATUS      current
      DESCRIPTION "ObjectName column"
      ::= { jdbcReplayStatisticsRuntimeEntry 2  }
   
   
   jdbcReplayStatisticsRuntimeDeploymentState OBJECT-TYPE
      SYNTAX      Integer32
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jdbcReplayStatisticsRuntimeEntry 3  }
   
   
   jdbcReplayStatisticsRuntimeTotalCalls OBJECT-TYPE
      SYNTAX      Counter64
      MAX-ACCESS  read-only
      STATUS      current
      DESCRIPTION "Obtains the total number of JDBC calls executed so far. "
      ::= { jdbcReplayStatisticsRuntimeEntry 4  }
   
   
   jdbcReplayStatisticsRuntimeTotalCompletedRequests OBJECT-TYPE
      SYNTAX      Counter64
      MAX-ACCESS  read-only
      STATUS      current
      DESCRIPTION "Obtains the total number of completed requests so far. "
      ::= { jdbcReplayStatisticsRuntimeEntry 5  }
   
   
   jdbcReplayStatisticsRuntimeFailedReplayCount OBJECT-TYPE
      SYNTAX      Counter64
      MAX-ACCESS  read-only
      STATUS      current
      DESCRIPTION "Obtains the number of replays that failed.  When replay fails, it rethrows the original SQLRecoverableException to the application, with the reason for the failure chained to that original exception. Application can call getNextException to retrieve the reason. "
      ::= { jdbcReplayStatisticsRuntimeEntry 6  }
   
   
   jdbcReplayStatisticsRuntimeTotalRequests OBJECT-TYPE
      SYNTAX      Counter64
      MAX-ACCESS  read-only
      STATUS      current
      DESCRIPTION "Obtains the total number of successfully submitted requests so far. "
      ::= { jdbcReplayStatisticsRuntimeEntry 7  }
   
   
   jdbcReplayStatisticsRuntimeName OBJECT-TYPE
      SYNTAX      OCTET STRING
      MAX-ACCESS  read-only
      STATUS      current
      DESCRIPTION "The name of this configuration. WebLogic Server uses an MBean to implement and persist the configuration. "
      ::= { jdbcReplayStatisticsRuntimeEntry 8  }
   
   
   jdbcReplayStatisticsRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { jdbcReplayStatisticsRuntimeEntry 9  }
   
   
   jdbcReplayStatisticsRuntimeTotalCallsTriggeringReplay OBJECT-TYPE
      SYNTAX      Counter64
      MAX-ACCESS  read-only
      STATUS      current
      DESCRIPTION "Obtains the number of JDBC calls that triggered replay. Not all the calls affected by an outage trigger replay, because replay can be disabled for some requests. "
      ::= { jdbcReplayStatisticsRuntimeEntry 10  }
   
   
   jdbcReplayStatisticsRuntimeType OBJECT-TYPE
      SYNTAX      OCTET STRING
      MAX-ACCESS  read-only
      STATUS      current
      DESCRIPTION "Returns the type of the MBean. "
      ::= { jdbcReplayStatisticsRuntimeEntry 11  }
   
   
   jdbcReplayStatisticsRuntimeTotalReplayAttempts OBJECT-TYPE
      SYNTAX      Counter64
      MAX-ACCESS  read-only
      STATUS      current
      DESCRIPTION "Obtains the number of replay attempts.  AC automatically reattempts when replay fails, so this number may exceed the number of JDBC calls that triggered replay. "
      ::= { jdbcReplayStatisticsRuntimeEntry 12  }
   
   
   jdbcReplayStatisticsRuntimeTotalProtectedCalls OBJECT-TYPE
      SYNTAX      Counter64
      MAX-ACCESS  read-only
      STATUS      current
      DESCRIPTION "Obtains the total number of JDBC calls executed so far that are protected by AC. "
      ::= { jdbcReplayStatisticsRuntimeEntry 13  }
   
   
   jdbcReplayStatisticsRuntimeSuccessfulReplayCount OBJECT-TYPE
      SYNTAX      Counter64
      MAX-ACCESS  read-only
      STATUS      current
      DESCRIPTION "Obtains the number of replays that succeeded. Successful replays mask the outages from applications. "
      ::= { jdbcReplayStatisticsRuntimeEntry 14  }
   
   
   jdbcReplayStatisticsRuntimeTotalCallsAffectedByOutages OBJECT-TYPE
      SYNTAX      Counter64
      MAX-ACCESS  read-only
      STATUS      current
      DESCRIPTION "Obtains the number of JDBC calls affected by outages. This includes both local calls and calls that involve roundtrip(s) to the database server. "
      ::= { jdbcReplayStatisticsRuntimeEntry 15  }
   
   
   jdbcReplayStatisticsRuntimeTotalCallsAffectedByOutagesDuringReplay OBJECT-TYPE
      SYNTAX      Counter64
      MAX-ACCESS  read-only
      STATUS      current
      DESCRIPTION "Obtains the number of JDBC calls affected by outages in the middle of replay. Outages may be cascaded and strike a call multiple times when replay is ongoing. AC automatically reattempts replay when this happens, unless it reaches the maximum retry limit."
      ::= { jdbcReplayStatisticsRuntimeEntry 16  }
   
   
   jdbcReplayStatisticsRuntimeReplayDisablingCount OBJECT-TYPE
      SYNTAX      Counter64
      MAX-ACCESS  read-only
      STATUS      current
      DESCRIPTION "Obtains the number of times that replay is disabled.  When replay is disabled in the middle of a request, the remaining calls in that request are no longer protected by AC. In case an outage strikes one of those remaining calls, no replay will be attempted, and application simply gets an SQLRecoverableException. "
      ::= { jdbcReplayStatisticsRuntimeEntry 17  }
   
   
   jdbcUCPDataSourceRuntimeTable OBJECT-TYPE
      SYNTAX      SEQUENCE OF JdbcUCPDataSourceRuntimeEntry
      MAX-ACCESS  not-accessible
      STATUS      current
      DESCRIPTION "Runtime MBean that represents a UCP JDBC data source. "
      ::= { wls 2310  }
      
   
   jdbcUCPDataSourceRuntimeEntry OBJECT-TYPE
      SYNTAX      JdbcUCPDataSourceRuntimeEntry
      MAX-ACCESS  not-accessible
      STATUS      current
      DESCRIPTION "Generated SNMP Table Entry."
      INDEX { jdbcUCPDataSourceRuntimeIndex}
      ::= { jdbcUCPDataSourceRuntimeTable 1 }
      
   JdbcUCPDataSourceRuntimeEntry ::=
      SEQUENCE
      {
         jdbcUCPDataSourceRuntimeIndex OCTET STRING,
         jdbcUCPDataSourceRuntimeObjectName OCTET STRING,
         jdbcUCPDataSourceRuntimeDatabaseProductName OCTET STRING,
         jdbcUCPDataSourceRuntimePrepStmtCacheAccessCount Counter64,
         jdbcUCPDataSourceRuntimeConnectionsTotalCount Integer32,
         jdbcUCPDataSourceRuntimeDriverName OCTET STRING,
         jdbcUCPDataSourceRuntimeHighestNumUnavailable Integer32,
         jdbcUCPDataSourceRuntimeDatabaseProductVersion OCTET STRING,
         jdbcUCPDataSourceRuntimeHighestNumAvailable Integer32,
         jdbcUCPDataSourceRuntimeWaitSecondsHighCount Integer32,
         jdbcUCPDataSourceRuntimeWaitingForConnectionHighCount Integer32,
         jdbcUCPDataSourceRuntimeVersionJDBCDriver OCTET STRING,
         jdbcUCPDataSourceRuntimeName OCTET STRING,
         jdbcUCPDataSourceRuntimeWaitingForConnectionTotal Counter64,
         jdbcUCPDataSourceRuntimeCurrCapacityHighCount Integer32,
         jdbcUCPDataSourceRuntimeModuleId OCTET STRING,
         jdbcUCPDataSourceRuntimeNumUnavailable Integer32,
         jdbcUCPDataSourceRuntimePrepStmtCacheHitCount Integer32,
         jdbcUCPDataSourceRuntimeFailedReserveRequestCount Counter64,
         jdbcUCPDataSourceRuntimeWaitingForConnectionCurrentCount Integer32,
         jdbcUCPDataSourceRuntimeConnectionDelayTime Integer32,
         jdbcUCPDataSourceRuntimeWaitingForConnectionFailureTotal Counter64,
         jdbcUCPDataSourceRuntimeNumAvailable Integer32,
         jdbcUCPDataSourceRuntimePrepStmtCacheAddCount Counter64,
         jdbcUCPDataSourceRuntimeActiveConnectionsAverageCount Integer32,
         jdbcUCPDataSourceRuntimeLeakedConnectionCount Integer32,
         jdbcUCPDataSourceRuntimeDeploymentState Integer32,
         jdbcUCPDataSourceRuntimePrepStmtCacheCurrentSize Integer32,
         jdbcUCPDataSourceRuntimeActiveConnectionsCurrentCount Integer32,
         jdbcUCPDataSourceRuntimeEnabled OCTET STRING,
         jdbcUCPDataSourceRuntimeActiveConnectionsHighCount Integer32,
         jdbcUCPDataSourceRuntimeCurrCapacity Integer32,
         jdbcUCPDataSourceRuntimeFailuresToReconnectCount Integer32,
         jdbcUCPDataSourceRuntimeWaitingForConnectionSuccessTotal Counter64,
         jdbcUCPDataSourceRuntimeType OCTET STRING,
         jdbcUCPDataSourceRuntimeDriverVersion OCTET STRING,
         jdbcUCPDataSourceRuntimeState OCTET STRING,
         jdbcUCPDataSourceRuntimeReserveRequestCount Counter64,
         jdbcUCPDataSourceRuntimePrepStmtCacheMissCount Integer32,
         jdbcUCPDataSourceRuntimePrepStmtCacheDeleteCount Counter64,
         jdbcUCPDataSourceRuntimeRepurposeCount Counter64,
         jdbcUCPDataSourceRuntimeUnresolvedTotalCount Counter64,
         jdbcUCPDataSourceRuntimeResolvedAsCommittedTotalCount Counter64,
         jdbcUCPDataSourceRuntimeCommitOutcomeRetryTotalCount Counter64,
         jdbcUCPDataSourceRuntimeResolvedAsNotCommittedTotalCount Counter64,
         jdbcUCPDataSourceRuntimeFailedRepurposeCount Counter64
      }
      
   
   jdbcUCPDataSourceRuntimeIndex OBJECT-TYPE
      SYNTAX      OCTET STRING
      MAX-ACCESS  not-accessible
      STATUS      current
      DESCRIPTION "Index column"
      ::= { jdbcUCPDataSourceRuntimeEntry 1  }
   
   
   jdbcUCPDataSourceRuntimeObjectName OBJECT-TYPE
      SYNTAX      OCTET STRING
      MAX-ACCESS  read-only
      STATUS      current
      DESCRIPTION "ObjectName column"
      ::= { jdbcUCPDataSourceRuntimeEntry 2  }
   
   
   jdbcUCPDataSourceRuntimeDatabaseProductName OBJECT-TYPE
      SYNTAX      OCTET STRING
      MAX-ACCESS  read-only
      STATUS      current
      DESCRIPTION " The product name of the database that this data source is connected to.  "
      ::= { jdbcUCPDataSourceRuntimeEntry 3  }
   
   
   jdbcUCPDataSourceRuntimePrepStmtCacheAccessCount OBJECT-TYPE
      SYNTAX      Counter64
      MAX-ACCESS  read-only
      STATUS      current
      DESCRIPTION "The cumulative, running count of the number of times that the statement cache was accessed. "
      ::= { jdbcUCPDataSourceRuntimeEntry 4  }
   
   
   jdbcUCPDataSourceRuntimeConnectionsTotalCount OBJECT-TYPE
      SYNTAX      Integer32
      MAX-ACCESS  read-only
      STATUS      current
      DESCRIPTION "The cumulative total number of database connections created in this data source since the data source was deployed. "
      ::= { jdbcUCPDataSourceRuntimeEntry 5  }
   
   
   jdbcUCPDataSourceRuntimeDriverName OBJECT-TYPE
      SYNTAX      OCTET STRING
      MAX-ACCESS  read-only
      STATUS      current
      DESCRIPTION " The product name of the JDBC driver that this data source is configured to use.  "
      ::= { jdbcUCPDataSourceRuntimeEntry 6  }
   
   
   jdbcUCPDataSourceRuntimeHighestNumUnavailable OBJECT-TYPE
      SYNTAX      Integer32
      MAX-ACCESS  read-only
      STATUS      current
      DESCRIPTION "Highest number of database connections that were in use by applications or being tested by the system in this instance of the data source since the data source was deployed. "
      ::= { jdbcUCPDataSourceRuntimeEntry 7  }
   
   
   jdbcUCPDataSourceRuntimeDatabaseProductVersion OBJECT-TYPE
      SYNTAX      OCTET STRING
      MAX-ACCESS  read-only
      STATUS      current
      DESCRIPTION " The product version of the database that this data source is connected to.  "
      ::= { jdbcUCPDataSourceRuntimeEntry 8  }
   
   
   jdbcUCPDataSourceRuntimeHighestNumAvailable OBJECT-TYPE
      SYNTAX      Integer32
      MAX-ACCESS  read-only
      STATUS      current
      DESCRIPTION "Highest number of database connections that were idle and available to be used by an application at any time in this instance of the data source since the data source was deployed. "
      ::= { jdbcUCPDataSourceRuntimeEntry 9  }
   
   
   jdbcUCPDataSourceRuntimeWaitSecondsHighCount OBJECT-TYPE
      SYNTAX      Integer32
      MAX-ACCESS  read-only
      STATUS      current
      DESCRIPTION "The highest number of seconds that an application waited for a connection (the longest connection reserve wait time) from this instance of the connection pool since the connection pool was instantiated. This value is updated when a completed getConnection request takes longer to return a connection than any previous request. "
      ::= { jdbcUCPDataSourceRuntimeEntry 10  }
   
   
   jdbcUCPDataSourceRuntimeWaitingForConnectionHighCount OBJECT-TYPE
      SYNTAX      Integer32
      MAX-ACCESS  read-only
      STATUS      current
      DESCRIPTION "Highest number of application requests concurrently waiting for a connection from this instance of the data source. "
      ::= { jdbcUCPDataSourceRuntimeEntry 11  }
   
   
   jdbcUCPDataSourceRuntimeVersionJDBCDriver OBJECT-TYPE
      SYNTAX      OCTET STRING
      MAX-ACCESS  read-only
      STATUS      current
      DESCRIPTION "The driver class name of the JDBC driver used to create database connections.  "
      ::= { jdbcUCPDataSourceRuntimeEntry 12  }
   
   
   jdbcUCPDataSourceRuntimeName OBJECT-TYPE
      SYNTAX      OCTET STRING
      MAX-ACCESS  read-only
      STATUS      current
      DESCRIPTION "The name of this configuration. WebLogic Server uses an MBean to implement and persist the configuration. "
      ::= { jdbcUCPDataSourceRuntimeEntry 13  }
   
   
   jdbcUCPDataSourceRuntimeWaitingForConnectionTotal OBJECT-TYPE
      SYNTAX      Counter64
      MAX-ACCESS  read-only
      STATUS      current
      DESCRIPTION "The cumulative, running count of requests for a connection from this data source that had to wait before getting a connection, including those that eventually got a connection and those that did not get a connection. "
      ::= { jdbcUCPDataSourceRuntimeEntry 14  }
   
   
   jdbcUCPDataSourceRuntimeCurrCapacityHighCount OBJECT-TYPE
      SYNTAX      Integer32
      MAX-ACCESS  read-only
      STATUS      current
      DESCRIPTION "Highest number of database connections available or in use (current capacity) in this instance of the data source since the data source was deployed. "
      ::= { jdbcUCPDataSourceRuntimeEntry 15  }
   
   
   jdbcUCPDataSourceRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { jdbcUCPDataSourceRuntimeEntry 16  }
   
   
   jdbcUCPDataSourceRuntimeNumUnavailable OBJECT-TYPE
      SYNTAX      Integer32
      MAX-ACCESS  read-only
      STATUS      current
      DESCRIPTION "The number of connections currently in use by applications or being tested in this instance of the data source. "
      ::= { jdbcUCPDataSourceRuntimeEntry 17  }
   
   
   jdbcUCPDataSourceRuntimePrepStmtCacheHitCount OBJECT-TYPE
      SYNTAX      Integer32
      MAX-ACCESS  read-only
      STATUS      current
      DESCRIPTION "The cumulative, running count of the number of times that statements from the cache were used. "
      ::= { jdbcUCPDataSourceRuntimeEntry 18  }
   
   
   jdbcUCPDataSourceRuntimeFailedReserveRequestCount OBJECT-TYPE
      SYNTAX      Counter64
      MAX-ACCESS  read-only
      STATUS      current
      DESCRIPTION "The cumulative, running count of requests for a connection from this data source that could not be fulfilled. "
      ::= { jdbcUCPDataSourceRuntimeEntry 19  }
   
   
   jdbcUCPDataSourceRuntimeWaitingForConnectionCurrentCount OBJECT-TYPE
      SYNTAX      Integer32
      MAX-ACCESS  read-only
      STATUS      current
      DESCRIPTION "The number of connection requests waiting for a database connection. "
      ::= { jdbcUCPDataSourceRuntimeEntry 20  }
   
   
   jdbcUCPDataSourceRuntimeConnectionDelayTime OBJECT-TYPE
      SYNTAX      Integer32
      MAX-ACCESS  read-only
      STATUS      current
      DESCRIPTION "The average amount of time, in milliseconds, that it takes to create a physical connection to the database.  The value is calculated as summary of all times to connect divided by the total number of connections. "
      ::= { jdbcUCPDataSourceRuntimeEntry 21  }
   
   
   jdbcUCPDataSourceRuntimeWaitingForConnectionFailureTotal OBJECT-TYPE
      SYNTAX      Counter64
      MAX-ACCESS  read-only
      STATUS      current
      DESCRIPTION "The cumulative, running count of requests for a connection from this data source that had to wait before getting a connection and eventually failed to get a connection.  Waiting connection requests can fail for a variety of reasons, including waiting for longer than the ConnectionReserveTimeoutSeconds. "
      ::= { jdbcUCPDataSourceRuntimeEntry 22  }
   
   
   jdbcUCPDataSourceRuntimeNumAvailable OBJECT-TYPE
      SYNTAX      Integer32
      MAX-ACCESS  read-only
      STATUS      current
      DESCRIPTION "The number of database connections that are currently idle and  available to be used by applications in this instance of the data source. "
      ::= { jdbcUCPDataSourceRuntimeEntry 23  }
   
   
   jdbcUCPDataSourceRuntimePrepStmtCacheAddCount OBJECT-TYPE
      SYNTAX      Counter64
      MAX-ACCESS  read-only
      STATUS      current
      DESCRIPTION "The cumulative, running count of the number of statements added to the statement cache.  Each connection in the connection pool has its own cache of statements. This number is the sum of the number of statements added to the caches for all connections in the connection pool. "
      ::= { jdbcUCPDataSourceRuntimeEntry 24  }
   
   
   jdbcUCPDataSourceRuntimeActiveConnectionsAverageCount OBJECT-TYPE
      SYNTAX      Integer32
      MAX-ACCESS  read-only
      STATUS      current
      DESCRIPTION "Average number of active connections in this instance of the data source.  Active connections are connections in use by an application.  This value is only valid if the resource is configured to allow shrinking. "
      ::= { jdbcUCPDataSourceRuntimeEntry 25  }
   
   
   jdbcUCPDataSourceRuntimeLeakedConnectionCount OBJECT-TYPE
      SYNTAX      Integer32
      MAX-ACCESS  read-only
      STATUS      current
      DESCRIPTION "The number of leaked connections. A leaked connection is a connection that was reserved from the data source but was not returned to the data source by calling close(). "
      ::= { jdbcUCPDataSourceRuntimeEntry 26  }
   
   
   jdbcUCPDataSourceRuntimeDeploymentState OBJECT-TYPE
      SYNTAX      Integer32
      MAX-ACCESS  read-only
      STATUS      current
      DESCRIPTION "The current deployment state of the module.  A module can be in one and only one of the following states. State can be changed via deployment or administrator console.   UNPREPARED. State indicating at this  module is neither  prepared or active.  PREPARED. State indicating at this module of this application is prepared, but not active. The classes have been loaded and the module has been validated.  ACTIVATED. State indicating at this module  is currently active.  NEW. State indicating this module has just been created and is being initialized.  "
      ::= { jdbcUCPDataSourceRuntimeEntry 27  }
   
   
   jdbcUCPDataSourceRuntimePrepStmtCacheCurrentSize OBJECT-TYPE
      SYNTAX      Integer32
      MAX-ACCESS  read-only
      STATUS      current
      DESCRIPTION "The number of prepared and callable statements currently cached in the statement cache.  Each connection in the connection pool has its own cache of statements. This number is the sum of the number of statements in the caches for all connections in the connection pool. "
      ::= { jdbcUCPDataSourceRuntimeEntry 28  }
   
   
   jdbcUCPDataSourceRuntimeActiveConnectionsCurrentCount OBJECT-TYPE
      SYNTAX      Integer32
      MAX-ACCESS  read-only
      STATUS      current
      DESCRIPTION "The number of connections currently in use by applications. "
      ::= { jdbcUCPDataSourceRuntimeEntry 29  }
   
   
   jdbcUCPDataSourceRuntimeEnabled OBJECT-TYPE
      SYNTAX      OCTET STRING
      MAX-ACCESS  read-only
      STATUS      current
      DESCRIPTION "Indicates whether the data source is enabled or disabled:   true if the data source is enabled. false if the data source is disabled.  "
      ::= { jdbcUCPDataSourceRuntimeEntry 30  }
   
   
   jdbcUCPDataSourceRuntimeActiveConnectionsHighCount OBJECT-TYPE
      SYNTAX      Integer32
      MAX-ACCESS  read-only
      STATUS      current
      DESCRIPTION "Highest number of active database connections in this instance of the data source since the data source was instantiated.   Active connections are connections in use by an application. "
      ::= { jdbcUCPDataSourceRuntimeEntry 31  }
   
   
   jdbcUCPDataSourceRuntimeCurrCapacity OBJECT-TYPE
      SYNTAX      Integer32
      MAX-ACCESS  read-only
      STATUS      current
      DESCRIPTION "The current count of JDBC connections in the connection pool in the data source. "
      ::= { jdbcUCPDataSourceRuntimeEntry 32  }
   
   
   jdbcUCPDataSourceRuntimeFailuresToReconnectCount OBJECT-TYPE
      SYNTAX      Integer32
      MAX-ACCESS  read-only
      STATUS      current
      DESCRIPTION "The number of times that the data source attempted to refresh a database connection and failed.  Failures may occur when the database is unavailable or when the network connection to the database is interrupted. "
      ::= { jdbcUCPDataSourceRuntimeEntry 33  }
   
   
   jdbcUCPDataSourceRuntimeWaitingForConnectionSuccessTotal OBJECT-TYPE
      SYNTAX      Counter64
      MAX-ACCESS  read-only
      STATUS      current
      DESCRIPTION "The cumulative, running count of requests for a connection from this data source that had to wait before getting a connection and eventually succeeded in getting a connection. "
      ::= { jdbcUCPDataSourceRuntimeEntry 34  }
   
   
   jdbcUCPDataSourceRuntimeType OBJECT-TYPE
      SYNTAX      OCTET STRING
      MAX-ACCESS  read-only
      STATUS      current
      DESCRIPTION "Returns the type of the MBean. "
      ::= { jdbcUCPDataSourceRuntimeEntry 35  }
   
   
   jdbcUCPDataSourceRuntimeDriverVersion OBJECT-TYPE
      SYNTAX      OCTET STRING
      MAX-ACCESS  read-only
      STATUS      current
      DESCRIPTION " The version of the JDBC driver that this data source is configured to use.  "
      ::= { jdbcUCPDataSourceRuntimeEntry 36  }
   
   
   jdbcUCPDataSourceRuntimeState OBJECT-TYPE
      SYNTAX      OCTET STRING
      MAX-ACCESS  read-only
      STATUS      current
      DESCRIPTION "The current state of the data source. Possible states are: Running - the data source is enabled (deployed and not Suspended). This is the normal state of the data source. This state includes conditions when the database server is not available and the data source is created (creation retry must be enabled) or when all connections have failed connection tests (on creation, on reserve, or periodic testing). Suspended - the data source has been disabled. Shutdown - the data source is shutdown and all database connections have been closed. Overloaded - all resources in pool are in use. Unknown - the data source state is unknown. "
      ::= { jdbcUCPDataSourceRuntimeEntry 37  }
   
   
   jdbcUCPDataSourceRuntimeReserveRequestCount OBJECT-TYPE
      SYNTAX      Counter64
      MAX-ACCESS  read-only
      STATUS      current
      DESCRIPTION "The cumulative, running count of requests for a connection from this data source. "
      ::= { jdbcUCPDataSourceRuntimeEntry 38  }
   
   
   jdbcUCPDataSourceRuntimePrepStmtCacheMissCount OBJECT-TYPE
      SYNTAX      Integer32
      MAX-ACCESS  read-only
      STATUS      current
      DESCRIPTION "The number of times that a statement request could not be satisfied with a statement from the cache. "
      ::= { jdbcUCPDataSourceRuntimeEntry 39  }
   
   
   jdbcUCPDataSourceRuntimePrepStmtCacheDeleteCount OBJECT-TYPE
      SYNTAX      Counter64
      MAX-ACCESS  read-only
      STATUS      current
      DESCRIPTION "The cumulative, running count of statements discarded from the cache.  Each connection in the connection pool has its own cache of statements. This number is the sum of the number of statements that were discarded from the caches for all connections in the connection pool. "
      ::= { jdbcUCPDataSourceRuntimeEntry 40  }
   
   
   jdbcUCPDataSourceRuntimeRepurposeCount OBJECT-TYPE
      SYNTAX      Counter64
      MAX-ACCESS  read-only
      STATUS      current
      DESCRIPTION "The number of times connections have been repurposed since the datasource was deployed. "
      ::= { jdbcUCPDataSourceRuntimeEntry 41  }
   
   
   jdbcUCPDataSourceRuntimeUnresolvedTotalCount OBJECT-TYPE
      SYNTAX      Counter64
      MAX-ACCESS  read-only
      STATUS      current
      DESCRIPTION "The cumulative total number of commit outcomes unsuccessfully resolved in this data source since the data source was deployed. This does not refer to the number of outcome query retries used to resolve the outcomes. "
      ::= { jdbcUCPDataSourceRuntimeEntry 42  }
   
   
   jdbcUCPDataSourceRuntimeResolvedAsCommittedTotalCount OBJECT-TYPE
      SYNTAX      Counter64
      MAX-ACCESS  read-only
      STATUS      current
      DESCRIPTION "The cumulative total number of commit outcomes successfully resolved as committed in this data source since the data source was deployed. This does not refer to the number of outcome query retries used to resolve the outcomes. "
      ::= { jdbcUCPDataSourceRuntimeEntry 43  }
   
   
   jdbcUCPDataSourceRuntimeCommitOutcomeRetryTotalCount OBJECT-TYPE
      SYNTAX      Counter64
      MAX-ACCESS  read-only
      STATUS      current
      DESCRIPTION "The cumulative total number of commit outcome query retries conducted before resolving the outcome or exceeding the retry seconds in this data source since the data source was deployed. "
      ::= { jdbcUCPDataSourceRuntimeEntry 44  }
   
   
   jdbcUCPDataSourceRuntimeResolvedAsNotCommittedTotalCount OBJECT-TYPE
      SYNTAX      Counter64
      MAX-ACCESS  read-only
      STATUS      current
      DESCRIPTION "The cumulative total number of commit outcomes successfully resolved as not committed in this data source since the data source was deployed. This does not refer to the number of outcome query retries used to resolve the outcomes. "
      ::= { jdbcUCPDataSourceRuntimeEntry 45  }
   
   
   jdbcUCPDataSourceRuntimeFailedRepurposeCount OBJECT-TYPE
      SYNTAX      Counter64
      MAX-ACCESS  read-only
      STATUS      current
      DESCRIPTION "The number of repurpose errors that have occurred since the datasource was deployed. "
      ::= { jdbcUCPDataSourceRuntimeEntry 46  }
   
   
   jtaPartitionRuntimeTable OBJECT-TYPE
      SYNTAX      SEQUENCE OF JtaPartitionRuntimeEntry
      MAX-ACCESS  not-accessible
      STATUS      current
      DESCRIPTION "This interface is used for accessing transaction runtime characteristics within a WebLogic server. "
      ::= { wls 2315  }
      
   
   jtaPartitionRuntimeEntry OBJECT-TYPE
      SYNTAX      JtaPartitionRuntimeEntry
      MAX-ACCESS  not-accessible
      STATUS      current
      DESCRIPTION "Generated SNMP Table Entry."
      INDEX { jtaPartitionRuntimeIndex}
      ::= { jtaPartitionRuntimeTable 1 }
      
   JtaPartitionRuntimeEntry ::=
      SEQUENCE
      {
         jtaPartitionRuntimeIndex OCTET STRING,
         jtaPartitionRuntimeObjectName OCTET STRING,
         jtaPartitionRuntimeTransactionReadOnlyOnePhaseCommittedTotalCount Counter64,
         jtaPartitionRuntimeTransactionOneResourceOnePhaseCommittedTotalCount Counter64,
         jtaPartitionRuntimeTransactionTwoPhaseCommittedTotalCount Counter64,
         jtaPartitionRuntimeName OCTET STRING,
         jtaPartitionRuntimeTransactionTwoPhaseCommittedNotLoggedTotalCount Counter64,
         jtaPartitionRuntimeTransactionRolledBackAppTotalCount Counter64,
         jtaPartitionRuntimeTransactionRolledBackTotalCount Counter64,
         jtaPartitionRuntimeTransactionRolledBackResourceTotalCount Counter64,
         jtaPartitionRuntimeTransactionRolledBackSystemTotalCount Counter64,
         jtaPartitionRuntimeTransactionCommittedTotalCount Counter64,
         jtaPartitionRuntimeSecondsActiveTotalCount Counter64,
         jtaPartitionRuntimeType OCTET STRING,
         jtaPartitionRuntimeTransactionLLRCommittedTotalCount Counter64,
         jtaPartitionRuntimeActiveTransactionsTotalCount Integer32,
         jtaPartitionRuntimeRegisteredNonXAResourceNames OCTET STRING,
         jtaPartitionRuntimeRegisteredResourceNames OCTET STRING,
         jtaPartitionRuntimeTransactionAbandonedTotalCount Counter64,
         jtaPartitionRuntimeTransactionRolledBackTimeoutTotalCount Counter64,
         jtaPartitionRuntimeTransactionNoResourcesCommittedTotalCount Counter64,
         jtaPartitionRuntimeTransactionTotalCount Counter64,
         jtaPartitionRuntimeTransactionHeuristicsTotalCount Counter64,
         jtaPartitionRuntimeTransactionTwoPhaseCommittedLoggedTotalCount Counter64
      }
      
   
   jtaPartitionRuntimeIndex OBJECT-TYPE
      SYNTAX      OCTET STRING
      MAX-ACCESS  not-accessible
      STATUS      current
      DESCRIPTION "Index column"
      ::= { jtaPartitionRuntimeEntry 1  }
   
   
   jtaPartitionRuntimeObjectName OBJECT-TYPE
      SYNTAX      OCTET STRING
      MAX-ACCESS  read-only
      STATUS      current
      DESCRIPTION "ObjectName column"
      ::= { jtaPartitionRuntimeEntry 2  }
   
   
   jtaPartitionRuntimeTransactionReadOnlyOnePhaseCommittedTotalCount OBJECT-TYPE
      SYNTAX      Counter64
      MAX-ACCESS  read-only
      STATUS      current
      DESCRIPTION "The total number of transactions with more than one enlisted resource that were one-phase committed due to read-only optimization since the server was started."
      ::= { jtaPartitionRuntimeEntry 3  }
   
   
   jtaPartitionRuntimeTransactionOneResourceOnePhaseCommittedTotalCount OBJECT-TYPE
      SYNTAX      Counter64
      MAX-ACCESS  read-only
      STATUS      current
      DESCRIPTION "The total number of transactions with only one enlisted resource that were one-phase committed since the server was started."
      ::= { jtaPartitionRuntimeEntry 4  }
   
   
   jtaPartitionRuntimeTransactionTwoPhaseCommittedTotalCount OBJECT-TYPE
      SYNTAX      Counter64
      MAX-ACCESS  read-only
      STATUS      current
      DESCRIPTION "The total number of transactions with more than one enlisted resource that were two-phase committed since the server was started. "
      ::= { jtaPartitionRuntimeEntry 5  }
   
   
   jtaPartitionRuntimeName OBJECT-TYPE
      SYNTAX      OCTET STRING
      MAX-ACCESS  read-only
      STATUS      current
      DESCRIPTION "The name of this configuration. WebLogic Server uses an MBean to implement and persist the configuration. "
      ::= { jtaPartitionRuntimeEntry 6  }
   
   
   jtaPartitionRuntimeTransactionTwoPhaseCommittedNotLoggedTotalCount OBJECT-TYPE
      SYNTAX      Counter64
      MAX-ACCESS  read-only
      STATUS      current
      DESCRIPTION "The total number of two phase commited transactions that were committed without TLog since the server was started."
      ::= { jtaPartitionRuntimeEntry 7  }
   
   
   jtaPartitionRuntimeTransactionRolledBackAppTotalCount OBJECT-TYPE
      SYNTAX      Counter64
      MAX-ACCESS  read-only
      STATUS      current
      DESCRIPTION "The number of transactions that were rolled back due to an application error. "
      ::= { jtaPartitionRuntimeEntry 8  }
   
   
   jtaPartitionRuntimeTransactionRolledBackTotalCount OBJECT-TYPE
      SYNTAX      Counter64
      MAX-ACCESS  read-only
      STATUS      current
      DESCRIPTION "The number of transactions that were rolled back since the server was started. "
      ::= { jtaPartitionRuntimeEntry 9  }
   
   
   jtaPartitionRuntimeTransactionRolledBackResourceTotalCount OBJECT-TYPE
      SYNTAX      Counter64
      MAX-ACCESS  read-only
      STATUS      current
      DESCRIPTION "The number of transactions that were rolled back due to a resource error. "
      ::= { jtaPartitionRuntimeEntry 10  }
   
   
   jtaPartitionRuntimeTransactionRolledBackSystemTotalCount OBJECT-TYPE
      SYNTAX      Counter64
      MAX-ACCESS  read-only
      STATUS      current
      DESCRIPTION "The number of transactions that were rolled back due to an internal system error. "
      ::= { jtaPartitionRuntimeEntry 11  }
   
   
   jtaPartitionRuntimeTransactionCommittedTotalCount OBJECT-TYPE
      SYNTAX      Counter64
      MAX-ACCESS  read-only
      STATUS      current
      DESCRIPTION "The total number of transactions committed since the server was started. "
      ::= { jtaPartitionRuntimeEntry 12  }
   
   
   jtaPartitionRuntimeSecondsActiveTotalCount OBJECT-TYPE
      SYNTAX      Counter64
      MAX-ACCESS  read-only
      STATUS      current
      DESCRIPTION "The total number of seconds that transactions were active for all committed transactions. "
      ::= { jtaPartitionRuntimeEntry 13  }
   
   
   jtaPartitionRuntimeType OBJECT-TYPE
      SYNTAX      OCTET STRING
      MAX-ACCESS  read-only
      STATUS      current
      DESCRIPTION "Returns the type of the MBean. "
      ::= { jtaPartitionRuntimeEntry 14  }
   
   
   jtaPartitionRuntimeTransactionLLRCommittedTotalCount OBJECT-TYPE
      SYNTAX      Counter64
      MAX-ACCESS  read-only
      STATUS      current
      DESCRIPTION "The total number of LLR transactions that were committed since the server was started. "
      ::= { jtaPartitionRuntimeEntry 15  }
   
   
   jtaPartitionRuntimeActiveTransactionsTotalCount OBJECT-TYPE
      SYNTAX      Integer32
      MAX-ACCESS  read-only
      STATUS      current
      DESCRIPTION "The number of active transactions on the server. "
      ::= { jtaPartitionRuntimeEntry 16  }
   
   
   jtaPartitionRuntimeRegisteredNonXAResourceNames OBJECT-TYPE
      SYNTAX      OCTET STRING
      MAX-ACCESS  read-only
      STATUS      current
      DESCRIPTION "An array of NonXA resource names that are registered with the transaction manager. "
      ::= { jtaPartitionRuntimeEntry 17  }
   
   
   jtaPartitionRuntimeRegisteredResourceNames OBJECT-TYPE
      SYNTAX      OCTET STRING
      MAX-ACCESS  read-only
      STATUS      current
      DESCRIPTION "An array of XA resource names that are registered with the transaction manager. "
      ::= { jtaPartitionRuntimeEntry 18  }
   
   
   jtaPartitionRuntimeTransactionAbandonedTotalCount OBJECT-TYPE
      SYNTAX      Counter64
      MAX-ACCESS  read-only
      STATUS      current
      DESCRIPTION "The total number of transactions that were abandoned since the server was started. "
      ::= { jtaPartitionRuntimeEntry 19  }
   
   
   jtaPartitionRuntimeTransactionRolledBackTimeoutTotalCount OBJECT-TYPE
      SYNTAX      Counter64
      MAX-ACCESS  read-only
      STATUS      current
      DESCRIPTION "The number of transactions that were rolled back due to a timeout expiration. "
      ::= { jtaPartitionRuntimeEntry 20  }
   
   
   jtaPartitionRuntimeTransactionNoResourcesCommittedTotalCount OBJECT-TYPE
      SYNTAX      Counter64
      MAX-ACCESS  read-only
      STATUS      current
      DESCRIPTION "The total number of transactions with no enlisted resources that were committed since the server was started. "
      ::= { jtaPartitionRuntimeEntry 21  }
   
   
   jtaPartitionRuntimeTransactionTotalCount OBJECT-TYPE
      SYNTAX      Counter64
      MAX-ACCESS  read-only
      STATUS      current
      DESCRIPTION "The total number of transactions processed. This total includes all committed, rolled back, and heuristic transaction completions since the server was started. "
      ::= { jtaPartitionRuntimeEntry 22  }
   
   
   jtaPartitionRuntimeTransactionHeuristicsTotalCount OBJECT-TYPE
      SYNTAX      Counter64
      MAX-ACCESS  read-only
      STATUS      current
      DESCRIPTION "The number of transactions that completed with a heuristic status since the server was started. "
      ::= { jtaPartitionRuntimeEntry 23  }
   
   
   jtaPartitionRuntimeTransactionTwoPhaseCommittedLoggedTotalCount OBJECT-TYPE
      SYNTAX      Counter64
      MAX-ACCESS  read-only
      STATUS      current
      DESCRIPTION "The total number of two phase commit transactions that were committed with TLog since the server was started. "
      ::= { jtaPartitionRuntimeEntry 24  }
   
   
   jaxRsExceptionMapperStatisticsRuntimeTable OBJECT-TYPE
      SYNTAX      SEQUENCE OF JaxRsExceptionMapperStatisticsRuntimeEntry
      MAX-ACCESS  not-accessible
      STATUS      current
      DESCRIPTION "Monitoring statistics of exception mapper executions. "
      ::= { wls 2320  }
      
   
   jaxRsExceptionMapperStatisticsRuntimeEntry OBJECT-TYPE
      SYNTAX      JaxRsExceptionMapperStatisticsRuntimeEntry
      MAX-ACCESS  not-accessible
      STATUS      current
      DESCRIPTION "Generated SNMP Table Entry."
      INDEX { jaxRsExceptionMapperStatisticsRuntimeIndex}
      ::= { jaxRsExceptionMapperStatisticsRuntimeTable 1 }
      
   JaxRsExceptionMapperStatisticsRuntimeEntry ::=
      SEQUENCE
      {
         jaxRsExceptionMapperStatisticsRuntimeIndex OCTET STRING,
         jaxRsExceptionMapperStatisticsRuntimeObjectName OCTET STRING,
         jaxRsExceptionMapperStatisticsRuntimeTotalMappings Counter64,
         jaxRsExceptionMapperStatisticsRuntimeSuccessfulMappings Counter64,
         jaxRsExceptionMapperStatisticsRuntimeName OCTET STRING,
         jaxRsExceptionMapperStatisticsRuntimeUnsuccessfulMappings Counter64,
         jaxRsExceptionMapperStatisticsRuntimeType OCTET STRING
      }
      
   
   jaxRsExceptionMapperStatisticsRuntimeIndex OBJECT-TYPE
      SYNTAX      OCTET STRING
      MAX-ACCESS  not-accessible
      STATUS      current
      DESCRIPTION "Index column"
      ::= { jaxRsExceptionMapperStatisticsRuntimeEntry 1  }
   
   
   jaxRsExceptionMapperStatisticsRuntimeObjectName OBJECT-TYPE
      SYNTAX      OCTET STRING
      MAX-ACCESS  read-only
      STATUS      current
      DESCRIPTION "ObjectName column"
      ::= { jaxRsExceptionMapperStatisticsRuntimeEntry 2  }
   
   
   jaxRsExceptionMapperStatisticsRuntimeTotalMappings OBJECT-TYPE
      SYNTAX      Counter64
      MAX-ACCESS  read-only
      STATUS      current
      DESCRIPTION "Get count of exception mappings that were performed on exceptions. "
      ::= { jaxRsExceptionMapperStatisticsRuntimeEntry 3  }
   
   
   jaxRsExceptionMapperStatisticsRuntimeSuccessfulMappings OBJECT-TYPE
      SYNTAX      Counter64
      MAX-ACCESS  read-only
      STATUS      current
      DESCRIPTION "Get count of all successful exception mappings. Successful exception mapping occurs when any exception mapper returns a valid response (even if response contains non-successful response status code). "
      ::= { jaxRsExceptionMapperStatisticsRuntimeEntry 4  }
   
   
   jaxRsExceptionMapperStatisticsRuntimeName OBJECT-TYPE
      SYNTAX      OCTET STRING
      MAX-ACCESS  read-only
      STATUS      current
      DESCRIPTION "The name of this configuration. WebLogic Server uses an MBean to implement and persist the configuration. "
      ::= { jaxRsExceptionMapperStatisticsRuntimeEntry 5  }
   
   
   jaxRsExceptionMapperStatisticsRuntimeUnsuccessfulMappings OBJECT-TYPE
      SYNTAX      Counter64
      MAX-ACCESS  read-only
      STATUS      current
      DESCRIPTION "Get count of all unsuccessful exception mappings. Unsuccessful exception mapping occurs when any exception mapping process does not produce a valid response. The reason can be that the exception mapper is not found, or is found but throws an exception. "
      ::= { jaxRsExceptionMapperStatisticsRuntimeEntry 6  }
   
   
   jaxRsExceptionMapperStatisticsRuntimeType OBJECT-TYPE
      SYNTAX      OCTET STRING
      MAX-ACCESS  read-only
      STATUS      current
      DESCRIPTION "Returns the type of the MBean. "
      ::= { jaxRsExceptionMapperStatisticsRuntimeEntry 7  }
   
   
   jaxRsExecutionStatisticsRuntimeTable OBJECT-TYPE
      SYNTAX      SEQUENCE OF JaxRsExecutionStatisticsRuntimeEntry
      MAX-ACCESS  not-accessible
      STATUS      current
      DESCRIPTION "Execution statistics such as min/max/avg time and request count/rate. "
      ::= { wls 2325  }
      
   
   jaxRsExecutionStatisticsRuntimeEntry OBJECT-TYPE
      SYNTAX      JaxRsExecutionStatisticsRuntimeEntry
      MAX-ACCESS  not-accessible
      STATUS      current
      DESCRIPTION "Generated SNMP Table Entry."
      INDEX { jaxRsExecutionStatisticsRuntimeIndex}
      ::= { jaxRsExecutionStatisticsRuntimeTable 1 }
      
   JaxRsExecutionStatisticsRuntimeEntry ::=
      SEQUENCE
      {
         jaxRsExecutionStatisticsRuntimeIndex OCTET STRING,
         jaxRsExecutionStatisticsRuntimeObjectName OCTET STRING,
         jaxRsExecutionStatisticsRuntimeMaxTimeLast1s Counter64,
         jaxRsExecutionStatisticsRuntimeMinTimeLast15m Counter64,
         jaxRsExecutionStatisticsRuntimeMaxTimeLast1m Counter64,
         jaxRsExecutionStatisticsRuntimeRequestCountTotal Counter64,
         jaxRsExecutionStatisticsRuntimeMinTimeLast1h Counter64,
         jaxRsExecutionStatisticsRuntimeMinTimeLast15s Counter64,
         jaxRsExecutionStatisticsRuntimeName OCTET STRING,
         jaxRsExecutionStatisticsRuntimeMinTimeLast1s Counter64,
         jaxRsExecutionStatisticsRuntimeRequestCountLast15s Counter64,
         jaxRsExecutionStatisticsRuntimeMaxTimeTotal Counter64,
         jaxRsExecutionStatisticsRuntimeMinTimeLast1m Counter64,
         jaxRsExecutionStatisticsRuntimeRequestRateLast15s OCTET STRING,
         jaxRsExecutionStatisticsRuntimeRequestRateLast15m OCTET STRING,
         jaxRsExecutionStatisticsRuntimeRequestCountLast15m Counter64,
         jaxRsExecutionStatisticsRuntimeRequestRateLast1m OCTET STRING,
         jaxRsExecutionStatisticsRuntimeRequestRateLast1s OCTET STRING,
         jaxRsExecutionStatisticsRuntimeRequestCountLast1h Counter64,
         jaxRsExecutionStatisticsRuntimeAvgTimeLast1h Counter64,
         jaxRsExecutionStatisticsRuntimeAvgTimeLast15s Counter64,
         jaxRsExecutionStatisticsRuntimeMaxTimeLast15s Counter64,
         jaxRsExecutionStatisticsRuntimeRequestRateLast1h OCTET STRING,
         jaxRsExecutionStatisticsRuntimeAvgTimeLast15m Counter64,
         jaxRsExecutionStatisticsRuntimeMinTimeTotal Counter64,
         jaxRsExecutionStatisticsRuntimeMaxTimeLast15m Counter64,
         jaxRsExecutionStatisticsRuntimeType OCTET STRING,
         jaxRsExecutionStatisticsRuntimeAvgTimeTotal Counter64,
         jaxRsExecutionStatisticsRuntimeMaxTimeLast1h Counter64,
         jaxRsExecutionStatisticsRuntimeRequestCountLast1s Counter64,
         jaxRsExecutionStatisticsRuntimeAvgTimeLast1m Counter64,
         jaxRsExecutionStatisticsRuntimeRequestRateTotal OCTET STRING,
         jaxRsExecutionStatisticsRuntimeRequestCountLast1m Counter64,
         jaxRsExecutionStatisticsRuntimeAvgTimeLast1s Counter64
      }
      
   
   jaxRsExecutionStatisticsRuntimeIndex OBJECT-TYPE
      SYNTAX      OCTET STRING
      MAX-ACCESS  not-accessible
      STATUS      current
      DESCRIPTION "Index column"
      ::= { jaxRsExecutionStatisticsRuntimeEntry 1  }
   
   
   jaxRsExecutionStatisticsRuntimeObjectName OBJECT-TYPE
      SYNTAX      OCTET STRING
      MAX-ACCESS  read-only
      STATUS      current
      DESCRIPTION "ObjectName column"
      ::= { jaxRsExecutionStatisticsRuntimeEntry 2  }
   
   
   jaxRsExecutionStatisticsRuntimeMaxTimeLast1s OBJECT-TYPE
      SYNTAX      Counter64
      MAX-ACCESS  read-only
      STATUS      current
      DESCRIPTION "Get maximum request processing time in milliseconds in the last 1s. "
      ::= { jaxRsExecutionStatisticsRuntimeEntry 3  }
   
   
   jaxRsExecutionStatisticsRuntimeMinTimeLast15m OBJECT-TYPE
      SYNTAX      Counter64
      MAX-ACCESS  read-only
      STATUS      current
      DESCRIPTION "Get minimum request processing time in milliseconds in the last 15m. "
      ::= { jaxRsExecutionStatisticsRuntimeEntry 4  }
   
   
   jaxRsExecutionStatisticsRuntimeMaxTimeLast1m OBJECT-TYPE
      SYNTAX      Counter64
      MAX-ACCESS  read-only
      STATUS      current
      DESCRIPTION "Get maximum request processing time in milliseconds in the last 1m. "
      ::= { jaxRsExecutionStatisticsRuntimeEntry 5  }
   
   
   jaxRsExecutionStatisticsRuntimeRequestCountTotal OBJECT-TYPE
      SYNTAX      Counter64
      MAX-ACCESS  read-only
      STATUS      current
      DESCRIPTION "Get request count for the whole lifetime of an application. "
      ::= { jaxRsExecutionStatisticsRuntimeEntry 6  }
   
   
   jaxRsExecutionStatisticsRuntimeMinTimeLast1h OBJECT-TYPE
      SYNTAX      Counter64
      MAX-ACCESS  read-only
      STATUS      current
      DESCRIPTION "Get minimum request processing time in milliseconds in the last 1h. "
      ::= { jaxRsExecutionStatisticsRuntimeEntry 7  }
   
   
   jaxRsExecutionStatisticsRuntimeMinTimeLast15s OBJECT-TYPE
      SYNTAX      Counter64
      MAX-ACCESS  read-only
      STATUS      current
      DESCRIPTION "Get minimum request processing time in milliseconds in the last 5m. "
      ::= { jaxRsExecutionStatisticsRuntimeEntry 8  }
   
   
   jaxRsExecutionStatisticsRuntimeName OBJECT-TYPE
      SYNTAX      OCTET STRING
      MAX-ACCESS  read-only
      STATUS      current
      DESCRIPTION "The name of this configuration. WebLogic Server uses an MBean to implement and persist the configuration. "
      ::= { jaxRsExecutionStatisticsRuntimeEntry 9  }
   
   
   jaxRsExecutionStatisticsRuntimeMinTimeLast1s OBJECT-TYPE
      SYNTAX      Counter64
      MAX-ACCESS  read-only
      STATUS      current
      DESCRIPTION "Get minimum request processing time in milliseconds in the last 1s. "
      ::= { jaxRsExecutionStatisticsRuntimeEntry 10  }
   
   
   jaxRsExecutionStatisticsRuntimeRequestCountLast15s OBJECT-TYPE
      SYNTAX      Counter64
      MAX-ACCESS  read-only
      STATUS      current
      DESCRIPTION "Get request count in the last 5m. "
      ::= { jaxRsExecutionStatisticsRuntimeEntry 11  }
   
   
   jaxRsExecutionStatisticsRuntimeMaxTimeTotal OBJECT-TYPE
      SYNTAX      Counter64
      MAX-ACCESS  read-only
      STATUS      current
      DESCRIPTION "Get maximum request processing time in milliseconds for the whole lifetime of an application. "
      ::= { jaxRsExecutionStatisticsRuntimeEntry 12  }
   
   
   jaxRsExecutionStatisticsRuntimeMinTimeLast1m OBJECT-TYPE
      SYNTAX      Counter64
      MAX-ACCESS  read-only
      STATUS      current
      DESCRIPTION "Get minimum request processing time in milliseconds in the last 1m. "
      ::= { jaxRsExecutionStatisticsRuntimeEntry 13  }
   
   
   jaxRsExecutionStatisticsRuntimeRequestRateLast15s OBJECT-TYPE
      SYNTAX      OCTET STRING
      MAX-ACCESS  read-only
      STATUS      current
      DESCRIPTION "Get average request rate per second in the last 5m. "
      ::= { jaxRsExecutionStatisticsRuntimeEntry 14  }
   
   
   jaxRsExecutionStatisticsRuntimeRequestRateLast15m OBJECT-TYPE
      SYNTAX      OCTET STRING
      MAX-ACCESS  read-only
      STATUS      current
      DESCRIPTION "Get average request rate per second in the last 15m. "
      ::= { jaxRsExecutionStatisticsRuntimeEntry 15  }
   
   
   jaxRsExecutionStatisticsRuntimeRequestCountLast15m OBJECT-TYPE
      SYNTAX      Counter64
      MAX-ACCESS  read-only
      STATUS      current
      DESCRIPTION "Get request count in the last 15m. "
      ::= { jaxRsExecutionStatisticsRuntimeEntry 16  }
   
   
   jaxRsExecutionStatisticsRuntimeRequestRateLast1m OBJECT-TYPE
      SYNTAX      OCTET STRING
      MAX-ACCESS  read-only
      STATUS      current
      DESCRIPTION "Get average request rate per second in the last 1m. "
      ::= { jaxRsExecutionStatisticsRuntimeEntry 17  }
   
   
   jaxRsExecutionStatisticsRuntimeRequestRateLast1s OBJECT-TYPE
      SYNTAX      OCTET STRING
      MAX-ACCESS  read-only
      STATUS      current
      DESCRIPTION "Get average request rate per second in the last 1s. "
      ::= { jaxRsExecutionStatisticsRuntimeEntry 18  }
   
   
   jaxRsExecutionStatisticsRuntimeRequestCountLast1h OBJECT-TYPE
      SYNTAX      Counter64
      MAX-ACCESS  read-only
      STATUS      current
      DESCRIPTION "Get request count in the last 1h. "
      ::= { jaxRsExecutionStatisticsRuntimeEntry 19  }
   
   
   jaxRsExecutionStatisticsRuntimeAvgTimeLast1h OBJECT-TYPE
      SYNTAX      Counter64
      MAX-ACCESS  read-only
      STATUS      current
      DESCRIPTION "Get average request processing time in milliseconds in the last 1h. "
      ::= { jaxRsExecutionStatisticsRuntimeEntry 20  }
   
   
   jaxRsExecutionStatisticsRuntimeAvgTimeLast15s OBJECT-TYPE
      SYNTAX      Counter64
      MAX-ACCESS  read-only
      STATUS      current
      DESCRIPTION "Get average request processing time in milliseconds in the last 5m. "
      ::= { jaxRsExecutionStatisticsRuntimeEntry 21  }
   
   
   jaxRsExecutionStatisticsRuntimeMaxTimeLast15s OBJECT-TYPE
      SYNTAX      Counter64
      MAX-ACCESS  read-only
      STATUS      current
      DESCRIPTION "Get maximum request processing time in milliseconds in the last 5m. "
      ::= { jaxRsExecutionStatisticsRuntimeEntry 22  }
   
   
   jaxRsExecutionStatisticsRuntimeRequestRateLast1h OBJECT-TYPE
      SYNTAX      OCTET STRING
      MAX-ACCESS  read-only
      STATUS      current
      DESCRIPTION "Get average request rate per second in the last 1h. "
      ::= { jaxRsExecutionStatisticsRuntimeEntry 23  }
   
   
   jaxRsExecutionStatisticsRuntimeAvgTimeLast15m OBJECT-TYPE
      SYNTAX      Counter64
      MAX-ACCESS  read-only
      STATUS      current
      DESCRIPTION "Get average request processing time in milliseconds in the last 15m. "
      ::= { jaxRsExecutionStatisticsRuntimeEntry 24  }
   
   
   jaxRsExecutionStatisticsRuntimeMinTimeTotal OBJECT-TYPE
      SYNTAX      Counter64
      MAX-ACCESS  read-only
      STATUS      current
      DESCRIPTION "Get minimum request processing time in milliseconds for the whole lifetime of an application. "
      ::= { jaxRsExecutionStatisticsRuntimeEntry 25  }
   
   
   jaxRsExecutionStatisticsRuntimeMaxTimeLast15m OBJECT-TYPE
      SYNTAX      Counter64
      MAX-ACCESS  read-only
      STATUS      current
      DESCRIPTION "Get maximum request processing time in milliseconds in the last 15m. "
      ::= { jaxRsExecutionStatisticsRuntimeEntry 26  }
   
   
   jaxRsExecutionStatisticsRuntimeType OBJECT-TYPE
      SYNTAX      OCTET STRING
      MAX-ACCESS  read-only
      STATUS      current
      DESCRIPTION "Returns the type of the MBean. "
      ::= { jaxRsExecutionStatisticsRuntimeEntry 27  }
   
   
   jaxRsExecutionStatisticsRuntimeAvgTimeTotal OBJECT-TYPE
      SYNTAX      Counter64
      MAX-ACCESS  read-only
      STATUS      current
      DESCRIPTION "Get average request processing time in milliseconds for the whole lifetime of an application. "
      ::= { jaxRsExecutionStatisticsRuntimeEntry 28  }
   
   
   jaxRsExecutionStatisticsRuntimeMaxTimeLast1h OBJECT-TYPE
      SYNTAX      Counter64
      MAX-ACCESS  read-only
      STATUS      current
      DESCRIPTION "Get maximum request processing time in milliseconds in the last 1h. "
      ::= { jaxRsExecutionStatisticsRuntimeEntry 29  }
   
   
   jaxRsExecutionStatisticsRuntimeRequestCountLast1s OBJECT-TYPE
      SYNTAX      Counter64
      MAX-ACCESS  read-only
      STATUS      current
      DESCRIPTION "Get request count in the last 1s. "
      ::= { jaxRsExecutionStatisticsRuntimeEntry 30  }
   
   
   jaxRsExecutionStatisticsRuntimeAvgTimeLast1m OBJECT-TYPE
      SYNTAX      Counter64
      MAX-ACCESS  read-only
      STATUS      current
      DESCRIPTION "Get average request processing time in milliseconds in the last 1m. "
      ::= { jaxRsExecutionStatisticsRuntimeEntry 31  }
   
   
   jaxRsExecutionStatisticsRuntimeRequestRateTotal OBJECT-TYPE
      SYNTAX      OCTET STRING
      MAX-ACCESS  read-only
      STATUS      current
      DESCRIPTION "Get average request rate per second for the whole lifetime of an application. "
      ::= { jaxRsExecutionStatisticsRuntimeEntry 32  }
   
   
   jaxRsExecutionStatisticsRuntimeRequestCountLast1m OBJECT-TYPE
      SYNTAX      Counter64
      MAX-ACCESS  read-only
      STATUS      current
      DESCRIPTION "Get request count in the last 1m. "
      ::= { jaxRsExecutionStatisticsRuntimeEntry 33  }
   
   
   jaxRsExecutionStatisticsRuntimeAvgTimeLast1s OBJECT-TYPE
      SYNTAX      Counter64
      MAX-ACCESS  read-only
      STATUS      current
      DESCRIPTION "Get average request processing time in milliseconds in the last 1s. "
      ::= { jaxRsExecutionStatisticsRuntimeEntry 34  }
   
   
   jaxRsResponseStatisticsRuntimeTable OBJECT-TYPE
      SYNTAX      SEQUENCE OF JaxRsResponseStatisticsRuntimeEntry
      MAX-ACCESS  not-accessible
      STATUS      current
      DESCRIPTION "Monitoring statistics of responses produced by application. "
      ::= { wls 2330  }
      
   
   jaxRsResponseStatisticsRuntimeEntry OBJECT-TYPE
      SYNTAX      JaxRsResponseStatisticsRuntimeEntry
      MAX-ACCESS  not-accessible
      STATUS      current
      DESCRIPTION "Generated SNMP Table Entry."
      INDEX { jaxRsResponseStatisticsRuntimeIndex}
      ::= { jaxRsResponseStatisticsRuntimeTable 1 }
      
   JaxRsResponseStatisticsRuntimeEntry ::=
      SEQUENCE
      {
         jaxRsResponseStatisticsRuntimeIndex OCTET STRING,
         jaxRsResponseStatisticsRuntimeObjectName OCTET STRING,
         jaxRsResponseStatisticsRuntimeName OCTET STRING,
         jaxRsResponseStatisticsRuntimeType OCTET STRING,
         jaxRsResponseStatisticsRuntimeLastResponseCode Integer32
      }
      
   
   jaxRsResponseStatisticsRuntimeIndex OBJECT-TYPE
      SYNTAX      OCTET STRING
      MAX-ACCESS  not-accessible
      STATUS      current
      DESCRIPTION "Index column"
      ::= { jaxRsResponseStatisticsRuntimeEntry 1  }
   
   
   jaxRsResponseStatisticsRuntimeObjectName OBJECT-TYPE
      SYNTAX      OCTET STRING
      MAX-ACCESS  read-only
      STATUS      current
      DESCRIPTION "ObjectName column"
      ::= { jaxRsResponseStatisticsRuntimeEntry 2  }
   
   
   jaxRsResponseStatisticsRuntimeName OBJECT-TYPE
      SYNTAX      OCTET STRING
      MAX-ACCESS  read-only
      STATUS      current
      DESCRIPTION "The name of this configuration. WebLogic Server uses an MBean to implement and persist the configuration. "
      ::= { jaxRsResponseStatisticsRuntimeEntry 3  }
   
   
   jaxRsResponseStatisticsRuntimeType OBJECT-TYPE
      SYNTAX      OCTET STRING
      MAX-ACCESS  read-only
      STATUS      current
      DESCRIPTION "Returns the type of the MBean. "
      ::= { jaxRsResponseStatisticsRuntimeEntry 4  }
   
   
   jaxRsResponseStatisticsRuntimeLastResponseCode OBJECT-TYPE
      SYNTAX      Integer32
      MAX-ACCESS  read-only
      STATUS      current
      DESCRIPTION "Returns the HTTP response code of the last response written by the application. "
      ::= { jaxRsResponseStatisticsRuntimeEntry 5  }
   
   
   managedScheduledExecutorServiceRuntimeTable OBJECT-TYPE
      SYNTAX      SEQUENCE OF ManagedScheduledExecutorServiceRuntimeEntry
      MAX-ACCESS  not-accessible
      STATUS      current
      DESCRIPTION "ManagedScheduledExecutorService Runtime information. It can be the information of a partition level MSES, an application level MSES or a regular JSR236 MSES. "
      ::= { wls 2335  }
      
   
   managedScheduledExecutorServiceRuntimeEntry OBJECT-TYPE
      SYNTAX      ManagedScheduledExecutorServiceRuntimeEntry
      MAX-ACCESS  not-accessible
      STATUS      current
      DESCRIPTION "Generated SNMP Table Entry."
      INDEX { managedScheduledExecutorServiceRuntimeIndex}
      ::= { managedScheduledExecutorServiceRuntimeTable 1 }
      
   ManagedScheduledExecutorServiceRuntimeEntry ::=
      SEQUENCE
      {
         managedScheduledExecutorServiceRuntimeIndex OCTET STRING,
         managedScheduledExecutorServiceRuntimeObjectName OCTET STRING,
         managedScheduledExecutorServiceRuntimeFailedRequests Counter64,
         managedScheduledExecutorServiceRuntimeApplicationName OCTET STRING,
         managedScheduledExecutorServiceRuntimeModuleName OCTET STRING,
         managedScheduledExecutorServiceRuntimeSubmitedShortRunningRequests Counter64,
         managedScheduledExecutorServiceRuntimeRejectedLongRunningRequests Counter64,
         managedScheduledExecutorServiceRuntimeName OCTET STRING,
         managedScheduledExecutorServiceRuntimePartitionName OCTET STRING,
         managedScheduledExecutorServiceRuntimeRejectedShortRunningRequests Counter64,
         managedScheduledExecutorServiceRuntimeType OCTET STRING,
         managedScheduledExecutorServiceRuntimeCompletedShortRunningRequests Counter64,
         managedScheduledExecutorServiceRuntimeRunningLongRunningRequests Counter64,
         managedScheduledExecutorServiceRuntimeCompletedLongRunningRequests Counter64,
         managedScheduledExecutorServiceRuntimeSubmittedLongRunningRequests Counter64
      }
      
   
   managedScheduledExecutorServiceRuntimeIndex OBJECT-TYPE
      SYNTAX      OCTET STRING
      MAX-ACCESS  not-accessible
      STATUS      current
      DESCRIPTION "Index column"
      ::= { managedScheduledExecutorServiceRuntimeEntry 1  }
   
   
   managedScheduledExecutorServiceRuntimeObjectName OBJECT-TYPE
      SYNTAX      OCTET STRING
      MAX-ACCESS  read-only
      STATUS      current
      DESCRIPTION "ObjectName column"
      ::= { managedScheduledExecutorServiceRuntimeEntry 2  }
   
   
   managedScheduledExecutorServiceRuntimeFailedRequests OBJECT-TYPE
      SYNTAX      Counter64
      MAX-ACCESS  read-only
      STATUS      current
      DESCRIPTION "Total number of tasks which terminated abnormally by throwing exception, including both long and short term tasks. "
      ::= { managedScheduledExecutorServiceRuntimeEntry 3  }
   
   
   managedScheduledExecutorServiceRuntimeApplicationName OBJECT-TYPE
      SYNTAX      OCTET STRING
      MAX-ACCESS  read-only
      STATUS      current
      DESCRIPTION " Get the name of the application this ManagedExecutor is associated with  "
      ::= { managedScheduledExecutorServiceRuntimeEntry 4  }
   
   
   managedScheduledExecutorServiceRuntimeModuleName OBJECT-TYPE
      SYNTAX      OCTET STRING
      MAX-ACCESS  read-only
      STATUS      current
      DESCRIPTION " Get the name of the module this ManagedExecutor is associated with  "
      ::= { managedScheduledExecutorServiceRuntimeEntry 5  }
   
   
   managedScheduledExecutorServiceRuntimeSubmitedShortRunningRequests OBJECT-TYPE
      SYNTAX      Counter64
      MAX-ACCESS  read-only
      STATUS      current
      DESCRIPTION "Total number of submitted short running tasks"
      ::= { managedScheduledExecutorServiceRuntimeEntry 6  }
   
   
   managedScheduledExecutorServiceRuntimeRejectedLongRunningRequests OBJECT-TYPE
      SYNTAX      Counter64
      MAX-ACCESS  read-only
      STATUS      current
      DESCRIPTION "Total number of long running tasks rejected by max-concurrent-long-running-requests"
      ::= { managedScheduledExecutorServiceRuntimeEntry 7  }
   
   
   managedScheduledExecutorServiceRuntimeName OBJECT-TYPE
      SYNTAX      OCTET STRING
      MAX-ACCESS  read-only
      STATUS      current
      DESCRIPTION "The name of this configuration. WebLogic Server uses an MBean to implement and persist the configuration. "
      ::= { managedScheduledExecutorServiceRuntimeEntry 8  }
   
   
   managedScheduledExecutorServiceRuntimePartitionName OBJECT-TYPE
      SYNTAX      OCTET STRING
      MAX-ACCESS  read-only
      STATUS      current
      DESCRIPTION " Get the name of the partition this ManagedExecutor is associated with  "
      ::= { managedScheduledExecutorServiceRuntimeEntry 9  }
   
   
   managedScheduledExecutorServiceRuntimeRejectedShortRunningRequests OBJECT-TYPE
      SYNTAX      Counter64
      MAX-ACCESS  read-only
      STATUS      current
      DESCRIPTION "Total number of short running tasks rejected by workmanager overload policy"
      ::= { managedScheduledExecutorServiceRuntimeEntry 10  }
   
   
   managedScheduledExecutorServiceRuntimeType OBJECT-TYPE
      SYNTAX      OCTET STRING
      MAX-ACCESS  read-only
      STATUS      current
      DESCRIPTION "Returns the type of the MBean. "
      ::= { managedScheduledExecutorServiceRuntimeEntry 11  }
   
   
   managedScheduledExecutorServiceRuntimeCompletedShortRunningRequests OBJECT-TYPE
      SYNTAX      Counter64
      MAX-ACCESS  read-only
      STATUS      current
      DESCRIPTION "Total number of short running tasks which is successfully completed."
      ::= { managedScheduledExecutorServiceRuntimeEntry 12  }
   
   
   managedScheduledExecutorServiceRuntimeRunningLongRunningRequests OBJECT-TYPE
      SYNTAX      Counter64
      MAX-ACCESS  read-only
      STATUS      current
      DESCRIPTION "Total number of long running tasks which is currently running. "
      ::= { managedScheduledExecutorServiceRuntimeEntry 13  }
   
   
   managedScheduledExecutorServiceRuntimeCompletedLongRunningRequests OBJECT-TYPE
      SYNTAX      Counter64
      MAX-ACCESS  read-only
      STATUS      current
      DESCRIPTION "Total number of long running tasks which is successfully completed."
      ::= { managedScheduledExecutorServiceRuntimeEntry 14  }
   
   
   managedScheduledExecutorServiceRuntimeSubmittedLongRunningRequests OBJECT-TYPE
      SYNTAX      Counter64
      MAX-ACCESS  read-only
      STATUS      current
      DESCRIPTION "Total number of submitted long running tasks"
      ::= { managedScheduledExecutorServiceRuntimeEntry 15  }
   
   
   managedThreadFactoryRuntimeTable OBJECT-TYPE
      SYNTAX      SEQUENCE OF ManagedThreadFactoryRuntimeEntry
      MAX-ACCESS  not-accessible
      STATUS      current
      DESCRIPTION "ManagedThreadFactory Runtime information. It can be the information of a partition level MTF, an application level MTF or a regular JSR236 MTF. "
      ::= { wls 2340  }
      
   
   managedThreadFactoryRuntimeEntry OBJECT-TYPE
      SYNTAX      ManagedThreadFactoryRuntimeEntry
      MAX-ACCESS  not-accessible
      STATUS      current
      DESCRIPTION "Generated SNMP Table Entry."
      INDEX { managedThreadFactoryRuntimeIndex}
      ::= { managedThreadFactoryRuntimeTable 1 }
      
   ManagedThreadFactoryRuntimeEntry ::=
      SEQUENCE
      {
         managedThreadFactoryRuntimeIndex OCTET STRING,
         managedThreadFactoryRuntimeObjectName OCTET STRING,
         managedThreadFactoryRuntimeApplicationName OCTET STRING,
         managedThreadFactoryRuntimeModuleName OCTET STRING,
         managedThreadFactoryRuntimeName OCTET STRING,
         managedThreadFactoryRuntimePartitionName OCTET STRING,
         managedThreadFactoryRuntimeRunningThreadsCount Integer32,
         managedThreadFactoryRuntimeType OCTET STRING,
         managedThreadFactoryRuntimeCompletedThreadsCount Counter64,
         managedThreadFactoryRuntimeRejectedNewThreadRequests Counter64
      }
      
   
   managedThreadFactoryRuntimeIndex OBJECT-TYPE
      SYNTAX      OCTET STRING
      MAX-ACCESS  not-accessible
      STATUS      current
      DESCRIPTION "Index column"
      ::= { managedThreadFactoryRuntimeEntry 1  }
   
   
   managedThreadFactoryRuntimeObjectName OBJECT-TYPE
      SYNTAX      OCTET STRING
      MAX-ACCESS  read-only
      STATUS      current
      DESCRIPTION "ObjectName column"
      ::= { managedThreadFactoryRuntimeEntry 2  }
   
   
   managedThreadFactoryRuntimeApplicationName OBJECT-TYPE
      SYNTAX      OCTET STRING
      MAX-ACCESS  read-only
      STATUS      current
      DESCRIPTION "Get the name of the application this ManagedThreadFactory is associated with "
      ::= { managedThreadFactoryRuntimeEntry 3  }
   
   
   managedThreadFactoryRuntimeModuleName OBJECT-TYPE
      SYNTAX      OCTET STRING
      MAX-ACCESS  read-only
      STATUS      current
      DESCRIPTION "Get the name of the module this ManagedThreadFactory is associated with "
      ::= { managedThreadFactoryRuntimeEntry 4  }
   
   
   managedThreadFactoryRuntimeName OBJECT-TYPE
      SYNTAX      OCTET STRING
      MAX-ACCESS  read-only
      STATUS      current
      DESCRIPTION "The name of this configuration. WebLogic Server uses an MBean to implement and persist the configuration. "
      ::= { managedThreadFactoryRuntimeEntry 5  }
   
   
   managedThreadFactoryRuntimePartitionName OBJECT-TYPE
      SYNTAX      OCTET STRING
      MAX-ACCESS  read-only
      STATUS      current
      DESCRIPTION "Get the name of the partition this ManagedThreadFactory is associated with "
      ::= { managedThreadFactoryRuntimeEntry 6  }
   
   
   managedThreadFactoryRuntimeRunningThreadsCount OBJECT-TYPE
      SYNTAX      Integer32
      MAX-ACCESS  read-only
      STATUS      current
      DESCRIPTION "The number of running threads. "
      ::= { managedThreadFactoryRuntimeEntry 7  }
   
   
   managedThreadFactoryRuntimeType OBJECT-TYPE
      SYNTAX      OCTET STRING
      MAX-ACCESS  read-only
      STATUS      current
      DESCRIPTION "Returns the type of the MBean. "
      ::= { managedThreadFactoryRuntimeEntry 8  }
   
   
   managedThreadFactoryRuntimeCompletedThreadsCount OBJECT-TYPE
      SYNTAX      Counter64
      MAX-ACCESS  read-only
      STATUS      current
      DESCRIPTION "The number of completed threads. "
      ::= { managedThreadFactoryRuntimeEntry 9  }
   
   
   managedThreadFactoryRuntimeRejectedNewThreadRequests OBJECT-TYPE
      SYNTAX      Counter64
      MAX-ACCESS  read-only
      STATUS      current
      DESCRIPTION "The number of newThread method invocations that have been rejected because the limit of running threads was exceeded.  "
      ::= { managedThreadFactoryRuntimeEntry 10  }
   
   
   nodeManagerRuntimeTable OBJECT-TYPE
      SYNTAX      SEQUENCE OF NodeManagerRuntimeEntry
      MAX-ACCESS  not-accessible
      STATUS      current
      DESCRIPTION "Provides methods for retrieving runtime information about a server instance and for transitioning a server from one state to another. "
      ::= { wls 2345  }
      
   
   nodeManagerRuntimeEntry OBJECT-TYPE
      SYNTAX      NodeManagerRuntimeEntry
      MAX-ACCESS  not-accessible
      STATUS      current
      DESCRIPTION "Generated SNMP Table Entry."
      INDEX { nodeManagerRuntimeIndex}
      ::= { nodeManagerRuntimeTable 1 }
      
   NodeManagerRuntimeEntry ::=
      SEQUENCE
      {
         nodeManagerRuntimeIndex OCTET STRING,
         nodeManagerRuntimeObjectName OCTET STRING,
         nodeManagerRuntimeName OCTET STRING,
         nodeManagerRuntimeType OCTET STRING,
         nodeManagerRuntimeReachable OCTET STRING
      }
      
   
   nodeManagerRuntimeIndex OBJECT-TYPE
      SYNTAX      OCTET STRING
      MAX-ACCESS  not-accessible
      STATUS      current
      DESCRIPTION "Index column"
      ::= { nodeManagerRuntimeEntry 1  }
   
   
   nodeManagerRuntimeObjectName OBJECT-TYPE
      SYNTAX      OCTET STRING
      MAX-ACCESS  read-only
      STATUS      current
      DESCRIPTION "ObjectName column"
      ::= { nodeManagerRuntimeEntry 2  }
   
   
   nodeManagerRuntimeName OBJECT-TYPE
      SYNTAX      OCTET STRING
      MAX-ACCESS  read-only
      STATUS      current
      DESCRIPTION "The name of this configuration. WebLogic Server uses an MBean to implement and persist the configuration. "
      ::= { nodeManagerRuntimeEntry 3  }
   
   
   nodeManagerRuntimeType OBJECT-TYPE
      SYNTAX      OCTET STRING
      MAX-ACCESS  read-only
      STATUS      current
      DESCRIPTION "Returns the type of the MBean. "
      ::= { nodeManagerRuntimeEntry 4  }
   
   
   nodeManagerRuntimeReachable OBJECT-TYPE
      SYNTAX      OCTET STRING
      MAX-ACCESS  read-only
      STATUS      current
      DESCRIPTION " "
      ::= { nodeManagerRuntimeEntry 5  }
   
   
   partitionFairShareRuntimeTable OBJECT-TYPE
      SYNTAX      SEQUENCE OF PartitionFairShareRuntimeEntry
      MAX-ACCESS  not-accessible
      STATUS      current
      DESCRIPTION "Monitoring information for PartitionFairShare "
      ::= { wls 2350  }
      
   
   partitionFairShareRuntimeEntry OBJECT-TYPE
      SYNTAX      PartitionFairShareRuntimeEntry
      MAX-ACCESS  not-accessible
      STATUS      current
      DESCRIPTION "Generated SNMP Table Entry."
      INDEX { partitionFairShareRuntimeIndex}
      ::= { partitionFairShareRuntimeTable 1 }
      
   PartitionFairShareRuntimeEntry ::=
      SEQUENCE
      {
         partitionFairShareRuntimeIndex OCTET STRING,
         partitionFairShareRuntimeObjectName OCTET STRING,
         partitionFairShareRuntimeConfiguredFairShare Integer32,
         partitionFairShareRuntimeThreadUse Counter64,
         partitionFairShareRuntimeName OCTET STRING,
         partitionFairShareRuntimeType OCTET STRING,
         partitionFairShareRuntimeFairShare Integer32,
         partitionFairShareRuntimePartitionAdjuster OCTET STRING
      }
      
   
   partitionFairShareRuntimeIndex OBJECT-TYPE
      SYNTAX      OCTET STRING
      MAX-ACCESS  not-accessible
      STATUS      current
      DESCRIPTION "Index column"
      ::= { partitionFairShareRuntimeEntry 1  }
   
   
   partitionFairShareRuntimeObjectName OBJECT-TYPE
      SYNTAX      OCTET STRING
      MAX-ACCESS  read-only
      STATUS      current
      DESCRIPTION "ObjectName column"
      ::= { partitionFairShareRuntimeEntry 2  }
   
   
   partitionFairShareRuntimeConfiguredFairShare OBJECT-TYPE
      SYNTAX      Integer32
      MAX-ACCESS  read-only
      STATUS      current
      DESCRIPTION "The configured fair share value. "
      ::= { partitionFairShareRuntimeEntry 3  }
   
   
   partitionFairShareRuntimeThreadUse OBJECT-TYPE
      SYNTAX      Counter64
      MAX-ACCESS  read-only
      STATUS      current
      DESCRIPTION "Total amount of thread use time in milliseconds used by the partition during the past period. "
      ::= { partitionFairShareRuntimeEntry 4  }
   
   
   partitionFairShareRuntimeName OBJECT-TYPE
      SYNTAX      OCTET STRING
      MAX-ACCESS  read-only
      STATUS      current
      DESCRIPTION "The name of this configuration. WebLogic Server uses an MBean to implement and persist the configuration. "
      ::= { partitionFairShareRuntimeEntry 5  }
   
   
   partitionFairShareRuntimeType OBJECT-TYPE
      SYNTAX      OCTET STRING
      MAX-ACCESS  read-only
      STATUS      current
      DESCRIPTION "Returns the type of the MBean. "
      ::= { partitionFairShareRuntimeEntry 6  }
   
   
   partitionFairShareRuntimeFairShare OBJECT-TYPE
      SYNTAX      Integer32
      MAX-ACCESS  read-only
      STATUS      current
      DESCRIPTION "The current fair share value. This could be different from the configured value as Resource Consumption Management could dynamically adjust the actual fair share value based on configured RCM policies and actual thread usage by the partition "
      ::= { partitionFairShareRuntimeEntry 7  }
   
   
   partitionFairShareRuntimePartitionAdjuster OBJECT-TYPE
      SYNTAX      OCTET STRING
      MAX-ACCESS  read-only
      STATUS      current
      DESCRIPTION "The multiplier to be used to adjust the priority of requests from the partition in the request queue. "
      ::= { partitionFairShareRuntimeEntry 8  }
   
   
   partitionLifeCycleRuntimeTable OBJECT-TYPE
      SYNTAX      SEQUENCE OF PartitionLifeCycleRuntimeEntry
      MAX-ACCESS  not-accessible
      STATUS      current
      DESCRIPTION "Provides methods that transition partitions from one state to another. This class is instantiated once for each partition but only on the Administration Server. Even so, you can use a partition's instance to change the state of the partition on Managed Servers as well as on the Administration Server.  Detecting when Operations Complete  Methods representing operations on partitions return a {@link PartitionLifeCycleTaskRuntimeMBean} object. The caller should monitor the returned instance, invoking its {@link PartitionLifeCycleTaskRuntimeMBean#isRunning()} method to detect when the operation has completed. In particular, the caller should not rely on the value returned from {@link #getState()} to indicate when an operation on a partition that is targeted to multiple servers has finished. That value will be accurate as described in detail on {@link #getState()} but can change before the operation has finished.  Desired States The system tracks the desired state for each partition, which defaults to the state SHUTDOWN and substate HALTED. Whenever a lifecycle operation method is called the system not only performs the requested action on the partition but also records the resulting state as the new desired state for the partition. The system uses the desired state for a partition to bring the partition to the correct state during server restart. It can also be used when the {@link #getState()} method computes the overall state for the partition. "
      ::= { wls 2355  }
      
   
   partitionLifeCycleRuntimeEntry OBJECT-TYPE
      SYNTAX      PartitionLifeCycleRuntimeEntry
      MAX-ACCESS  not-accessible
      STATUS      current
      DESCRIPTION "Generated SNMP Table Entry."
      INDEX { partitionLifeCycleRuntimeIndex}
      ::= { partitionLifeCycleRuntimeTable 1 }
      
   PartitionLifeCycleRuntimeEntry ::=
      SEQUENCE
      {
         partitionLifeCycleRuntimeIndex OCTET STRING,
         partitionLifeCycleRuntimeObjectName OCTET STRING,
         partitionLifeCycleRuntimeName OCTET STRING,
         partitionLifeCycleRuntimeType OCTET STRING,
         partitionLifeCycleRuntimeState OCTET STRING,
         partitionLifeCycleRuntimeSubState OCTET STRING
      }
      
   
   partitionLifeCycleRuntimeIndex OBJECT-TYPE
      SYNTAX      OCTET STRING
      MAX-ACCESS  not-accessible
      STATUS      current
      DESCRIPTION "Index column"
      ::= { partitionLifeCycleRuntimeEntry 1  }
   
   
   partitionLifeCycleRuntimeObjectName OBJECT-TYPE
      SYNTAX      OCTET STRING
      MAX-ACCESS  read-only
      STATUS      current
      DESCRIPTION "ObjectName column"
      ::= { partitionLifeCycleRuntimeEntry 2  }
   
   
   partitionLifeCycleRuntimeName OBJECT-TYPE
      SYNTAX      OCTET STRING
      MAX-ACCESS  read-only
      STATUS      current
      DESCRIPTION "The name of this configuration. WebLogic Server uses an MBean to implement and persist the configuration. "
      ::= { partitionLifeCycleRuntimeEntry 3  }
   
   
   partitionLifeCycleRuntimeType OBJECT-TYPE
      SYNTAX      OCTET STRING
      MAX-ACCESS  read-only
      STATUS      current
      DESCRIPTION "Returns the type of the MBean. "
      ::= { partitionLifeCycleRuntimeEntry 4  }
   
   
   partitionLifeCycleRuntimeState OBJECT-TYPE
      SYNTAX      OCTET STRING
      MAX-ACCESS  read-only
      STATUS      current
      DESCRIPTION "The current overall state of the partition. The value returned is the highest state for the partition on all servers where it is targeted. As a result, the overall partition state can change (for example, to RUNNING) as soon as the operation (such as start) has finished on one server, even while the operation is still in progress elsewhere. If the partition is not currently targeted to any running server then its reported state is the desired state indicated by the most recent partition life cycle operation on the partition. "
      ::= { partitionLifeCycleRuntimeEntry 5  }
   
   
   partitionLifeCycleRuntimeSubState OBJECT-TYPE
      SYNTAX      OCTET STRING
      MAX-ACCESS  read-only
      STATUS      current
      DESCRIPTION "The current substate of the partition. It is mostly useful for knowing whether the partition is completely shutdown and the administrative resource groups are not running, in which case this method returns HALTED, or if the partition is in the SHUTDOWN.BOOTED state and the administrative resource groups are running, in which case this method returns BOOTED. "
      ::= { partitionLifeCycleRuntimeEntry 6  }
   
   
   partitionLifeCycleTaskRuntimeTable OBJECT-TYPE
      SYNTAX      SEQUENCE OF PartitionLifeCycleTaskRuntimeEntry
      MAX-ACCESS  not-accessible
      STATUS      current
      DESCRIPTION "Exposes information about a long-running task related to the partition life cycle. "
      ::= { wls 2360  }
      
   
   partitionLifeCycleTaskRuntimeEntry OBJECT-TYPE
      SYNTAX      PartitionLifeCycleTaskRuntimeEntry
      MAX-ACCESS  not-accessible
      STATUS      current
      DESCRIPTION "Generated SNMP Table Entry."
      INDEX { partitionLifeCycleTaskRuntimeIndex}
      ::= { partitionLifeCycleTaskRuntimeTable 1 }
      
   PartitionLifeCycleTaskRuntimeEntry ::=
      SEQUENCE
      {
         partitionLifeCycleTaskRuntimeIndex OCTET STRING,
         partitionLifeCycleTaskRuntimeObjectName OCTET STRING,
         partitionLifeCycleTaskRuntimeStatus OCTET STRING,
         partitionLifeCycleTaskRuntimeProgress OCTET STRING,
         partitionLifeCycleTaskRuntimeDescription OCTET STRING,
         partitionLifeCycleTaskRuntimeEndTime Counter64,
         partitionLifeCycleTaskRuntimeBeginTime Counter64,
         partitionLifeCycleTaskRuntimeOperation OCTET STRING,
         partitionLifeCycleTaskRuntimeName OCTET STRING,
         partitionLifeCycleTaskRuntimePartitionName OCTET STRING,
         partitionLifeCycleTaskRuntimeType OCTET STRING,
         partitionLifeCycleTaskRuntimeSystemTask OCTET STRING,
         partitionLifeCycleTaskRuntimeRunning OCTET STRING,
         partitionLifeCycleTaskRuntimeServerName OCTET STRING
      }
      
   
   partitionLifeCycleTaskRuntimeIndex OBJECT-TYPE
      SYNTAX      OCTET STRING
      MAX-ACCESS  not-accessible
      STATUS      current
      DESCRIPTION "Index column"
      ::= { partitionLifeCycleTaskRuntimeEntry 1  }
   
   
   partitionLifeCycleTaskRuntimeObjectName OBJECT-TYPE
      SYNTAX      OCTET STRING
      MAX-ACCESS  read-only
      STATUS      current
      DESCRIPTION "ObjectName column"
      ::= { partitionLifeCycleTaskRuntimeEntry 2  }
   
   
   partitionLifeCycleTaskRuntimeStatus OBJECT-TYPE
      SYNTAX      OCTET STRING
      MAX-ACCESS  read-only
      STATUS      current
      DESCRIPTION "The status of this task. "
      ::= { partitionLifeCycleTaskRuntimeEntry 3  }
   
   
   partitionLifeCycleTaskRuntimeProgress OBJECT-TYPE
      SYNTAX      OCTET STRING
      MAX-ACCESS  read-only
      STATUS      current
      DESCRIPTION "The progress of this task. "
      ::= { partitionLifeCycleTaskRuntimeEntry 4  }
   
   
   partitionLifeCycleTaskRuntimeDescription OBJECT-TYPE
      SYNTAX      OCTET STRING
      MAX-ACCESS  read-only
      STATUS      current
      DESCRIPTION "A description of this task. "
      ::= { partitionLifeCycleTaskRuntimeEntry 5  }
   
   
   partitionLifeCycleTaskRuntimeEndTime OBJECT-TYPE
      SYNTAX      Counter64
      MAX-ACCESS  read-only
      STATUS      current
      DESCRIPTION "The time at which this task was completed.  A value of -1 indicates that the task is currently running. "
      ::= { partitionLifeCycleTaskRuntimeEntry 6  }
   
   
   partitionLifeCycleTaskRuntimeBeginTime OBJECT-TYPE
      SYNTAX      Counter64
      MAX-ACCESS  read-only
      STATUS      current
      DESCRIPTION "The time at which this task was started. "
      ::= { partitionLifeCycleTaskRuntimeEntry 7  }
   
   
   partitionLifeCycleTaskRuntimeOperation OBJECT-TYPE
      SYNTAX      OCTET STRING
      MAX-ACCESS  read-only
      STATUS      current
      DESCRIPTION "Returns the name of the current operation. "
      ::= { partitionLifeCycleTaskRuntimeEntry 8  }
   
   
   partitionLifeCycleTaskRuntimeName OBJECT-TYPE
      SYNTAX      OCTET STRING
      MAX-ACCESS  read-only
      STATUS      current
      DESCRIPTION "The name of this configuration. WebLogic Server uses an MBean to implement and persist the configuration. "
      ::= { partitionLifeCycleTaskRuntimeEntry 9  }
   
   
   partitionLifeCycleTaskRuntimePartitionName OBJECT-TYPE
      SYNTAX      OCTET STRING
      MAX-ACCESS  read-only
      STATUS      current
      DESCRIPTION "Returns the name of the partition being operated on. "
      ::= { partitionLifeCycleTaskRuntimeEntry 10  }
   
   
   partitionLifeCycleTaskRuntimeType OBJECT-TYPE
      SYNTAX      OCTET STRING
      MAX-ACCESS  read-only
      STATUS      current
      DESCRIPTION "Returns the type of the MBean. "
      ::= { partitionLifeCycleTaskRuntimeEntry 11  }
   
   
   partitionLifeCycleTaskRuntimeSystemTask OBJECT-TYPE
      SYNTAX      OCTET STRING
      MAX-ACCESS  read-only
      STATUS      current
      DESCRIPTION "Indicates whether this task was initiated by the server versus a user. "
      ::= { partitionLifeCycleTaskRuntimeEntry 12  }
   
   
   partitionLifeCycleTaskRuntimeRunning OBJECT-TYPE
      SYNTAX      OCTET STRING
      MAX-ACCESS  read-only
      STATUS      current
      DESCRIPTION "Indicates whether the task is still running. "
      ::= { partitionLifeCycleTaskRuntimeEntry 13  }
   
   
   partitionLifeCycleTaskRuntimeServerName OBJECT-TYPE
      SYNTAX      OCTET STRING
      MAX-ACCESS  read-only
      STATUS      current
      DESCRIPTION "Returns the name of the server on which operation happens. "
      ::= { partitionLifeCycleTaskRuntimeEntry 14  }
   
   
   partitionMinThreadsConstraintCapRuntimeTable OBJECT-TYPE
      SYNTAX      SEQUENCE OF PartitionMinThreadsConstraintCapRuntimeEntry
      MAX-ACCESS  not-accessible
      STATUS      current
      DESCRIPTION "Monitoring information for PartitionMinThreadsConstraint "
      ::= { wls 2365  }
      
   
   partitionMinThreadsConstraintCapRuntimeEntry OBJECT-TYPE
      SYNTAX      PartitionMinThreadsConstraintCapRuntimeEntry
      MAX-ACCESS  not-accessible
      STATUS      current
      DESCRIPTION "Generated SNMP Table Entry."
      INDEX { partitionMinThreadsConstraintCapRuntimeIndex}
      ::= { partitionMinThreadsConstraintCapRuntimeTable 1 }
      
   PartitionMinThreadsConstraintCapRuntimeEntry ::=
      SEQUENCE
      {
         partitionMinThreadsConstraintCapRuntimeIndex OCTET STRING,
         partitionMinThreadsConstraintCapRuntimeObjectName OCTET STRING,
         partitionMinThreadsConstraintCapRuntimeName OCTET STRING,
         partitionMinThreadsConstraintCapRuntimeSumMinThreadsConstraints Integer32,
         partitionMinThreadsConstraintCapRuntimeType OCTET STRING,
         partitionMinThreadsConstraintCapRuntimeExecutingRequests Integer32
      }
      
   
   partitionMinThreadsConstraintCapRuntimeIndex OBJECT-TYPE
      SYNTAX      OCTET STRING
      MAX-ACCESS  not-accessible
      STATUS      current
      DESCRIPTION "Index column"
      ::= { partitionMinThreadsConstraintCapRuntimeEntry 1  }
   
   
   partitionMinThreadsConstraintCapRuntimeObjectName OBJECT-TYPE
      SYNTAX      OCTET STRING
      MAX-ACCESS  read-only
      STATUS      current
      DESCRIPTION "ObjectName column"
      ::= { partitionMinThreadsConstraintCapRuntimeEntry 2  }
   
   
   partitionMinThreadsConstraintCapRuntimeName OBJECT-TYPE
      SYNTAX      OCTET STRING
      MAX-ACCESS  read-only
      STATUS      current
      DESCRIPTION "The name of this configuration. WebLogic Server uses an MBean to implement and persist the configuration. "
      ::= { partitionMinThreadsConstraintCapRuntimeEntry 3  }
   
   
   partitionMinThreadsConstraintCapRuntimeSumMinThreadsConstraints OBJECT-TYPE
      SYNTAX      Integer32
      MAX-ACCESS  read-only
      STATUS      current
      DESCRIPTION "Sum of all configured minimum threads constraints in the partition. This is the number of threads that is needed in order to satisfy all configured minimum threads constraints in the partition if all of them have more than that amount of concurrent work requests. "
      ::= { partitionMinThreadsConstraintCapRuntimeEntry 4  }
   
   
   partitionMinThreadsConstraintCapRuntimeType OBJECT-TYPE
      SYNTAX      OCTET STRING
      MAX-ACCESS  read-only
      STATUS      current
      DESCRIPTION "Returns the type of the MBean. "
      ::= { partitionMinThreadsConstraintCapRuntimeEntry 5  }
   
   
   partitionMinThreadsConstraintCapRuntimeExecutingRequests OBJECT-TYPE
      SYNTAX      Integer32
      MAX-ACCESS  read-only
      STATUS      current
      DESCRIPTION "Number of requests that are currently executing. "
      ::= { partitionMinThreadsConstraintCapRuntimeEntry 6  }
   
   
   partitionResourceMetricsRuntimeTable OBJECT-TYPE
      SYNTAX      SEQUENCE OF PartitionResourceMetricsRuntimeEntry
      MAX-ACCESS  not-accessible
      STATUS      current
      DESCRIPTION "The runtime MBean interface for partition specific resource consumption metrics. The resource meters are added lazily for a partition. Therefore, the first time these metrics are queried, it might return zero values. Subsequent gets would return non-zero values based on the resource consumption. These metrics are applicable in the context of a partition since either server start or partition creation/restart, whichever was later. "
      ::= { wls 2370  }
      
   
   partitionResourceMetricsRuntimeEntry OBJECT-TYPE
      SYNTAX      PartitionResourceMetricsRuntimeEntry
      MAX-ACCESS  not-accessible
      STATUS      current
      DESCRIPTION "Generated SNMP Table Entry."
      INDEX { partitionResourceMetricsRuntimeIndex}
      ::= { partitionResourceMetricsRuntimeTable 1 }
      
   PartitionResourceMetricsRuntimeEntry ::=
      SEQUENCE
      {
         partitionResourceMetricsRuntimeIndex OCTET STRING,
         partitionResourceMetricsRuntimeObjectName OCTET STRING,
         partitionResourceMetricsRuntimeAllocatedMemory Counter64,
         partitionResourceMetricsRuntimeFileBytesRead Counter64,
         partitionResourceMetricsRuntimeNetworkBytesRead Counter64,
         partitionResourceMetricsRuntimeRCMMetricsDataAvailable OCTET STRING,
         partitionResourceMetricsRuntimeCpuTimeNanos Counter64,
         partitionResourceMetricsRuntimeName OCTET STRING,
         partitionResourceMetricsRuntimeType OCTET STRING,
         partitionResourceMetricsRuntimeFileBytesWritten Counter64,
         partitionResourceMetricsRuntimeThreadCount Counter64,
         partitionResourceMetricsRuntimeTotalOpenedFileDescriptorCount Counter64,
         partitionResourceMetricsRuntimeCurrentOpenFileDescriptorCount Counter64,
         partitionResourceMetricsRuntimeCurrentOpenFileCount Counter64,
         partitionResourceMetricsRuntimeCurrentOpenSocketCount Counter64,
         partitionResourceMetricsRuntimeNetworkBytesWritten Counter64,
         partitionResourceMetricsRuntimeTotalOpenedFileCount Counter64,
         partitionResourceMetricsRuntimeTotalOpenedSocketCount Counter64
      }
      
   
   partitionResourceMetricsRuntimeIndex OBJECT-TYPE
      SYNTAX      OCTET STRING
      MAX-ACCESS  not-accessible
      STATUS      current
      DESCRIPTION "Index column"
      ::= { partitionResourceMetricsRuntimeEntry 1  }
   
   
   partitionResourceMetricsRuntimeObjectName OBJECT-TYPE
      SYNTAX      OCTET STRING
      MAX-ACCESS  read-only
      STATUS      current
      DESCRIPTION "ObjectName column"
      ::= { partitionResourceMetricsRuntimeEntry 2  }
   
   
   partitionResourceMetricsRuntimeAllocatedMemory OBJECT-TYPE
      SYNTAX      Counter64
      MAX-ACCESS  read-only
      STATUS      current
      DESCRIPTION "Total allocated memory in bytes for the partition. This metric value increases monotonically over time, it never decreases. Retained memory should be used to get current net values. "
      ::= { partitionResourceMetricsRuntimeEntry 3  }
   
   
   partitionResourceMetricsRuntimeFileBytesRead OBJECT-TYPE
      SYNTAX      Counter64
      MAX-ACCESS  read-only
      STATUS      current
      DESCRIPTION "Total number of file bytes read in the context of a partition. "
      ::= { partitionResourceMetricsRuntimeEntry 4  }
   
   
   partitionResourceMetricsRuntimeNetworkBytesRead OBJECT-TYPE
      SYNTAX      Counter64
      MAX-ACCESS  read-only
      STATUS      current
      DESCRIPTION "Total number of bytes read from sockets for a partition. "
      ::= { partitionResourceMetricsRuntimeEntry 5  }
   
   
   partitionResourceMetricsRuntimeRCMMetricsDataAvailable OBJECT-TYPE
      SYNTAX      OCTET STRING
      MAX-ACCESS  read-only
      STATUS      current
      DESCRIPTION "Checks whether RCM metrics data is available for this partition. "
      ::= { partitionResourceMetricsRuntimeEntry 6  }
   
   
   partitionResourceMetricsRuntimeCpuTimeNanos OBJECT-TYPE
      SYNTAX      Counter64
      MAX-ACCESS  read-only
      STATUS      current
      DESCRIPTION "Total CPU time spent measured in nanoseconds in the context of a partition. "
      ::= { partitionResourceMetricsRuntimeEntry 7  }
   
   
   partitionResourceMetricsRuntimeName OBJECT-TYPE
      SYNTAX      OCTET STRING
      MAX-ACCESS  read-only
      STATUS      current
      DESCRIPTION "The name of this configuration. WebLogic Server uses an MBean to implement and persist the configuration. "
      ::= { partitionResourceMetricsRuntimeEntry 8  }
   
   
   partitionResourceMetricsRuntimeType OBJECT-TYPE
      SYNTAX      OCTET STRING
      MAX-ACCESS  read-only
      STATUS      current
      DESCRIPTION "Returns the type of the MBean. "
      ::= { partitionResourceMetricsRuntimeEntry 9  }
   
   
   partitionResourceMetricsRuntimeFileBytesWritten OBJECT-TYPE
      SYNTAX      Counter64
      MAX-ACCESS  read-only
      STATUS      current
      DESCRIPTION "Total number of file bytes written in the context of a partition. "
      ::= { partitionResourceMetricsRuntimeEntry 10  }
   
   
   partitionResourceMetricsRuntimeThreadCount OBJECT-TYPE
      SYNTAX      Counter64
      MAX-ACCESS  read-only
      STATUS      current
      DESCRIPTION "Number of threads currently assigned to the partition. "
      ::= { partitionResourceMetricsRuntimeEntry 11  }
   
   
   partitionResourceMetricsRuntimeTotalOpenedFileDescriptorCount OBJECT-TYPE
      SYNTAX      Counter64
      MAX-ACCESS  read-only
      STATUS      current
      DESCRIPTION "Total number of file descriptors opened in the context of a partition. "
      ::= { partitionResourceMetricsRuntimeEntry 12  }
   
   
   partitionResourceMetricsRuntimeCurrentOpenFileDescriptorCount OBJECT-TYPE
      SYNTAX      Counter64
      MAX-ACCESS  read-only
      STATUS      current
      DESCRIPTION "Number of file descriptors currently open in the context of a partition. "
      ::= { partitionResourceMetricsRuntimeEntry 13  }
   
   
   partitionResourceMetricsRuntimeCurrentOpenFileCount OBJECT-TYPE
      SYNTAX      Counter64
      MAX-ACCESS  read-only
      STATUS      current
      DESCRIPTION "Number of files currently open in the context of a partition. "
      ::= { partitionResourceMetricsRuntimeEntry 14  }
   
   
   partitionResourceMetricsRuntimeCurrentOpenSocketCount OBJECT-TYPE
      SYNTAX      Counter64
      MAX-ACCESS  read-only
      STATUS      current
      DESCRIPTION "Number of sockets currently open in the context of a partition. "
      ::= { partitionResourceMetricsRuntimeEntry 15  }
   
   
   partitionResourceMetricsRuntimeNetworkBytesWritten OBJECT-TYPE
      SYNTAX      Counter64
      MAX-ACCESS  read-only
      STATUS      current
      DESCRIPTION "Total number of bytes written to sockets for a partition. "
      ::= { partitionResourceMetricsRuntimeEntry 16  }
   
   
   partitionResourceMetricsRuntimeTotalOpenedFileCount OBJECT-TYPE
      SYNTAX      Counter64
      MAX-ACCESS  read-only
      STATUS      current
      DESCRIPTION "Total number of files opened in the context of a partition. "
      ::= { partitionResourceMetricsRuntimeEntry 17  }
   
   
   partitionResourceMetricsRuntimeTotalOpenedSocketCount OBJECT-TYPE
      SYNTAX      Counter64
      MAX-ACCESS  read-only
      STATUS      current
      DESCRIPTION "Total number of sockets opened in the context of a partition. "
      ::= { partitionResourceMetricsRuntimeEntry 18  }
   
   
   partitionRuntimeTable OBJECT-TYPE
      SYNTAX      SEQUENCE OF PartitionRuntimeEntry
      MAX-ACCESS  not-accessible
      STATUS      current
      DESCRIPTION "Partition Runtime information. "
      ::= { wls 2375  }
      
   
   partitionRuntimeEntry OBJECT-TYPE
      SYNTAX      PartitionRuntimeEntry
      MAX-ACCESS  not-accessible
      STATUS      current
      DESCRIPTION "Generated SNMP Table Entry."
      INDEX { partitionRuntimeIndex}
      ::= { partitionRuntimeTable 1 }
      
   PartitionRuntimeEntry ::=
      SEQUENCE
      {
         partitionRuntimeIndex OCTET STRING,
         partitionRuntimeObjectName OCTET STRING,
         partitionRuntimeRestartRequired OCTET STRING,
         partitionRuntimeOverallHealthState OCTET STRING,
         partitionRuntimePartitionID OCTET STRING,
         partitionRuntimeName OCTET STRING,
         partitionRuntimeType OCTET STRING,
         partitionRuntimeState OCTET STRING,
         partitionRuntimeServerName OCTET STRING,
         partitionRuntimeSystemFileSystemRoot OCTET STRING,
         partitionRuntimeUserFileSystemRoot OCTET STRING,
         partitionRuntimeSubState OCTET STRING
      }
      
   
   partitionRuntimeIndex OBJECT-TYPE
      SYNTAX      OCTET STRING
      MAX-ACCESS  not-accessible
      STATUS      current
      DESCRIPTION "Index column"
      ::= { partitionRuntimeEntry 1  }
   
   
   partitionRuntimeObjectName OBJECT-TYPE
      SYNTAX      OCTET STRING
      MAX-ACCESS  read-only
      STATUS      current
      DESCRIPTION "ObjectName column"
      ::= { partitionRuntimeEntry 2  }
   
   
   partitionRuntimeRestartRequired OBJECT-TYPE
      SYNTAX      OCTET STRING
      MAX-ACCESS  read-only
      STATUS      current
      DESCRIPTION "Indicates whether the partition must be restarted in order to activate configuration changes. "
      ::= { partitionRuntimeEntry 3  }
   
   
   partitionRuntimeOverallHealthState OBJECT-TYPE
      SYNTAX      OCTET STRING
      MAX-ACCESS  read-only
      STATUS      current
      DESCRIPTION "The aggregate health state of the partition as reported by components within the partition  "
      ::= { partitionRuntimeEntry 4  }
   
   
   partitionRuntimePartitionID OBJECT-TYPE
      SYNTAX      OCTET STRING
      MAX-ACCESS  read-only
      STATUS      current
      DESCRIPTION "Partition ID for this partition. "
      ::= { partitionRuntimeEntry 5  }
   
   
   partitionRuntimeName OBJECT-TYPE
      SYNTAX      OCTET STRING
      MAX-ACCESS  read-only
      STATUS      current
      DESCRIPTION "The name of this configuration. WebLogic Server uses an MBean to implement and persist the configuration. "
      ::= { partitionRuntimeEntry 6  }
   
   
   partitionRuntimeType OBJECT-TYPE
      SYNTAX      OCTET STRING
      MAX-ACCESS  read-only
      STATUS      current
      DESCRIPTION "Returns the type of the MBean. "
      ::= { partitionRuntimeEntry 7  }
   
   
   partitionRuntimeState OBJECT-TYPE
      SYNTAX      OCTET STRING
      MAX-ACCESS  read-only
      STATUS      current
      DESCRIPTION "The current state of the partition runtime MBean "
      ::= { partitionRuntimeEntry 8  }
   
   
   partitionRuntimeServerName OBJECT-TYPE
      SYNTAX      OCTET STRING
      MAX-ACCESS  read-only
      STATUS      current
      DESCRIPTION "The server associated with this configuration.  "
      ::= { partitionRuntimeEntry 9  }
   
   
   partitionRuntimeSystemFileSystemRoot OBJECT-TYPE
      SYNTAX      OCTET STRING
      MAX-ACCESS  read-only
      STATUS      current
      DESCRIPTION "System file system root directory for this partition. "
      ::= { partitionRuntimeEntry 10  }
   
   
   partitionRuntimeUserFileSystemRoot OBJECT-TYPE
      SYNTAX      OCTET STRING
      MAX-ACCESS  read-only
      STATUS      current
      DESCRIPTION "User file system root directory for this partition. "
      ::= { partitionRuntimeEntry 11  }
   
   
   partitionRuntimeSubState OBJECT-TYPE
      SYNTAX      OCTET STRING
      MAX-ACCESS  read-only
      STATUS      current
      DESCRIPTION "The current substate of the partition runtime MBean "
      ::= { partitionRuntimeEntry 12  }
   
   
   partitionWorkManagerRuntimeTable OBJECT-TYPE
      SYNTAX      SEQUENCE OF PartitionWorkManagerRuntimeEntry
      MAX-ACCESS  not-accessible
      STATUS      current
      DESCRIPTION "Monitoring information for PartitionWorkManager "
      ::= { wls 2380  }
      
   
   partitionWorkManagerRuntimeEntry OBJECT-TYPE
      SYNTAX      PartitionWorkManagerRuntimeEntry
      MAX-ACCESS  not-accessible
      STATUS      current
      DESCRIPTION "Generated SNMP Table Entry."
      INDEX { partitionWorkManagerRuntimeIndex}
      ::= { partitionWorkManagerRuntimeTable 1 }
      
   PartitionWorkManagerRuntimeEntry ::=
      SEQUENCE
      {
         partitionWorkManagerRuntimeIndex OCTET STRING,
         partitionWorkManagerRuntimeObjectName OCTET STRING,
         partitionWorkManagerRuntimePendingUserRequestCount Integer32,
         partitionWorkManagerRuntimeOverloadRejectedRequestsCount Integer32,
         partitionWorkManagerRuntimeName OCTET STRING,
         partitionWorkManagerRuntimeSharedCapacityForWorkManagers Integer32,
         partitionWorkManagerRuntimeType OCTET STRING
      }
      
   
   partitionWorkManagerRuntimeIndex OBJECT-TYPE
      SYNTAX      OCTET STRING
      MAX-ACCESS  not-accessible
      STATUS      current
      DESCRIPTION "Index column"
      ::= { partitionWorkManagerRuntimeEntry 1  }
   
   
   partitionWorkManagerRuntimeObjectName OBJECT-TYPE
      SYNTAX      OCTET STRING
      MAX-ACCESS  read-only
      STATUS      current
      DESCRIPTION "ObjectName column"
      ::= { partitionWorkManagerRuntimeEntry 2  }
   
   
   partitionWorkManagerRuntimePendingUserRequestCount OBJECT-TYPE
      SYNTAX      Integer32
      MAX-ACCESS  read-only
      STATUS      current
      DESCRIPTION "The number of pending user requests in the priority queue. The priority queue contains requests from internal subsystems and users. This is just the count of all user requests. "
      ::= { partitionWorkManagerRuntimeEntry 3  }
   
   
   partitionWorkManagerRuntimeOverloadRejectedRequestsCount OBJECT-TYPE
      SYNTAX      Integer32
      MAX-ACCESS  read-only
      STATUS      current
      DESCRIPTION "Number of requests rejected due to configured Shared Capacity for work managers have been reached. "
      ::= { partitionWorkManagerRuntimeEntry 4  }
   
   
   partitionWorkManagerRuntimeName OBJECT-TYPE
      SYNTAX      OCTET STRING
      MAX-ACCESS  read-only
      STATUS      current
      DESCRIPTION "The name of this configuration. WebLogic Server uses an MBean to implement and persist the configuration. "
      ::= { partitionWorkManagerRuntimeEntry 5  }
   
   
   partitionWorkManagerRuntimeSharedCapacityForWorkManagers OBJECT-TYPE
      SYNTAX      Integer32
      MAX-ACCESS  read-only
      STATUS      current
      DESCRIPTION "Maximum amount of requests that can be accepted in the priority queue. Note that a request with higher priority will be accepted in place of a lower priority request already in the queue even after the threshold is reached. The lower priority request is kept waiting in the queue till all high priority requests are executed. Also note that further enqueues of the low priority requests are rejected right away.  "
      ::= { partitionWorkManagerRuntimeEntry 6  }
   
   
   partitionWorkManagerRuntimeType OBJECT-TYPE
      SYNTAX      OCTET STRING
      MAX-ACCESS  read-only
      STATUS      current
      DESCRIPTION "Returns the type of the MBean. "
      ::= { partitionWorkManagerRuntimeEntry 7  }
   
   
   resourceGroupLifeCycleRuntimeTable OBJECT-TYPE
      SYNTAX      SEQUENCE OF ResourceGroupLifeCycleRuntimeEntry
      MAX-ACCESS  not-accessible
      STATUS      current
      DESCRIPTION "Provides methods that transition resource groups from one state to another. This class is instantiated once for each resource group but only on the Administration Server. Even so, you can use a resource group's instance to change the state of the resource group on Managed Servers as well as on the Administration Server.  Detecting when Operations Complete Methods representing operations on resource groups return a {@link ResourceGroupLifeCycleTaskRuntimeMBean} object. The caller should monitor the returned instance, invoking its {@link ResourceGroupLifeCycleTaskRuntimeMBean#isRunning()} method to detect when the operation has completed. In particular, the caller should not rely on the value returned from {@link #getState()} to indicate when an operation on a resource group that is targeted to multiple servers has finished. That value will be accurate as described in detail on {@link #getState()} but can change before the operation has finished.  Desired States The system tracks the desired state for each resource group, which defaults to the state RUNNING. Whenever a lifecycle operation method is called the system not only performs the requested action on the resource group but also records the resulting state as the new desired state for the resource group. The system uses the desired state for a resource group to bring the resource group to the correct state during server and partition start-up. The desired can also be used when the {@link #getState()} method computes the overall state for the resource group. "
      ::= { wls 2385  }
      
   
   resourceGroupLifeCycleRuntimeEntry OBJECT-TYPE
      SYNTAX      ResourceGroupLifeCycleRuntimeEntry
      MAX-ACCESS  not-accessible
      STATUS      current
      DESCRIPTION "Generated SNMP Table Entry."
      INDEX { resourceGroupLifeCycleRuntimeIndex}
      ::= { resourceGroupLifeCycleRuntimeTable 1 }
      
   ResourceGroupLifeCycleRuntimeEntry ::=
      SEQUENCE
      {
         resourceGroupLifeCycleRuntimeIndex OCTET STRING,
         resourceGroupLifeCycleRuntimeObjectName OCTET STRING,
         resourceGroupLifeCycleRuntimeName OCTET STRING,
         resourceGroupLifeCycleRuntimeType OCTET STRING,
         resourceGroupLifeCycleRuntimeState OCTET STRING
      }
      
   
   resourceGroupLifeCycleRuntimeIndex OBJECT-TYPE
      SYNTAX      OCTET STRING
      MAX-ACCESS  not-accessible
      STATUS      current
      DESCRIPTION "Index column"
      ::= { resourceGroupLifeCycleRuntimeEntry 1  }
   
   
   resourceGroupLifeCycleRuntimeObjectName OBJECT-TYPE
      SYNTAX      OCTET STRING
      MAX-ACCESS  read-only
      STATUS      current
      DESCRIPTION "ObjectName column"
      ::= { resourceGroupLifeCycleRuntimeEntry 2  }
   
   
   resourceGroupLifeCycleRuntimeName OBJECT-TYPE
      SYNTAX      OCTET STRING
      MAX-ACCESS  read-only
      STATUS      current
      DESCRIPTION "The name of this configuration. WebLogic Server uses an MBean to implement and persist the configuration. "
      ::= { resourceGroupLifeCycleRuntimeEntry 3  }
   
   
   resourceGroupLifeCycleRuntimeType OBJECT-TYPE
      SYNTAX      OCTET STRING
      MAX-ACCESS  read-only
      STATUS      current
      DESCRIPTION "Returns the type of the MBean. "
      ::= { resourceGroupLifeCycleRuntimeEntry 4  }
   
   
   resourceGroupLifeCycleRuntimeState OBJECT-TYPE
      SYNTAX      OCTET STRING
      MAX-ACCESS  read-only
      STATUS      current
      DESCRIPTION "The current overall state of the resource group. The value returned is the highest state for the resource group on all servers where it is targeted. As a result, the overall resource group state can change (for example, to RUNNING) as soon as the operation (such as start) has finished on one server, even while the operation is still in progress elsewhere. If the resource group is not currently targeted to any running server then its reported state is the desired state indicated by the most recent resource group life cycle operation on the resource group. "
      ::= { resourceGroupLifeCycleRuntimeEntry 5  }
   
   
   resourceGroupLifeCycleTaskRuntimeTable OBJECT-TYPE
      SYNTAX      SEQUENCE OF ResourceGroupLifeCycleTaskRuntimeEntry
      MAX-ACCESS  not-accessible
      STATUS      current
      DESCRIPTION " "
      ::= { wls 2390  }
      
   
   resourceGroupLifeCycleTaskRuntimeEntry OBJECT-TYPE
      SYNTAX      ResourceGroupLifeCycleTaskRuntimeEntry
      MAX-ACCESS  not-accessible
      STATUS      current
      DESCRIPTION "Generated SNMP Table Entry."
      INDEX { resourceGroupLifeCycleTaskRuntimeIndex}
      ::= { resourceGroupLifeCycleTaskRuntimeTable 1 }
      
   ResourceGroupLifeCycleTaskRuntimeEntry ::=
      SEQUENCE
      {
         resourceGroupLifeCycleTaskRuntimeIndex OCTET STRING,
         resourceGroupLifeCycleTaskRuntimeObjectName OCTET STRING,
         resourceGroupLifeCycleTaskRuntimeStatus OCTET STRING,
         resourceGroupLifeCycleTaskRuntimeProgress OCTET STRING,
         resourceGroupLifeCycleTaskRuntimeDescription OCTET STRING,
         resourceGroupLifeCycleTaskRuntimeEndTime Counter64,
         resourceGroupLifeCycleTaskRuntimeBeginTime Counter64,
         resourceGroupLifeCycleTaskRuntimeOperation OCTET STRING,
         resourceGroupLifeCycleTaskRuntimeName OCTET STRING,
         resourceGroupLifeCycleTaskRuntimeType OCTET STRING,
         resourceGroupLifeCycleTaskRuntimeSystemTask OCTET STRING,
         resourceGroupLifeCycleTaskRuntimeRunning OCTET STRING,
         resourceGroupLifeCycleTaskRuntimeResourceGroupName OCTET STRING,
         resourceGroupLifeCycleTaskRuntimeServerName OCTET STRING
      }
      
   
   resourceGroupLifeCycleTaskRuntimeIndex OBJECT-TYPE
      SYNTAX      OCTET STRING
      MAX-ACCESS  not-accessible
      STATUS      current
      DESCRIPTION "Index column"
      ::= { resourceGroupLifeCycleTaskRuntimeEntry 1  }
   
   
   resourceGroupLifeCycleTaskRuntimeObjectName OBJECT-TYPE
      SYNTAX      OCTET STRING
      MAX-ACCESS  read-only
      STATUS      current
      DESCRIPTION "ObjectName column"
      ::= { resourceGroupLifeCycleTaskRuntimeEntry 2  }
   
   
   resourceGroupLifeCycleTaskRuntimeStatus OBJECT-TYPE
      SYNTAX      OCTET STRING
      MAX-ACCESS  read-only
      STATUS      current
      DESCRIPTION "The status of this task. "
      ::= { resourceGroupLifeCycleTaskRuntimeEntry 3  }
   
   
   resourceGroupLifeCycleTaskRuntimeProgress OBJECT-TYPE
      SYNTAX      OCTET STRING
      MAX-ACCESS  read-only
      STATUS      current
      DESCRIPTION "The progress of this task. "
      ::= { resourceGroupLifeCycleTaskRuntimeEntry 4  }
   
   
   resourceGroupLifeCycleTaskRuntimeDescription OBJECT-TYPE
      SYNTAX      OCTET STRING
      MAX-ACCESS  read-only
      STATUS      current
      DESCRIPTION "A description of this task. "
      ::= { resourceGroupLifeCycleTaskRuntimeEntry 5  }
   
   
   resourceGroupLifeCycleTaskRuntimeEndTime OBJECT-TYPE
      SYNTAX      Counter64
      MAX-ACCESS  read-only
      STATUS      current
      DESCRIPTION "The time at which this task was completed.  A value of -1 indicates that the task is currently running. "
      ::= { resourceGroupLifeCycleTaskRuntimeEntry 6  }
   
   
   resourceGroupLifeCycleTaskRuntimeBeginTime OBJECT-TYPE
      SYNTAX      Counter64
      MAX-ACCESS  read-only
      STATUS      current
      DESCRIPTION "The time at which this task was started. "
      ::= { resourceGroupLifeCycleTaskRuntimeEntry 7  }
   
   
   resourceGroupLifeCycleTaskRuntimeOperation OBJECT-TYPE
      SYNTAX      OCTET STRING
      MAX-ACCESS  read-only
      STATUS      current
      DESCRIPTION "Returns the name of the current operation. "
      ::= { resourceGroupLifeCycleTaskRuntimeEntry 8  }
   
   
   resourceGroupLifeCycleTaskRuntimeName OBJECT-TYPE
      SYNTAX      OCTET STRING
      MAX-ACCESS  read-only
      STATUS      current
      DESCRIPTION "The name of this configuration. WebLogic Server uses an MBean to implement and persist the configuration. "
      ::= { resourceGroupLifeCycleTaskRuntimeEntry 9  }
   
   
   resourceGroupLifeCycleTaskRuntimeType OBJECT-TYPE
      SYNTAX      OCTET STRING
      MAX-ACCESS  read-only
      STATUS      current
      DESCRIPTION "Returns the type of the MBean. "
      ::= { resourceGroupLifeCycleTaskRuntimeEntry 10  }
   
   
   resourceGroupLifeCycleTaskRuntimeSystemTask OBJECT-TYPE
      SYNTAX      OCTET STRING
      MAX-ACCESS  read-only
      STATUS      current
      DESCRIPTION "Indicates whether this task was initiated by the server versus a user. "
      ::= { resourceGroupLifeCycleTaskRuntimeEntry 11  }
   
   
   resourceGroupLifeCycleTaskRuntimeRunning OBJECT-TYPE
      SYNTAX      OCTET STRING
      MAX-ACCESS  read-only
      STATUS      current
      DESCRIPTION "Indicates whether the task is still running. "
      ::= { resourceGroupLifeCycleTaskRuntimeEntry 12  }
   
   
   resourceGroupLifeCycleTaskRuntimeResourceGroupName OBJECT-TYPE
      SYNTAX      OCTET STRING
      MAX-ACCESS  read-only
      STATUS      current
      DESCRIPTION "Returns the name of the resource group being operated on. "
      ::= { resourceGroupLifeCycleTaskRuntimeEntry 13  }
   
   
   resourceGroupLifeCycleTaskRuntimeServerName OBJECT-TYPE
      SYNTAX      OCTET STRING
      MAX-ACCESS  read-only
      STATUS      current
      DESCRIPTION "Returns the name of the server on which operation happens. "
      ::= { resourceGroupLifeCycleTaskRuntimeEntry 14  }
   
   
   resourceManagerRuntimeTable OBJECT-TYPE
      SYNTAX      SEQUENCE OF ResourceManagerRuntimeEntry
      MAX-ACCESS  not-accessible
      STATUS      current
      DESCRIPTION "The {@code ResourceManagerRuntimeMBean} holds runtime information about a Resource Manager that has been assigned to the current Domain Partition.  The {@code ResourceManagerRuntimeMBean} is used for retrieving the runtime state (information about policy evaluation, current resource usage, recourse actions executed) of configured resource management policies established for the current Partition by a system administrator in the current server instance. "
      ::= { wls 2395  }
      
   
   resourceManagerRuntimeEntry OBJECT-TYPE
      SYNTAX      ResourceManagerRuntimeEntry
      MAX-ACCESS  not-accessible
      STATUS      current
      DESCRIPTION "Generated SNMP Table Entry."
      INDEX { resourceManagerRuntimeIndex}
      ::= { resourceManagerRuntimeTable 1 }
      
   ResourceManagerRuntimeEntry ::=
      SEQUENCE
      {
         resourceManagerRuntimeIndex OCTET STRING,
         resourceManagerRuntimeObjectName OCTET STRING,
         resourceManagerRuntimeName OCTET STRING,
         resourceManagerRuntimeType OCTET STRING
      }
      
   
   resourceManagerRuntimeIndex OBJECT-TYPE
      SYNTAX      OCTET STRING
      MAX-ACCESS  not-accessible
      STATUS      current
      DESCRIPTION "Index column"
      ::= { resourceManagerRuntimeEntry 1  }
   
   
   resourceManagerRuntimeObjectName OBJECT-TYPE
      SYNTAX      OCTET STRING
      MAX-ACCESS  read-only
      STATUS      current
      DESCRIPTION "ObjectName column"
      ::= { resourceManagerRuntimeEntry 2  }
   
   
   resourceManagerRuntimeName OBJECT-TYPE
      SYNTAX      OCTET STRING
      MAX-ACCESS  read-only
      STATUS      current
      DESCRIPTION "The name of this configuration. WebLogic Server uses an MBean to implement and persist the configuration. "
      ::= { resourceManagerRuntimeEntry 3  }
   
   
   resourceManagerRuntimeType OBJECT-TYPE
      SYNTAX      OCTET STRING
      MAX-ACCESS  read-only
      STATUS      current
      DESCRIPTION "Returns the type of the MBean. "
      ::= { resourceManagerRuntimeEntry 4  }
   
   
   resourceRuntimeTable OBJECT-TYPE
      SYNTAX      SEQUENCE OF ResourceRuntimeEntry
      MAX-ACCESS  not-accessible
      STATUS      current
      DESCRIPTION " The {@code ResourceRuntimeMBean} holds runtime state about the policy evaluations that have been performed for a Resource type in the current Domain Partition in the current server instance.  "
      ::= { wls 2400  }
      
   
   resourceRuntimeEntry OBJECT-TYPE
      SYNTAX      ResourceRuntimeEntry
      MAX-ACCESS  not-accessible
      STATUS      current
      DESCRIPTION "Generated SNMP Table Entry."
      INDEX { resourceRuntimeIndex}
      ::= { resourceRuntimeTable 1 }
      
   ResourceRuntimeEntry ::=
      SEQUENCE
      {
         resourceRuntimeIndex OCTET STRING,
         resourceRuntimeObjectName OCTET STRING,
         resourceRuntimeUsage Counter64,
         resourceRuntimeResourceType OCTET STRING,
         resourceRuntimeName  OCTET STRING,
         resourceRuntimeType  OCTET STRING
      }
      
   
   resourceRuntimeIndex OBJECT-TYPE
      SYNTAX      OCTET STRING
      MAX-ACCESS  not-accessible
      STATUS      current
      DESCRIPTION "Index column"
      ::= { resourceRuntimeEntry 1  }
   
   
   resourceRuntimeObjectName OBJECT-TYPE
      SYNTAX      OCTET STRING
      MAX-ACCESS  read-only
      STATUS      current
      DESCRIPTION "ObjectName column"
      ::= { resourceRuntimeEntry 2  }
   
   
   resourceRuntimeUsage OBJECT-TYPE
      SYNTAX      Counter64
      MAX-ACCESS  read-only
      STATUS      current
      DESCRIPTION "The current resource utilization of a Resource by the current Domain Partition, in the current Server instance.  To track or monitor resource consumption for a Domain Partition without creating resource consumption management policies, see {@link weblogic.management.runtime.PartitionResourceMetricsRuntimeMBean}.  "
      ::= { resourceRuntimeEntry 3  }
   
   
   resourceRuntimeResourceType OBJECT-TYPE
      SYNTAX      OCTET STRING
      MAX-ACCESS  read-only
      STATUS      current
      DESCRIPTION "The resource type associated with this MBean. "
      ::= { resourceRuntimeEntry 4  }
   
   
   resourceRuntimeName OBJECT-TYPE
      SYNTAX      OCTET STRING
      MAX-ACCESS  read-only
      STATUS      current
      DESCRIPTION "The name of the policy defined for this resource as configured in the {@code ResourceManagerMBean} for this MBean's resource type {@link #getResourceType()}. "
      ::= { resourceRuntimeEntry 5  }
   
   
   resourceRuntimeType OBJECT-TYPE
      SYNTAX      OCTET STRING
      MAX-ACCESS  read-only
      STATUS      current
      DESCRIPTION "Returns the type of the MBean. "
      ::= { resourceRuntimeEntry 6  }
   
   
   rolloutServiceRuntimeTable OBJECT-TYPE
      SYNTAX      SEQUENCE OF RolloutServiceRuntimeEntry
      MAX-ACCESS  not-accessible
      STATUS      current
      DESCRIPTION " "
      ::= { wls 2405  }
      
   
   rolloutServiceRuntimeEntry OBJECT-TYPE
      SYNTAX      RolloutServiceRuntimeEntry
      MAX-ACCESS  not-accessible
      STATUS      current
      DESCRIPTION "Generated SNMP Table Entry."
      INDEX { rolloutServiceRuntimeIndex}
      ::= { rolloutServiceRuntimeTable 1 }
      
   RolloutServiceRuntimeEntry ::=
      SEQUENCE
      {
         rolloutServiceRuntimeIndex OCTET STRING,
         rolloutServiceRuntimeObjectName OCTET STRING,
         rolloutServiceRuntimeName OCTET STRING,
         rolloutServiceRuntimeType OCTET STRING
      }
      
   
   rolloutServiceRuntimeIndex OBJECT-TYPE
      SYNTAX      OCTET STRING
      MAX-ACCESS  not-accessible
      STATUS      current
      DESCRIPTION "Index column"
      ::= { rolloutServiceRuntimeEntry 1  }
   
   
   rolloutServiceRuntimeObjectName OBJECT-TYPE
      SYNTAX      OCTET STRING
      MAX-ACCESS  read-only
      STATUS      current
      DESCRIPTION "ObjectName column"
      ::= { rolloutServiceRuntimeEntry 2  }
   
   
   rolloutServiceRuntimeName OBJECT-TYPE
      SYNTAX      OCTET STRING
      MAX-ACCESS  read-only
      STATUS      current
      DESCRIPTION "The name of this configuration. WebLogic Server uses an MBean to implement and persist the configuration. "
      ::= { rolloutServiceRuntimeEntry 3  }
   
   
   rolloutServiceRuntimeType OBJECT-TYPE
      SYNTAX      OCTET STRING
      MAX-ACCESS  read-only
      STATUS      current
      DESCRIPTION "Returns the type of the MBean. "
      ::= { rolloutServiceRuntimeEntry 4  }
   
   
   rolloutTaskRuntimeTable OBJECT-TYPE
      SYNTAX      SEQUENCE OF RolloutTaskRuntimeEntry
      MAX-ACCESS  not-accessible
      STATUS      current
      DESCRIPTION "TaskRuntimeMBean for any workflow (WorkflowProgress) executed using management orchestration framework. "
      ::= { wls 2410  }
      
   
   rolloutTaskRuntimeEntry OBJECT-TYPE
      SYNTAX      RolloutTaskRuntimeEntry
      MAX-ACCESS  not-accessible
      STATUS      current
      DESCRIPTION "Generated SNMP Table Entry."
      INDEX { rolloutTaskRuntimeIndex}
      ::= { rolloutTaskRuntimeTable 1 }
      
   RolloutTaskRuntimeEntry ::=
      SEQUENCE
      {
         rolloutTaskRuntimeIndex OCTET STRING,
         rolloutTaskRuntimeObjectName OCTET STRING,
         rolloutTaskRuntimeDescription OCTET STRING,
         rolloutTaskRuntimeEndTime Counter64,
         rolloutTaskRuntimeWorkflowName OCTET STRING,
         rolloutTaskRuntimeBeginTime Counter64,
         rolloutTaskRuntimeProgressString OCTET STRING,
         rolloutTaskRuntimeWorkflowId OCTET STRING,
         rolloutTaskRuntimeName OCTET STRING,
         rolloutTaskRuntimeNumTotalCommands Integer32,
         rolloutTaskRuntimeSystemTask OCTET STRING,
         rolloutTaskRuntimeWorkflowTarget OCTET STRING,
         rolloutTaskRuntimeStatus OCTET STRING,
         rolloutTaskRuntimeProgress OCTET STRING,
         rolloutTaskRuntimeStatusHistory OCTET STRING,
         rolloutTaskRuntimeType OCTET STRING,
         rolloutTaskRuntimeWorkflowType OCTET STRING,
         rolloutTaskRuntimeRunning OCTET STRING,
         rolloutTaskRuntimeNumCompletedCommands Integer32
      }
      
   
   rolloutTaskRuntimeIndex OBJECT-TYPE
      SYNTAX      OCTET STRING
      MAX-ACCESS  not-accessible
      STATUS      current
      DESCRIPTION "Index column"
      ::= { rolloutTaskRuntimeEntry 1  }
   
   
   rolloutTaskRuntimeObjectName OBJECT-TYPE
      SYNTAX      OCTET STRING
      MAX-ACCESS  read-only
      STATUS      current
      DESCRIPTION "ObjectName column"
      ::= { rolloutTaskRuntimeEntry 2  }
   
   
   rolloutTaskRuntimeDescription OBJECT-TYPE
      SYNTAX      OCTET STRING
      MAX-ACCESS  read-only
      STATUS      current
      DESCRIPTION "A description of this task. "
      ::= { rolloutTaskRuntimeEntry 3  }
   
   
   rolloutTaskRuntimeEndTime OBJECT-TYPE
      SYNTAX      Counter64
      MAX-ACCESS  read-only
      STATUS      current
      DESCRIPTION "The time at which this task was completed.  A value of -1 indicates that the task is currently running. "
      ::= { rolloutTaskRuntimeEntry 4  }
   
   
   rolloutTaskRuntimeWorkflowName OBJECT-TYPE
      SYNTAX      OCTET STRING
      MAX-ACCESS  read-only
      STATUS      current
      DESCRIPTION "User defined name of this workflow. "
      ::= { rolloutTaskRuntimeEntry 5  }
   
   
   rolloutTaskRuntimeBeginTime OBJECT-TYPE
      SYNTAX      Counter64
      MAX-ACCESS  read-only
      STATUS      current
      DESCRIPTION "The time at which this task was started. "
      ::= { rolloutTaskRuntimeEntry 6  }
   
   
   rolloutTaskRuntimeProgressString OBJECT-TYPE
      SYNTAX      OCTET STRING
      MAX-ACCESS  read-only
      STATUS      current
      DESCRIPTION "Human-readable message containing information about the current workflow progress. "
      ::= { rolloutTaskRuntimeEntry 7  }
   
   
   rolloutTaskRuntimeWorkflowId OBJECT-TYPE
      SYNTAX      OCTET STRING
      MAX-ACCESS  read-only
      STATUS      current
      DESCRIPTION "Each workflow has a unique id. "
      ::= { rolloutTaskRuntimeEntry 8  }
   
   
   rolloutTaskRuntimeName OBJECT-TYPE
      SYNTAX      OCTET STRING
      MAX-ACCESS  read-only
      STATUS      current
      DESCRIPTION "The name of this configuration. WebLogic Server uses an MBean to implement and persist the configuration. "
      ::= { rolloutTaskRuntimeEntry 9  }
   
   
   rolloutTaskRuntimeNumTotalCommands OBJECT-TYPE
      SYNTAX      Integer32
      MAX-ACCESS  read-only
      STATUS      current
      DESCRIPTION "Number of all commands in the workflow. Together with {@code getNumCompletedCommands()} defines kind of progress information. "
      ::= { rolloutTaskRuntimeEntry 10  }
   
   
   rolloutTaskRuntimeSystemTask OBJECT-TYPE
      SYNTAX      OCTET STRING
      MAX-ACCESS  read-only
      STATUS      current
      DESCRIPTION "Indicates whether this task was initiated by the server versus a user. "
      ::= { rolloutTaskRuntimeEntry 11  }
   
   
   rolloutTaskRuntimeWorkflowTarget OBJECT-TYPE
      SYNTAX      OCTET STRING
      MAX-ACCESS  read-only
      STATUS      current
      DESCRIPTION "Returns the target that was specified when the workflow was created. It will typically be either the name of the domain, of one or more clusters, or one or more servers. "
      ::= { rolloutTaskRuntimeEntry 12  }
   
   
   rolloutTaskRuntimeStatus OBJECT-TYPE
      SYNTAX      OCTET STRING
      MAX-ACCESS  read-only
      STATUS      current
      DESCRIPTION "The status of this task. "
      ::= { rolloutTaskRuntimeEntry 13  }
   
   
   rolloutTaskRuntimeProgress OBJECT-TYPE
      SYNTAX      OCTET STRING
      MAX-ACCESS  read-only
      STATUS      current
      DESCRIPTION "The progress of this task. "
      ::= { rolloutTaskRuntimeEntry 14  }
   
   
   rolloutTaskRuntimeStatusHistory OBJECT-TYPE
      SYNTAX      OCTET STRING
      MAX-ACCESS  read-only
      STATUS      current
      DESCRIPTION "Provides step by step information (log) about the progress of the workflow. "
      ::= { rolloutTaskRuntimeEntry 15  }
   
   
   rolloutTaskRuntimeType OBJECT-TYPE
      SYNTAX      OCTET STRING
      MAX-ACCESS  read-only
      STATUS      current
      DESCRIPTION "Returns the type of the MBean. "
      ::= { rolloutTaskRuntimeEntry 16  }
   
   
   rolloutTaskRuntimeWorkflowType OBJECT-TYPE
      SYNTAX      OCTET STRING
      MAX-ACCESS  read-only
      STATUS      current
      DESCRIPTION "Returns a string that can be used to identify the different types of workflows. "
      ::= { rolloutTaskRuntimeEntry 17  }
   
   
   rolloutTaskRuntimeRunning OBJECT-TYPE
      SYNTAX      OCTET STRING
      MAX-ACCESS  read-only
      STATUS      current
      DESCRIPTION "Indicates whether the task is still running. "
      ::= { rolloutTaskRuntimeEntry 18  }
   
   
   rolloutTaskRuntimeNumCompletedCommands OBJECT-TYPE
      SYNTAX      Integer32
      MAX-ACCESS  read-only
      STATUS      current
      DESCRIPTION "Number of completed commands in the workflow. Together with {@code getNumTotalCommands()} defines kind of progress information. "
      ::= { rolloutTaskRuntimeEntry 19  }
   
   
   scalingTaskRuntimeTable OBJECT-TYPE
      SYNTAX      SEQUENCE OF ScalingTaskRuntimeEntry
      MAX-ACCESS  not-accessible
      STATUS      current
      DESCRIPTION " "
      ::= { wls 2415  }
      
   
   scalingTaskRuntimeEntry OBJECT-TYPE
      SYNTAX      ScalingTaskRuntimeEntry
      MAX-ACCESS  not-accessible
      STATUS      current
      DESCRIPTION "Generated SNMP Table Entry."
      INDEX { scalingTaskRuntimeIndex}
      ::= { scalingTaskRuntimeTable 1 }
      
   ScalingTaskRuntimeEntry ::=
      SEQUENCE
      {
         scalingTaskRuntimeIndex OCTET STRING,
         scalingTaskRuntimeObjectName OCTET STRING,
         scalingTaskRuntimeStatus OCTET STRING,
         scalingTaskRuntimeProgress OCTET STRING,
         scalingTaskRuntimeDescription OCTET STRING,
         scalingTaskRuntimeEndTime Counter64,
         scalingTaskRuntimeSelectedInstanceNames OCTET STRING,
         scalingTaskRuntimeBeginTime Counter64,
         scalingTaskRuntimeSuccess OCTET STRING,
         scalingTaskRuntimeName OCTET STRING,
         scalingTaskRuntimeScalingType OCTET STRING,
         scalingTaskRuntimeType OCTET STRING,
         scalingTaskRuntimeSystemTask OCTET STRING,
         scalingTaskRuntimeRunning OCTET STRING,
         scalingTaskRuntimeClusterName OCTET STRING,
         scalingTaskRuntimeScaledInstanceNames OCTET STRING
      }
      
   
   scalingTaskRuntimeIndex OBJECT-TYPE
      SYNTAX      OCTET STRING
      MAX-ACCESS  not-accessible
      STATUS      current
      DESCRIPTION "Index column"
      ::= { scalingTaskRuntimeEntry 1  }
   
   
   scalingTaskRuntimeObjectName OBJECT-TYPE
      SYNTAX      OCTET STRING
      MAX-ACCESS  read-only
      STATUS      current
      DESCRIPTION "ObjectName column"
      ::= { scalingTaskRuntimeEntry 2  }
   
   
   scalingTaskRuntimeStatus OBJECT-TYPE
      SYNTAX      OCTET STRING
      MAX-ACCESS  read-only
      STATUS      current
      DESCRIPTION "The status of this task. "
      ::= { scalingTaskRuntimeEntry 3  }
   
   
   scalingTaskRuntimeProgress OBJECT-TYPE
      SYNTAX      OCTET STRING
      MAX-ACCESS  read-only
      STATUS      current
      DESCRIPTION "The progress of this task. "
      ::= { scalingTaskRuntimeEntry 4  }
   
   
   scalingTaskRuntimeDescription OBJECT-TYPE
      SYNTAX      OCTET STRING
      MAX-ACCESS  read-only
      STATUS      current
      DESCRIPTION "A description of this task. "
      ::= { scalingTaskRuntimeEntry 5  }
   
   
   scalingTaskRuntimeEndTime OBJECT-TYPE
      SYNTAX      Counter64
      MAX-ACCESS  read-only
      STATUS      current
      DESCRIPTION "The time at which this task was completed.  A value of -1 indicates that the task is currently running. "
      ::= { scalingTaskRuntimeEntry 6  }
   
   
   scalingTaskRuntimeSelectedInstanceNames OBJECT-TYPE
      SYNTAX      OCTET STRING
      MAX-ACCESS  read-only
      STATUS      current
      DESCRIPTION " "
      ::= { scalingTaskRuntimeEntry 7  }
   
   
   scalingTaskRuntimeBeginTime OBJECT-TYPE
      SYNTAX      Counter64
      MAX-ACCESS  read-only
      STATUS      current
      DESCRIPTION "The time at which this task was started. "
      ::= { scalingTaskRuntimeEntry 8  }
   
   
   scalingTaskRuntimeSuccess OBJECT-TYPE
      SYNTAX      OCTET STRING
      MAX-ACCESS  read-only
      STATUS      current
      DESCRIPTION " "
      ::= { scalingTaskRuntimeEntry 9  }
   
   
   scalingTaskRuntimeName OBJECT-TYPE
      SYNTAX      OCTET STRING
      MAX-ACCESS  read-only
      STATUS      current
      DESCRIPTION "The name of this configuration. WebLogic Server uses an MBean to implement and persist the configuration. "
      ::= { scalingTaskRuntimeEntry 10  }
   
   
   scalingTaskRuntimeScalingType OBJECT-TYPE
      SYNTAX      OCTET STRING
      MAX-ACCESS  read-only
      STATUS      current
      DESCRIPTION " "
      ::= { scalingTaskRuntimeEntry 11  }
   
   
   scalingTaskRuntimeType OBJECT-TYPE
      SYNTAX      OCTET STRING
      MAX-ACCESS  read-only
      STATUS      current
      DESCRIPTION "Returns the type of the MBean. "
      ::= { scalingTaskRuntimeEntry 12  }
   
   
   scalingTaskRuntimeSystemTask OBJECT-TYPE
      SYNTAX      OCTET STRING
      MAX-ACCESS  read-only
      STATUS      current
      DESCRIPTION "Indicates whether this task was initiated by the server versus a user. "
      ::= { scalingTaskRuntimeEntry 13  }
   
   
   scalingTaskRuntimeRunning OBJECT-TYPE
      SYNTAX      OCTET STRING
      MAX-ACCESS  read-only
      STATUS      current
      DESCRIPTION "Indicates whether the task is still running. "
      ::= { scalingTaskRuntimeEntry 14  }
   
   
   scalingTaskRuntimeClusterName OBJECT-TYPE
      SYNTAX      OCTET STRING
      MAX-ACCESS  read-only
      STATUS      current
      DESCRIPTION " "
      ::= { scalingTaskRuntimeEntry 15  }
   
   
   scalingTaskRuntimeScaledInstanceNames OBJECT-TYPE
      SYNTAX      OCTET STRING
      MAX-ACCESS  read-only
      STATUS      current
      DESCRIPTION " "
      ::= { scalingTaskRuntimeEntry 16  }
   
   
   triggerRuntimeTable OBJECT-TYPE
      SYNTAX      SEQUENCE OF TriggerRuntimeEntry
      MAX-ACCESS  not-accessible
      STATUS      current
      DESCRIPTION " The {@code TriggerRuntimeMBean} holds runtime state (for the current Server instance) for a Trigger that has been configured in the Resource Consumption Management policy of the current Domain Partition.   The WebLogic Resource Consumption Management feature automatically initiates the configured recourse action of a Trigger when the Trigger's configured usage limits are exceeded by a Domain Partition. When a usage limit is exceeded, and the configured recourse action has been successfully executed, the Trigger is Activated.   When the current resource usage by the Domain Partition falls below the Trigger's configured usage limit, the feature automatically withdraws the recourse action where possible. When the current usage is below the configured usage limit, and the configured recourse action has been successfully withdrawn, the Trigger is said to be not Activated.   The MBean captures the following states for a Trigger when the current resource consumption usage by the Domain Partition exceeds or goes below the configured usage limit for the Domain Partition:   Whether the Trigger is Activated (usage has exceeded the limit and the recourse action was successfully executed) or not The time when the last recourse action was executed successfully for the Trigger Whether a recourse action has been initiated in response to the resource usage by the Domain Partition exceeding the configured usage limits  "
      ::= { wls 2420  }
      
   
   triggerRuntimeEntry OBJECT-TYPE
      SYNTAX      TriggerRuntimeEntry
      MAX-ACCESS  not-accessible
      STATUS      current
      DESCRIPTION "Generated SNMP Table Entry."
      INDEX { triggerRuntimeIndex}
      ::= { triggerRuntimeTable 1 }
      
   TriggerRuntimeEntry ::=
      SEQUENCE
      {
         triggerRuntimeIndex  OCTET STRING,
         triggerRuntimeObjectName OCTET STRING,
         triggerRuntimeName   OCTET STRING,
         triggerRuntimeActivated OCTET STRING,
         triggerRuntimeInitiated OCTET STRING,
         triggerRuntimeType   OCTET STRING,
         triggerRuntimeLastTimeExecuted OCTET STRING
      }
      
   
   triggerRuntimeIndex OBJECT-TYPE
      SYNTAX      OCTET STRING
      MAX-ACCESS  not-accessible
      STATUS      current
      DESCRIPTION "Index column"
      ::= { triggerRuntimeEntry 1  }
   
   
   triggerRuntimeObjectName OBJECT-TYPE
      SYNTAX      OCTET STRING
      MAX-ACCESS  read-only
      STATUS      current
      DESCRIPTION "ObjectName column"
      ::= { triggerRuntimeEntry 2  }
   
   
   triggerRuntimeName OBJECT-TYPE
      SYNTAX      OCTET STRING
      MAX-ACCESS  read-only
      STATUS      current
      DESCRIPTION "The name of the Trigger, as configured in the Resource Consumption Management policy of the Domain Partition. "
      ::= { triggerRuntimeEntry 3  }
   
   
   triggerRuntimeActivated OBJECT-TYPE
      SYNTAX      OCTET STRING
      MAX-ACCESS  read-only
      STATUS      current
      DESCRIPTION "Indicates if the Trigger is Activated. "
      ::= { triggerRuntimeEntry 4  }
   
   
   triggerRuntimeInitiated OBJECT-TYPE
      SYNTAX      OCTET STRING
      MAX-ACCESS  read-only
      STATUS      current
      DESCRIPTION "Indicates if a recourse action has been initiated for this Trigger as a result of the current resource usage by a Domain Partition exceeding its usage limit. A new {@code RecourseActionEventVBean} is added to the array returned by {@link #getRecourseActionEventsHistory()}.  The kind of recourse action initiated (for example, a new recourse action or a withdrawal of an existing recourse action) can be determined through {@link RecourseActionEventVBean#isActive()}.  "
      ::= { triggerRuntimeEntry 5  }
   
   
   triggerRuntimeType OBJECT-TYPE
      SYNTAX      OCTET STRING
      MAX-ACCESS  read-only
      STATUS      current
      DESCRIPTION "Returns the type of the MBean. "
      ::= { triggerRuntimeEntry 6  }
   
   
   triggerRuntimeLastTimeExecuted OBJECT-TYPE
      SYNTAX      OCTET STRING
      MAX-ACCESS  read-only
      STATUS      current
      DESCRIPTION "The {@code Date} when the last recourse action was successfully executed for the current Trigger. "
      ::= { triggerRuntimeEntry 7  }
   
   
   wldfDebugPatchTaskRuntimeTable OBJECT-TYPE
      SYNTAX      SEQUENCE OF WldfDebugPatchTaskRuntimeEntry
      MAX-ACCESS  not-accessible
      STATUS      current
      DESCRIPTION "This interface provides monitoring over activation and deactivation tasks for dynamic debug patches "
      ::= { wls 2425  }
      
   
   wldfDebugPatchTaskRuntimeEntry OBJECT-TYPE
      SYNTAX      WldfDebugPatchTaskRuntimeEntry
      MAX-ACCESS  not-accessible
      STATUS      current
      DESCRIPTION "Generated SNMP Table Entry."
      INDEX { wldfDebugPatchTaskRuntimeIndex}
      ::= { wldfDebugPatchTaskRuntimeTable 1 }
      
   WldfDebugPatchTaskRuntimeEntry ::=
      SEQUENCE
      {
         wldfDebugPatchTaskRuntimeIndex OCTET STRING,
         wldfDebugPatchTaskRuntimeObjectName OCTET STRING,
         wldfDebugPatchTaskRuntimeStatus OCTET STRING,
         wldfDebugPatchTaskRuntimeProgress OCTET STRING,
         wldfDebugPatchTaskRuntimeApplicationName OCTET STRING,
         wldfDebugPatchTaskRuntimeDescription OCTET STRING,
         wldfDebugPatchTaskRuntimeEndTime Counter64,
         wldfDebugPatchTaskRuntimeModuleName OCTET STRING,
         wldfDebugPatchTaskRuntimeBeginTime Counter64,
         wldfDebugPatchTaskRuntimeName OCTET STRING,
         wldfDebugPatchTaskRuntimeType OCTET STRING,
         wldfDebugPatchTaskRuntimeSystemTask OCTET STRING,
         wldfDebugPatchTaskRuntimeRunning OCTET STRING,
         wldfDebugPatchTaskRuntimeActivationTask OCTET STRING,
         wldfDebugPatchTaskRuntimePatches OCTET STRING
      }
      
   
   wldfDebugPatchTaskRuntimeIndex OBJECT-TYPE
      SYNTAX      OCTET STRING
      MAX-ACCESS  not-accessible
      STATUS      current
      DESCRIPTION "Index column"
      ::= { wldfDebugPatchTaskRuntimeEntry 1  }
   
   
   wldfDebugPatchTaskRuntimeObjectName OBJECT-TYPE
      SYNTAX      OCTET STRING
      MAX-ACCESS  read-only
      STATUS      current
      DESCRIPTION "ObjectName column"
      ::= { wldfDebugPatchTaskRuntimeEntry 2  }
   
   
   wldfDebugPatchTaskRuntimeStatus OBJECT-TYPE
      SYNTAX      OCTET STRING
      MAX-ACCESS  read-only
      STATUS      current
      DESCRIPTION "The status of this task. "
      ::= { wldfDebugPatchTaskRuntimeEntry 3  }
   
   
   wldfDebugPatchTaskRuntimeProgress OBJECT-TYPE
      SYNTAX      OCTET STRING
      MAX-ACCESS  read-only
      STATUS      current
      DESCRIPTION "The progress of this task. "
      ::= { wldfDebugPatchTaskRuntimeEntry 4  }
   
   
   wldfDebugPatchTaskRuntimeApplicationName OBJECT-TYPE
      SYNTAX      OCTET STRING
      MAX-ACCESS  read-only
      STATUS      current
      DESCRIPTION " "
      ::= { wldfDebugPatchTaskRuntimeEntry 5  }
   
   
   wldfDebugPatchTaskRuntimeDescription OBJECT-TYPE
      SYNTAX      OCTET STRING
      MAX-ACCESS  read-only
      STATUS      current
      DESCRIPTION "A description of this task. "
      ::= { wldfDebugPatchTaskRuntimeEntry 6  }
   
   
   wldfDebugPatchTaskRuntimeEndTime OBJECT-TYPE
      SYNTAX      Counter64
      MAX-ACCESS  read-only
      STATUS      current
      DESCRIPTION "The time at which this task was completed.  A value of -1 indicates that the task is currently running. "
      ::= { wldfDebugPatchTaskRuntimeEntry 7  }
   
   
   wldfDebugPatchTaskRuntimeModuleName OBJECT-TYPE
      SYNTAX      OCTET STRING
      MAX-ACCESS  read-only
      STATUS      current
      DESCRIPTION " "
      ::= { wldfDebugPatchTaskRuntimeEntry 8  }
   
   
   wldfDebugPatchTaskRuntimeBeginTime OBJECT-TYPE
      SYNTAX      Counter64
      MAX-ACCESS  read-only
      STATUS      current
      DESCRIPTION "The time at which this task was started. "
      ::= { wldfDebugPatchTaskRuntimeEntry 9  }
   
   
   wldfDebugPatchTaskRuntimeName OBJECT-TYPE
      SYNTAX      OCTET STRING
      MAX-ACCESS  read-only
      STATUS      current
      DESCRIPTION "The name of this configuration. WebLogic Server uses an MBean to implement and persist the configuration. "
      ::= { wldfDebugPatchTaskRuntimeEntry 10  }
   
   
   wldfDebugPatchTaskRuntimeType OBJECT-TYPE
      SYNTAX      OCTET STRING
      MAX-ACCESS  read-only
      STATUS      current
      DESCRIPTION "Returns the type of the MBean. "
      ::= { wldfDebugPatchTaskRuntimeEntry 11  }
   
   
   wldfDebugPatchTaskRuntimeSystemTask OBJECT-TYPE
      SYNTAX      OCTET STRING
      MAX-ACCESS  read-only
      STATUS      current
      DESCRIPTION "Indicates whether this task was initiated by the server versus a user. "
      ::= { wldfDebugPatchTaskRuntimeEntry 12  }
   
   
   wldfDebugPatchTaskRuntimeRunning OBJECT-TYPE
      SYNTAX      OCTET STRING
      MAX-ACCESS  read-only
      STATUS      current
      DESCRIPTION "Indicates whether the task is still running. "
      ::= { wldfDebugPatchTaskRuntimeEntry 13  }
   
   
   wldfDebugPatchTaskRuntimeActivationTask OBJECT-TYPE
      SYNTAX      OCTET STRING
      MAX-ACCESS  read-only
      STATUS      current
      DESCRIPTION " "
      ::= { wldfDebugPatchTaskRuntimeEntry 14  }
   
   
   wldfDebugPatchTaskRuntimePatches OBJECT-TYPE
      SYNTAX      OCTET STRING
      MAX-ACCESS  read-only
      STATUS      current
      DESCRIPTION " "
      ::= { wldfDebugPatchTaskRuntimeEntry 15  }
   
   
   wldfDebugPatchesRuntimeTable OBJECT-TYPE
      SYNTAX      SEQUENCE OF WldfDebugPatchesRuntimeEntry
      MAX-ACCESS  not-accessible
      STATUS      current
      DESCRIPTION "This interface provides functionality to activate/deactivate dynamic debug patches without requiring server restart. It is assummed that the WLDF instrumentation agent is enabled. This is an internal interface. "
      ::= { wls 2430  }
      
   
   wldfDebugPatchesRuntimeEntry OBJECT-TYPE
      SYNTAX      WldfDebugPatchesRuntimeEntry
      MAX-ACCESS  not-accessible
      STATUS      current
      DESCRIPTION "Generated SNMP Table Entry."
      INDEX { wldfDebugPatchesRuntimeIndex}
      ::= { wldfDebugPatchesRuntimeTable 1 }
      
   WldfDebugPatchesRuntimeEntry ::=
      SEQUENCE
      {
         wldfDebugPatchesRuntimeIndex OCTET STRING,
         wldfDebugPatchesRuntimeObjectName OCTET STRING,
         wldfDebugPatchesRuntimeName OCTET STRING,
         wldfDebugPatchesRuntimeType OCTET STRING,
         wldfDebugPatchesRuntimeActiveDebugPatches OCTET STRING,
         wldfDebugPatchesRuntimeAvailableDebugPatches OCTET STRING
      }
      
   
   wldfDebugPatchesRuntimeIndex OBJECT-TYPE
      SYNTAX      OCTET STRING
      MAX-ACCESS  not-accessible
      STATUS      current
      DESCRIPTION "Index column"
      ::= { wldfDebugPatchesRuntimeEntry 1  }
   
   
   wldfDebugPatchesRuntimeObjectName OBJECT-TYPE
      SYNTAX      OCTET STRING
      MAX-ACCESS  read-only
      STATUS      current
      DESCRIPTION "ObjectName column"
      ::= { wldfDebugPatchesRuntimeEntry 2  }
   
   
   wldfDebugPatchesRuntimeName OBJECT-TYPE
      SYNTAX      OCTET STRING
      MAX-ACCESS  read-only
      STATUS      current
      DESCRIPTION "The name of this configuration. WebLogic Server uses an MBean to implement and persist the configuration. "
      ::= { wldfDebugPatchesRuntimeEntry 3  }
   
   
   wldfDebugPatchesRuntimeType OBJECT-TYPE
      SYNTAX      OCTET STRING
      MAX-ACCESS  read-only
      STATUS      current
      DESCRIPTION "Returns the type of the MBean. "
      ::= { wldfDebugPatchesRuntimeEntry 4  }
   
   
   wldfDebugPatchesRuntimeActiveDebugPatches OBJECT-TYPE
      SYNTAX      OCTET STRING
      MAX-ACCESS  read-only
      STATUS      current
      DESCRIPTION " "
      ::= { wldfDebugPatchesRuntimeEntry 5  }
   
   
   wldfDebugPatchesRuntimeAvailableDebugPatches OBJECT-TYPE
      SYNTAX      OCTET STRING
      MAX-ACCESS  read-only
      STATUS      current
      DESCRIPTION " "
      ::= { wldfDebugPatchesRuntimeEntry 6  }
   
   
   wldfPartitionAccessRuntimeTable OBJECT-TYPE
      SYNTAX      SEQUENCE OF WldfPartitionAccessRuntimeEntry
      MAX-ACCESS  not-accessible
      STATUS      current
      DESCRIPTION "Use this interface to access the different types of diagnostic data generated by a partition. "
      ::= { wls 2435  }
      
   
   wldfPartitionAccessRuntimeEntry OBJECT-TYPE
      SYNTAX      WldfPartitionAccessRuntimeEntry
      MAX-ACCESS  not-accessible
      STATUS      current
      DESCRIPTION "Generated SNMP Table Entry."
      INDEX { wldfPartitionAccessRuntimeIndex}
      ::= { wldfPartitionAccessRuntimeTable 1 }
      
   WldfPartitionAccessRuntimeEntry ::=
      SEQUENCE
      {
         wldfPartitionAccessRuntimeIndex OCTET STRING,
         wldfPartitionAccessRuntimeObjectName OCTET STRING,
         wldfPartitionAccessRuntimeAvailableDiagnosticDataAccessorNames OCTET STRING,
         wldfPartitionAccessRuntimeName OCTET STRING,
         wldfPartitionAccessRuntimeType OCTET STRING
      }
      
   
   wldfPartitionAccessRuntimeIndex OBJECT-TYPE
      SYNTAX      OCTET STRING
      MAX-ACCESS  not-accessible
      STATUS      current
      DESCRIPTION "Index column"
      ::= { wldfPartitionAccessRuntimeEntry 1  }
   
   
   wldfPartitionAccessRuntimeObjectName OBJECT-TYPE
      SYNTAX      OCTET STRING
      MAX-ACCESS  read-only
      STATUS      current
      DESCRIPTION "ObjectName column"
      ::= { wldfPartitionAccessRuntimeEntry 2  }
   
   
   wldfPartitionAccessRuntimeAvailableDiagnosticDataAccessorNames OBJECT-TYPE
      SYNTAX      OCTET STRING
      MAX-ACCESS  read-only
      STATUS      current
      DESCRIPTION " "
      ::= { wldfPartitionAccessRuntimeEntry 3  }
   
   
   wldfPartitionAccessRuntimeName OBJECT-TYPE
      SYNTAX      OCTET STRING
      MAX-ACCESS  read-only
      STATUS      current
      DESCRIPTION "The name of this configuration. WebLogic Server uses an MBean to implement and persist the configuration. "
      ::= { wldfPartitionAccessRuntimeEntry 4  }
   
   
   wldfPartitionAccessRuntimeType OBJECT-TYPE
      SYNTAX      OCTET STRING
      MAX-ACCESS  read-only
      STATUS      current
      DESCRIPTION "Returns the type of the MBean. "
      ::= { wldfPartitionAccessRuntimeEntry 5  }
   
   
   wldfPartitionRuntimeTable OBJECT-TYPE
      SYNTAX      SEQUENCE OF WldfPartitionRuntimeEntry
      MAX-ACCESS  not-accessible
      STATUS      current
      DESCRIPTION "This interface provides access to all the runtime MBeans for the WebLogic Diagnostic Framework (WLDF). "
      ::= { wls 2440  }
      
   
   wldfPartitionRuntimeEntry OBJECT-TYPE
      SYNTAX      WldfPartitionRuntimeEntry
      MAX-ACCESS  not-accessible
      STATUS      current
      DESCRIPTION "Generated SNMP Table Entry."
      INDEX { wldfPartitionRuntimeIndex}
      ::= { wldfPartitionRuntimeTable 1 }
      
   WldfPartitionRuntimeEntry ::=
      SEQUENCE
      {
         wldfPartitionRuntimeIndex OCTET STRING,
         wldfPartitionRuntimeObjectName OCTET STRING,
         wldfPartitionRuntimeName OCTET STRING,
         wldfPartitionRuntimeType OCTET STRING
      }
      
   
   wldfPartitionRuntimeIndex OBJECT-TYPE
      SYNTAX      OCTET STRING
      MAX-ACCESS  not-accessible
      STATUS      current
      DESCRIPTION "Index column"
      ::= { wldfPartitionRuntimeEntry 1  }
   
   
   wldfPartitionRuntimeObjectName OBJECT-TYPE
      SYNTAX      OCTET STRING
      MAX-ACCESS  read-only
      STATUS      current
      DESCRIPTION "ObjectName column"
      ::= { wldfPartitionRuntimeEntry 2  }
   
   
   wldfPartitionRuntimeName OBJECT-TYPE
      SYNTAX      OCTET STRING
      MAX-ACCESS  read-only
      STATUS      current
      DESCRIPTION "The name of this configuration. WebLogic Server uses an MBean to implement and persist the configuration. "
      ::= { wldfPartitionRuntimeEntry 3  }
   
   
   wldfPartitionRuntimeType OBJECT-TYPE
      SYNTAX      OCTET STRING
      MAX-ACCESS  read-only
      STATUS      current
      DESCRIPTION "Returns the type of the MBean. "
      ::= { wldfPartitionRuntimeEntry 4  }
   
   
   websocketApplicationRuntimeTable OBJECT-TYPE
      SYNTAX      SEQUENCE OF WebsocketApplicationRuntimeEntry
      MAX-ACCESS  not-accessible
      STATUS      current
      DESCRIPTION "MBean used for accessing monitored application properties, such as registered endpoints, the number of currently open sessions, the maximal number of open sessions since the start of monitoring, and message statistics. "
      ::= { wls 2445  }
      
   
   websocketApplicationRuntimeEntry OBJECT-TYPE
      SYNTAX      WebsocketApplicationRuntimeEntry
      MAX-ACCESS  not-accessible
      STATUS      current
      DESCRIPTION "Generated SNMP Table Entry."
      INDEX { websocketApplicationRuntimeIndex}
      ::= { websocketApplicationRuntimeTable 1 }
      
   WebsocketApplicationRuntimeEntry ::=
      SEQUENCE
      {
         websocketApplicationRuntimeIndex OCTET STRING,
         websocketApplicationRuntimeObjectName OCTET STRING,
         websocketApplicationRuntimeOpenSessionsCount Integer32,
         websocketApplicationRuntimeMaximalSentMessageSize Counter64,
         websocketApplicationRuntimeReceivedMessagesCountPerSecond Counter64,
         websocketApplicationRuntimeMaximalReceivedMessageSize Counter64,
         websocketApplicationRuntimeAverageReceivedMessageSize Counter64,
         websocketApplicationRuntimeSentMessagesCountPerSecond Counter64,
         websocketApplicationRuntimeMaximalOpenSessionsCount Integer32,
         websocketApplicationRuntimeMinimalReceivedMessageSize Counter64,
         websocketApplicationRuntimeName OCTET STRING,
         websocketApplicationRuntimeType OCTET STRING,
         websocketApplicationRuntimeSentMessagesCount Counter64,
         websocketApplicationRuntimeAverageSentMessageSize Counter64,
         websocketApplicationRuntimeMinimalSentMessageSize Counter64,
         websocketApplicationRuntimeReceivedMessagesCount Counter64
      }
      
   
   websocketApplicationRuntimeIndex OBJECT-TYPE
      SYNTAX      OCTET STRING
      MAX-ACCESS  not-accessible
      STATUS      current
      DESCRIPTION "Index column"
      ::= { websocketApplicationRuntimeEntry 1  }
   
   
   websocketApplicationRuntimeObjectName OBJECT-TYPE
      SYNTAX      OCTET STRING
      MAX-ACCESS  read-only
      STATUS      current
      DESCRIPTION "ObjectName column"
      ::= { websocketApplicationRuntimeEntry 2  }
   
   
   websocketApplicationRuntimeOpenSessionsCount OBJECT-TYPE
      SYNTAX      Integer32
      MAX-ACCESS  read-only
      STATUS      current
      DESCRIPTION "Get the number of currently open sessions. "
      ::= { websocketApplicationRuntimeEntry 3  }
   
   
   websocketApplicationRuntimeMaximalSentMessageSize OBJECT-TYPE
      SYNTAX      Counter64
      MAX-ACCESS  read-only
      STATUS      current
      DESCRIPTION "Get the size of the largest message sent since the start of monitoring. "
      ::= { websocketApplicationRuntimeEntry 4  }
   
   
   websocketApplicationRuntimeReceivedMessagesCountPerSecond OBJECT-TYPE
      SYNTAX      Counter64
      MAX-ACCESS  read-only
      STATUS      current
      DESCRIPTION "Get the average number of received messages per second. "
      ::= { websocketApplicationRuntimeEntry 5  }
   
   
   websocketApplicationRuntimeMaximalReceivedMessageSize OBJECT-TYPE
      SYNTAX      Counter64
      MAX-ACCESS  read-only
      STATUS      current
      DESCRIPTION "Get the size of the largest message received since the start of monitoring. "
      ::= { websocketApplicationRuntimeEntry 6  }
   
   
   websocketApplicationRuntimeAverageReceivedMessageSize OBJECT-TYPE
      SYNTAX      Counter64
      MAX-ACCESS  read-only
      STATUS      current
      DESCRIPTION "Get the average size of all of the messages received since the start of monitoring. "
      ::= { websocketApplicationRuntimeEntry 7  }
   
   
   websocketApplicationRuntimeSentMessagesCountPerSecond OBJECT-TYPE
      SYNTAX      Counter64
      MAX-ACCESS  read-only
      STATUS      current
      DESCRIPTION "Get the average number of sent messages per second. "
      ::= { websocketApplicationRuntimeEntry 8  }
   
   
   websocketApplicationRuntimeMaximalOpenSessionsCount OBJECT-TYPE
      SYNTAX      Integer32
      MAX-ACCESS  read-only
      STATUS      current
      DESCRIPTION "Get the maximal number of open sessions since the start of monitoring. "
      ::= { websocketApplicationRuntimeEntry 9  }
   
   
   websocketApplicationRuntimeMinimalReceivedMessageSize OBJECT-TYPE
      SYNTAX      Counter64
      MAX-ACCESS  read-only
      STATUS      current
      DESCRIPTION "Get the size of the smallest message received since the start of monitoring. "
      ::= { websocketApplicationRuntimeEntry 10  }
   
   
   websocketApplicationRuntimeName OBJECT-TYPE
      SYNTAX      OCTET STRING
      MAX-ACCESS  read-only
      STATUS      current
      DESCRIPTION "The name of this configuration. WebLogic Server uses an MBean to implement and persist the configuration. "
      ::= { websocketApplicationRuntimeEntry 11  }
   
   
   websocketApplicationRuntimeType OBJECT-TYPE
      SYNTAX      OCTET STRING
      MAX-ACCESS  read-only
      STATUS      current
      DESCRIPTION "Returns the type of the MBean. "
      ::= { websocketApplicationRuntimeEntry 12  }
   
   
   websocketApplicationRuntimeSentMessagesCount OBJECT-TYPE
      SYNTAX      Counter64
      MAX-ACCESS  read-only
      STATUS      current
      DESCRIPTION "Get the total number of messages sent since the start of monitoring. "
      ::= { websocketApplicationRuntimeEntry 13  }
   
   
   websocketApplicationRuntimeAverageSentMessageSize OBJECT-TYPE
      SYNTAX      Counter64
      MAX-ACCESS  read-only
      STATUS      current
      DESCRIPTION "Get the average size of all of the messages sent since the start of monitoring. "
      ::= { websocketApplicationRuntimeEntry 14  }
   
   
   websocketApplicationRuntimeMinimalSentMessageSize OBJECT-TYPE
      SYNTAX      Counter64
      MAX-ACCESS  read-only
      STATUS      current
      DESCRIPTION "Get the size of the smallest message sent since the start of monitoring. "
      ::= { websocketApplicationRuntimeEntry 15  }
   
   
   websocketApplicationRuntimeReceivedMessagesCount OBJECT-TYPE
      SYNTAX      Counter64
      MAX-ACCESS  read-only
      STATUS      current
      DESCRIPTION "Get the total number of messages received since the start of monitoring. "
      ::= { websocketApplicationRuntimeEntry 16  }
   
   
   websocketEndpointRuntimeTable OBJECT-TYPE
      SYNTAX      SEQUENCE OF WebsocketEndpointRuntimeEntry
      MAX-ACCESS  not-accessible
      STATUS      current
      DESCRIPTION "MBean used for accessing monitored endpoint properties, such as the endpoint path and class name, the number of currently open sessions, the maximal number of open sessions since the start of monitoring, and message statistics. "
      ::= { wls 2450  }
      
   
   websocketEndpointRuntimeEntry OBJECT-TYPE
      SYNTAX      WebsocketEndpointRuntimeEntry
      MAX-ACCESS  not-accessible
      STATUS      current
      DESCRIPTION "Generated SNMP Table Entry."
      INDEX { websocketEndpointRuntimeIndex}
      ::= { websocketEndpointRuntimeTable 1 }
      
   WebsocketEndpointRuntimeEntry ::=
      SEQUENCE
      {
         websocketEndpointRuntimeIndex OCTET STRING,
         websocketEndpointRuntimeObjectName OCTET STRING,
         websocketEndpointRuntimeOpenSessionsCount Integer32,
         websocketEndpointRuntimeMaximalReceivedMessageSize Counter64,
         websocketEndpointRuntimeAverageReceivedMessageSize Counter64,
         websocketEndpointRuntimeSentMessagesCountPerSecond Counter64,
         websocketEndpointRuntimeName OCTET STRING,
         websocketEndpointRuntimeSentMessagesCount Counter64,
         websocketEndpointRuntimeAverageSentMessageSize Counter64,
         websocketEndpointRuntimeMinimalSentMessageSize Counter64,
         websocketEndpointRuntimeMaximalSentMessageSize Counter64,
         websocketEndpointRuntimeReceivedMessagesCountPerSecond Counter64,
         websocketEndpointRuntimeEndpointClassName OCTET STRING,
         websocketEndpointRuntimeEndpointPath OCTET STRING,
         websocketEndpointRuntimeMaximalOpenSessionsCount Integer32,
         websocketEndpointRuntimeMinimalReceivedMessageSize Counter64,
         websocketEndpointRuntimeType OCTET STRING,
         websocketEndpointRuntimeReceivedMessagesCount Counter64
      }
      
   
   websocketEndpointRuntimeIndex OBJECT-TYPE
      SYNTAX      OCTET STRING
      MAX-ACCESS  not-accessible
      STATUS      current
      DESCRIPTION "Index column"
      ::= { websocketEndpointRuntimeEntry 1  }
   
   
   websocketEndpointRuntimeObjectName OBJECT-TYPE
      SYNTAX      OCTET STRING
      MAX-ACCESS  read-only
      STATUS      current
      DESCRIPTION "ObjectName column"
      ::= { websocketEndpointRuntimeEntry 2  }
   
   
   websocketEndpointRuntimeOpenSessionsCount OBJECT-TYPE
      SYNTAX      Integer32
      MAX-ACCESS  read-only
      STATUS      current
      DESCRIPTION "Get the number of currently open sessions. "
      ::= { websocketEndpointRuntimeEntry 3  }
   
   
   websocketEndpointRuntimeMaximalReceivedMessageSize OBJECT-TYPE
      SYNTAX      Counter64
      MAX-ACCESS  read-only
      STATUS      current
      DESCRIPTION "Get the size of the largest message received since the start of monitoring. "
      ::= { websocketEndpointRuntimeEntry 4  }
   
   
   websocketEndpointRuntimeAverageReceivedMessageSize OBJECT-TYPE
      SYNTAX      Counter64
      MAX-ACCESS  read-only
      STATUS      current
      DESCRIPTION "Get the average size of all of the messages received since the start of monitoring. "
      ::= { websocketEndpointRuntimeEntry 5  }
   
   
   websocketEndpointRuntimeSentMessagesCountPerSecond OBJECT-TYPE
      SYNTAX      Counter64
      MAX-ACCESS  read-only
      STATUS      current
      DESCRIPTION "Get the average number of sent messages per second. "
      ::= { websocketEndpointRuntimeEntry 6  }
   
   
   websocketEndpointRuntimeName OBJECT-TYPE
      SYNTAX      OCTET STRING
      MAX-ACCESS  read-only
      STATUS      current
      DESCRIPTION "The name of this configuration. WebLogic Server uses an MBean to implement and persist the configuration. "
      ::= { websocketEndpointRuntimeEntry 7  }
   
   
   websocketEndpointRuntimeSentMessagesCount OBJECT-TYPE
      SYNTAX      Counter64
      MAX-ACCESS  read-only
      STATUS      current
      DESCRIPTION "Get the total number of messages sent since the start of monitoring. "
      ::= { websocketEndpointRuntimeEntry 8  }
   
   
   websocketEndpointRuntimeAverageSentMessageSize OBJECT-TYPE
      SYNTAX      Counter64
      MAX-ACCESS  read-only
      STATUS      current
      DESCRIPTION "Get the average size of all of the messages sent since the start of monitoring. "
      ::= { websocketEndpointRuntimeEntry 9  }
   
   
   websocketEndpointRuntimeMinimalSentMessageSize OBJECT-TYPE
      SYNTAX      Counter64
      MAX-ACCESS  read-only
      STATUS      current
      DESCRIPTION "Get the size of the smallest message sent since the start of monitoring. "
      ::= { websocketEndpointRuntimeEntry 10  }
   
   
   websocketEndpointRuntimeMaximalSentMessageSize OBJECT-TYPE
      SYNTAX      Counter64
      MAX-ACCESS  read-only
      STATUS      current
      DESCRIPTION "Get the size of the largest message sent since the start of monitoring. "
      ::= { websocketEndpointRuntimeEntry 11  }
   
   
   websocketEndpointRuntimeReceivedMessagesCountPerSecond OBJECT-TYPE
      SYNTAX      Counter64
      MAX-ACCESS  read-only
      STATUS      current
      DESCRIPTION "Get the average number of received messages per second. "
      ::= { websocketEndpointRuntimeEntry 12  }
   
   
   websocketEndpointRuntimeEndpointClassName OBJECT-TYPE
      SYNTAX      OCTET STRING
      MAX-ACCESS  read-only
      STATUS      current
      DESCRIPTION "Get the class name of the endpoint. "
      ::= { websocketEndpointRuntimeEntry 13  }
   
   
   websocketEndpointRuntimeEndpointPath OBJECT-TYPE
      SYNTAX      OCTET STRING
      MAX-ACCESS  read-only
      STATUS      current
      DESCRIPTION "Get the path on which the endpoint is registered. "
      ::= { websocketEndpointRuntimeEntry 14  }
   
   
   websocketEndpointRuntimeMaximalOpenSessionsCount OBJECT-TYPE
      SYNTAX      Integer32
      MAX-ACCESS  read-only
      STATUS      current
      DESCRIPTION "Get the maximal number of open sessions since the start of monitoring. "
      ::= { websocketEndpointRuntimeEntry 15  }
   
   
   websocketEndpointRuntimeMinimalReceivedMessageSize OBJECT-TYPE
      SYNTAX      Counter64
      MAX-ACCESS  read-only
      STATUS      current
      DESCRIPTION "Get the size of the smallest message received since the start of monitoring. "
      ::= { websocketEndpointRuntimeEntry 16  }
   
   
   websocketEndpointRuntimeType OBJECT-TYPE
      SYNTAX      OCTET STRING
      MAX-ACCESS  read-only
      STATUS      current
      DESCRIPTION "Returns the type of the MBean. "
      ::= { websocketEndpointRuntimeEntry 17  }
   
   
   websocketEndpointRuntimeReceivedMessagesCount OBJECT-TYPE
      SYNTAX      Counter64
      MAX-ACCESS  read-only
      STATUS      current
      DESCRIPTION "Get the total number of messages received since the start of monitoring. "
      ::= { websocketEndpointRuntimeEntry 18  }
   
   
   adminVirtualTargetTable OBJECT-TYPE
      SYNTAX      SEQUENCE OF AdminVirtualTargetEntry
      MAX-ACCESS  not-accessible
      STATUS      current
      DESCRIPTION " "
      ::= { wls 2455  }
      
   
   adminVirtualTargetEntry OBJECT-TYPE
      SYNTAX      AdminVirtualTargetEntry
      MAX-ACCESS  not-accessible
      STATUS      current
      DESCRIPTION "Generated SNMP Table Entry."
      INDEX { adminVirtualTargetIndex}
      ::= { adminVirtualTargetTable 1 }
      
   AdminVirtualTargetEntry ::=
      SEQUENCE
      {
         adminVirtualTargetIndex OCTET STRING,
         adminVirtualTargetObjectName OCTET STRING,
         adminVirtualTargetPortOffset Integer32,
         adminVirtualTargetName OCTET STRING,
         adminVirtualTargetType OCTET STRING,
         adminVirtualTargetPartitionChannel OCTET STRING,
         adminVirtualTargetUriPrefix OCTET STRING,
         adminVirtualTargetHostNames OCTET STRING,
         adminVirtualTargetExplicitPort Integer32,
         adminVirtualTargetDeploymentOrder Integer32,
         adminVirtualTargetTags OCTET STRING
      }
      
   
   adminVirtualTargetIndex OBJECT-TYPE
      SYNTAX      OCTET STRING
      MAX-ACCESS  not-accessible
      STATUS      current
      DESCRIPTION "Index column"
      ::= { adminVirtualTargetEntry 1  }
   
   
   adminVirtualTargetObjectName OBJECT-TYPE
      SYNTAX      OCTET STRING
      MAX-ACCESS  read-only
      STATUS      current
      DESCRIPTION "ObjectName column"
      ::= { adminVirtualTargetEntry 2  }
   
   
   adminVirtualTargetPortOffset OBJECT-TYPE
      SYNTAX      Integer32
      MAX-ACCESS  read-only
      STATUS      current
      DESCRIPTION "The port offset for this virtual target. If set to the minimum value, the port offset is not set. "
      ::= { adminVirtualTargetEntry 3  }
   
   
   adminVirtualTargetName OBJECT-TYPE
      SYNTAX      OCTET STRING
      MAX-ACCESS  read-only
      STATUS      current
      DESCRIPTION "The user-specified name of this MBean instance.  This name is included as one of the key properties in the MBean's javax.management.ObjectName:  Name=user-specified-name "
      ::= { adminVirtualTargetEntry 4  }
   
   
   adminVirtualTargetType OBJECT-TYPE
      SYNTAX      OCTET STRING
      MAX-ACCESS  read-only
      STATUS      current
      DESCRIPTION "Returns the type of the MBean. "
      ::= { adminVirtualTargetEntry 5  }
   
   
   adminVirtualTargetPartitionChannel OBJECT-TYPE
      SYNTAX      OCTET STRING
      MAX-ACCESS  read-only
      STATUS      current
      DESCRIPTION "The channel name to be used as a reference for creating a partition specific channel. "
      ::= { adminVirtualTargetEntry 6  }
   
   
   adminVirtualTargetUriPrefix OBJECT-TYPE
      SYNTAX      OCTET STRING
      MAX-ACCESS  read-only
      STATUS      current
      DESCRIPTION "The URI prefix for this virtual target. "
      ::= { adminVirtualTargetEntry 7  }
   
   
   adminVirtualTargetHostNames OBJECT-TYPE
      SYNTAX      OCTET STRING
      MAX-ACCESS  read-only
      STATUS      current
      DESCRIPTION "Host names, separated by line breaks, for which this virtual target will serve requests. "
      ::= { adminVirtualTargetEntry 8  }
   
   
   adminVirtualTargetExplicitPort OBJECT-TYPE
      SYNTAX      Integer32
      MAX-ACCESS  read-only
      STATUS      current
      DESCRIPTION "Get the explicit port for this virtual target. "
      ::= { adminVirtualTargetEntry 9  }
   
   
   adminVirtualTargetDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters. "
      ::= { adminVirtualTargetEntry 10  }
   
   
   adminVirtualTargetTags OBJECT-TYPE
      SYNTAX      OCTET STRING
      MAX-ACCESS  read-only
      STATUS      current
      DESCRIPTION "Return all tags on this Configuration MBean "
      ::= { adminVirtualTargetEntry 11  }
   
   
   partitionUserFileSystemTable OBJECT-TYPE
      SYNTAX      SEQUENCE OF PartitionUserFileSystemEntry
      MAX-ACCESS  not-accessible
      STATUS      current
      DESCRIPTION "Defines the partition file system configuration. "
      ::= { wls 2460  }
      
   
   partitionUserFileSystemEntry OBJECT-TYPE
      SYNTAX      PartitionUserFileSystemEntry
      MAX-ACCESS  not-accessible
      STATUS      current
      DESCRIPTION "Generated SNMP Table Entry."
      INDEX { partitionUserFileSystemIndex}
      ::= { partitionUserFileSystemTable 1 }
      
   PartitionUserFileSystemEntry ::=
      SEQUENCE
      {
         partitionUserFileSystemIndex OCTET STRING,
         partitionUserFileSystemObjectName OCTET STRING,
         partitionUserFileSystemRoot OCTET STRING,
         partitionUserFileSystemName OCTET STRING,
         partitionUserFileSystemType OCTET STRING,
         partitionUserFileSystemPreserved OCTET STRING,
         partitionUserFileSystemCreateOnDemand OCTET STRING,
         partitionUserFileSystemTags OCTET STRING
      }
      
   
   partitionUserFileSystemIndex OBJECT-TYPE
      SYNTAX      OCTET STRING
      MAX-ACCESS  not-accessible
      STATUS      current
      DESCRIPTION "Index column"
      ::= { partitionUserFileSystemEntry 1  }
   
   
   partitionUserFileSystemObjectName OBJECT-TYPE
      SYNTAX      OCTET STRING
      MAX-ACCESS  read-only
      STATUS      current
      DESCRIPTION "ObjectName column"
      ::= { partitionUserFileSystemEntry 2  }
   
   
   partitionUserFileSystemRoot OBJECT-TYPE
      SYNTAX      OCTET STRING
      MAX-ACCESS  read-only
      STATUS      current
      DESCRIPTION "The full path to the root of this file subsystem of the partition. "
      ::= { partitionUserFileSystemEntry 3  }
   
   
   partitionUserFileSystemName OBJECT-TYPE
      SYNTAX      OCTET STRING
      MAX-ACCESS  read-only
      STATUS      current
      DESCRIPTION "The user-specified name of this MBean instance.  This name is included as one of the key properties in the MBean's javax.management.ObjectName:  Name=user-specified-name "
      ::= { partitionUserFileSystemEntry 4  }
   
   
   partitionUserFileSystemType OBJECT-TYPE
      SYNTAX      OCTET STRING
      MAX-ACCESS  read-only
      STATUS      current
      DESCRIPTION "Returns the type of the MBean. "
      ::= { partitionUserFileSystemEntry 5  }
   
   
   partitionUserFileSystemPreserved OBJECT-TYPE
      SYNTAX      OCTET STRING
      MAX-ACCESS  read-only
      STATUS      current
      DESCRIPTION "Specifies whether the file system should be preserved when the partition is deleted. "
      ::= { partitionUserFileSystemEntry 6  }
   
   
   partitionUserFileSystemCreateOnDemand OBJECT-TYPE
      SYNTAX      OCTET STRING
      MAX-ACCESS  read-only
      STATUS      current
      DESCRIPTION "Specifies whether the file system should be created on-demand when the partition is first started. "
      ::= { partitionUserFileSystemEntry 7  }
   
   
   partitionUserFileSystemTags OBJECT-TYPE
      SYNTAX      OCTET STRING
      MAX-ACCESS  read-only
      STATUS      current
      DESCRIPTION "Return all tags on this Configuration MBean "
      ::= { partitionUserFileSystemEntry 8  }
   
   
   restartLoopProtectionTable OBJECT-TYPE
      SYNTAX      SEQUENCE OF RestartLoopProtectionEntry
      MAX-ACCESS  not-accessible
      STATUS      current
      DESCRIPTION " {@code RestartLoopProtectionMBean} defines the configuration to stop the partition from entering an endless restart loop. It is an optional configuration and when enabled it is a resource manager wide configuration.  "
      ::= { wls 2465  }
      
   
   restartLoopProtectionEntry OBJECT-TYPE
      SYNTAX      RestartLoopProtectionEntry
      MAX-ACCESS  not-accessible
      STATUS      current
      DESCRIPTION "Generated SNMP Table Entry."
      INDEX { restartLoopProtectionIndex}
      ::= { restartLoopProtectionTable 1 }
      
   RestartLoopProtectionEntry ::=
      SEQUENCE
      {
         restartLoopProtectionIndex OCTET STRING,
         restartLoopProtectionObjectName OCTET STRING,
         restartLoopProtectionMaxRestartAllowed Counter64,
         restartLoopProtectionMaxRestartAllowedInterval Counter64,
         restartLoopProtectionRestartDelay Counter64,
         restartLoopProtectionName OCTET STRING,
         restartLoopProtectionType OCTET STRING,
         restartLoopProtectionRestartLoopProtectionEnabled OCTET STRING,
         restartLoopProtectionTags OCTET STRING
      }
      
   
   restartLoopProtectionIndex OBJECT-TYPE
      SYNTAX      OCTET STRING
      MAX-ACCESS  not-accessible
      STATUS      current
      DESCRIPTION "Index column"
      ::= { restartLoopProtectionEntry 1  }
   
   
   restartLoopProtectionObjectName OBJECT-TYPE
      SYNTAX      OCTET STRING
      MAX-ACCESS  read-only
      STATUS      current
      DESCRIPTION "ObjectName column"
      ::= { restartLoopProtectionEntry 2  }
   
   
   restartLoopProtectionMaxRestartAllowed OBJECT-TYPE
      SYNTAX      Counter64
      MAX-ACCESS  read-only
      STATUS      current
      DESCRIPTION "Gets the value of max-restart-allowed. max-restart-allowed is defined as the maximum number of RCM initiated partition restarts allowed in the specified time interval(as specified by max-restart-allowed-interval), after which the partition will be halted upon an RCM initiated request to restart the partition. "
      ::= { restartLoopProtectionEntry 3  }
   
   
   restartLoopProtectionMaxRestartAllowedInterval OBJECT-TYPE
      SYNTAX      Counter64
      MAX-ACCESS  read-only
      STATUS      current
      DESCRIPTION "Gets the value of max-restart-allowed-interval. The max-restart-allowed-interval is defined as a fixed-width, sliding-window time interval (in seconds) within which the specified number (as specified by max-restart-allowed) of RCM initiated partition restarts are permitted. A RCM initiated request to restart the partition that exceeds the given max-restart-allowed number in the given max-restart-allowed-interval will lead to the partition being halted than being restarted. "
      ::= { restartLoopProtectionEntry 4  }
   
   
   restartLoopProtectionRestartDelay OBJECT-TYPE
      SYNTAX      Counter64
      MAX-ACCESS  read-only
      STATUS      current
      DESCRIPTION "The restart delay. A restart delay introduces a delay before starting the partition, as part of the RCM initiated restart action. "
      ::= { restartLoopProtectionEntry 5  }
   
   
   restartLoopProtectionName OBJECT-TYPE
      SYNTAX      OCTET STRING
      MAX-ACCESS  read-only
      STATUS      current
      DESCRIPTION "The user-specified name of this MBean instance.  This name is included as one of the key properties in the MBean's javax.management.ObjectName:  Name=user-specified-name "
      ::= { restartLoopProtectionEntry 6  }
   
   
   restartLoopProtectionType OBJECT-TYPE
      SYNTAX      OCTET STRING
      MAX-ACCESS  read-only
      STATUS      current
      DESCRIPTION "Returns the type of the MBean. "
      ::= { restartLoopProtectionEntry 7  }
   
   
   restartLoopProtectionRestartLoopProtectionEnabled OBJECT-TYPE
      SYNTAX      OCTET STRING
      MAX-ACCESS  read-only
      STATUS      current
      DESCRIPTION "Checks if restart loop protection is enabled. "
      ::= { restartLoopProtectionEntry 8  }
   
   
   restartLoopProtectionTags OBJECT-TYPE
      SYNTAX      OCTET STRING
      MAX-ACCESS  read-only
      STATUS      current
      DESCRIPTION "Return all tags on this Configuration MBean "
      ::= { restartLoopProtectionEntry 9  }
   
   
   secureModeTable OBJECT-TYPE
      SYNTAX      SEQUENCE OF SecureModeEntry
      MAX-ACCESS  not-accessible
      STATUS      current
      DESCRIPTION "Controls the behavior of Secure Mode in the current WebLogic Server domain. Attributes control whether secure mode is enabled and control the validation that is performed during startup. "
      ::= { wls 2470  }
      
   
   secureModeEntry OBJECT-TYPE
      SYNTAX      SecureModeEntry
      MAX-ACCESS  not-accessible
      STATUS      current
      DESCRIPTION "Generated SNMP Table Entry."
      INDEX { secureModeIndex}
      ::= { secureModeTable 1 }
      
   SecureModeEntry ::=
      SEQUENCE
      {
         secureModeIndex      OCTET STRING,
         secureModeObjectName OCTET STRING,
         secureModeRestrictiveJMXPolicies OCTET STRING,
         secureModeWarnOnInsecureFileSystem OCTET STRING,
         secureModeSecureModeEnabled OCTET STRING,
         secureModeWarnOnJavaSecurityManager OCTET STRING,
         secureModeWarnOnInsecureSSL OCTET STRING,
         secureModeName       OCTET STRING,
         secureModeType       OCTET STRING,
         secureModeWarnOnAuditing OCTET STRING,
         secureModeWarnOnInsecureApplications OCTET STRING,
         secureModeTags       OCTET STRING
      }
      
   
   secureModeIndex OBJECT-TYPE
      SYNTAX      OCTET STRING
      MAX-ACCESS  not-accessible
      STATUS      current
      DESCRIPTION "Index column"
      ::= { secureModeEntry 1  }
   
   
   secureModeObjectName OBJECT-TYPE
      SYNTAX      OCTET STRING
      MAX-ACCESS  read-only
      STATUS      current
      DESCRIPTION "ObjectName column"
      ::= { secureModeEntry 2  }
   
   
   secureModeRestrictiveJMXPolicies OBJECT-TYPE
      SYNTAX      OCTET STRING
      MAX-ACCESS  read-only
      STATUS      current
      DESCRIPTION "Returns whether restrictive policies will be used for JMX authorization.  If secure mode is enabled and restrictive policies are enabled, then the default policies for JMX only allow MBean access to the standard WLS roles (Admin, Deployer, Operator, or Monitor). If changed as part of a non-dynamic activation, then the ServerSecurityRuntimeMBean.resetDefaultPolicies method should also be invoked.  "
      ::= { secureModeEntry 3  }
   
   
   secureModeWarnOnInsecureFileSystem OBJECT-TYPE
      SYNTAX      OCTET STRING
      MAX-ACCESS  read-only
      STATUS      current
      DESCRIPTION "Returns whether warnings should be logged if the File System is not secure.   If secure mode is enabled and warnings are enabled, then messages will be logged for insecure file system setting. "
      ::= { secureModeEntry 4  }
   
   
   secureModeSecureModeEnabled OBJECT-TYPE
      SYNTAX      OCTET STRING
      MAX-ACCESS  read-only
      STATUS      current
      DESCRIPTION "Returns whether the domain will run in secure mode.  In secure mode, the configuration defaults are those recommended for securing a domain. The authorization policies for JNDI and MBean access are more restrictive in secure mode. In addition, WLS will validate the domain configuration and log warnings and errors for any insecure settings.   Secure mode requires the domain to be in production mode.  "
      ::= { secureModeEntry 5  }
   
   
   secureModeWarnOnJavaSecurityManager OBJECT-TYPE
      SYNTAX      OCTET STRING
      MAX-ACCESS  read-only
      STATUS      current
      DESCRIPTION "Returns whether warnings should be logged if the Java Security Manager is not enabled.   If secure mode is enabled and warning is enabled, then a messages will be logged if the Java Security Manager is not enabled. "
      ::= { secureModeEntry 6  }
   
   
   secureModeWarnOnInsecureSSL OBJECT-TYPE
      SYNTAX      OCTET STRING
      MAX-ACCESS  read-only
      STATUS      current
      DESCRIPTION "Returns whether warnings should be logged if the SSL configuration is not secure.   If secure mode is enabled and warnings are enabled, then messages will be logged for insecure SSL configuration settings. "
      ::= { secureModeEntry 7  }
   
   
   secureModeName OBJECT-TYPE
      SYNTAX      OCTET STRING
      MAX-ACCESS  read-only
      STATUS      current
      DESCRIPTION "The user-specified name of this MBean instance.  This name is included as one of the key properties in the MBean's javax.management.ObjectName:  Name=user-specified-name "
      ::= { secureModeEntry 8  }
   
   
   secureModeType OBJECT-TYPE
      SYNTAX      OCTET STRING
      MAX-ACCESS  read-only
      STATUS      current
      DESCRIPTION "Returns the type of the MBean. "
      ::= { secureModeEntry 9  }
   
   
   secureModeWarnOnAuditing OBJECT-TYPE
      SYNTAX      OCTET STRING
      MAX-ACCESS  read-only
      STATUS      current
      DESCRIPTION "Returns whether warnings should be logged if auditing not enabled.   If secure mode is enabled and warnings are enabled, then messages will be logged if auditing is not enabled. "
      ::= { secureModeEntry 10  }
   
   
   secureModeWarnOnInsecureApplications OBJECT-TYPE
      SYNTAX      OCTET STRING
      MAX-ACCESS  read-only
      STATUS      current
      DESCRIPTION "Returns whether warnings should be logged if applications are not secure.   If secure mode is enabled and warnings are enabled, then messages will be logged for insecure application elements. "
      ::= { secureModeEntry 11  }
   
   
   secureModeTags OBJECT-TYPE
      SYNTAX      OCTET STRING
      MAX-ACCESS  read-only
      STATUS      current
      DESCRIPTION "Return all tags on this Configuration MBean "
      ::= { secureModeEntry 12  }
   
   
   partitionUserFileSystemManagerTable OBJECT-TYPE
      SYNTAX      SEQUENCE OF PartitionUserFileSystemManagerEntry
      MAX-ACCESS  not-accessible
      STATUS      current
      DESCRIPTION "This class is used for partition user file system handling.  "
      ::= { wls 2475  }
      
   
   partitionUserFileSystemManagerEntry OBJECT-TYPE
      SYNTAX      PartitionUserFileSystemManagerEntry
      MAX-ACCESS  not-accessible
      STATUS      current
      DESCRIPTION "Generated SNMP Table Entry."
      INDEX { partitionUserFileSystemManagerIndex}
      ::= { partitionUserFileSystemManagerTable 1 }
      
   PartitionUserFileSystemManagerEntry ::=
      SEQUENCE
      {
         partitionUserFileSystemManagerIndex OCTET STRING,
         partitionUserFileSystemManagerObjectName OCTET STRING,
         partitionUserFileSystemManagerName OCTET STRING,
         partitionUserFileSystemManagerType OCTET STRING
      }
      
   
   partitionUserFileSystemManagerIndex OBJECT-TYPE
      SYNTAX      OCTET STRING
      MAX-ACCESS  not-accessible
      STATUS      current
      DESCRIPTION "Index column"
      ::= { partitionUserFileSystemManagerEntry 1  }
   
   
   partitionUserFileSystemManagerObjectName OBJECT-TYPE
      SYNTAX      OCTET STRING
      MAX-ACCESS  read-only
      STATUS      current
      DESCRIPTION "ObjectName column"
      ::= { partitionUserFileSystemManagerEntry 2  }
   
   
   partitionUserFileSystemManagerName OBJECT-TYPE
      SYNTAX      OCTET STRING
      MAX-ACCESS  read-only
      STATUS      current
      DESCRIPTION "The name of this configuration. WebLogic Server uses an MBean to implement and persist the configuration. "
      ::= { partitionUserFileSystemManagerEntry 3  }
   
   
   partitionUserFileSystemManagerType OBJECT-TYPE
      SYNTAX      OCTET STRING
      MAX-ACCESS  read-only
      STATUS      current
      DESCRIPTION "Returns the type of the MBean. "
      ::= { partitionUserFileSystemManagerEntry 4  }
   
   
   jdbcPropertyOverrideTable OBJECT-TYPE
      SYNTAX      SEQUENCE OF JdbcPropertyOverrideEntry
      MAX-ACCESS  not-accessible
      STATUS      current
      DESCRIPTION "Defines a JDBC driver property override. "
      ::= { wls 2480  }
      
   
   jdbcPropertyOverrideEntry OBJECT-TYPE
      SYNTAX      JdbcPropertyOverrideEntry
      MAX-ACCESS  not-accessible
      STATUS      current
      DESCRIPTION "Generated SNMP Table Entry."
      INDEX { jdbcPropertyOverrideIndex}
      ::= { jdbcPropertyOverrideTable 1 }
      
   JdbcPropertyOverrideEntry ::=
      SEQUENCE
      {
         jdbcPropertyOverrideIndex OCTET STRING,
         jdbcPropertyOverrideObjectName OCTET STRING,
         jdbcPropertyOverrideName OCTET STRING,
         jdbcPropertyOverrideSysPropValue OCTET STRING,
         jdbcPropertyOverrideType OCTET STRING,
         jdbcPropertyOverrideValue OCTET STRING,
         jdbcPropertyOverrideTags OCTET STRING
      }
      
   
   jdbcPropertyOverrideIndex OBJECT-TYPE
      SYNTAX      OCTET STRING
      MAX-ACCESS  not-accessible
      STATUS      current
      DESCRIPTION "Index column"
      ::= { jdbcPropertyOverrideEntry 1  }
   
   
   jdbcPropertyOverrideObjectName OBJECT-TYPE
      SYNTAX      OCTET STRING
      MAX-ACCESS  read-only
      STATUS      current
      DESCRIPTION "ObjectName column"
      ::= { jdbcPropertyOverrideEntry 2  }
   
   
   jdbcPropertyOverrideName OBJECT-TYPE
      SYNTAX      OCTET STRING
      MAX-ACCESS  read-only
      STATUS      current
      DESCRIPTION "The user-specified name of this MBean instance.  This name is included as one of the key properties in the MBean's javax.management.ObjectName:  Name=user-specified-name "
      ::= { jdbcPropertyOverrideEntry 3  }
   
   
   jdbcPropertyOverrideSysPropValue OBJECT-TYPE
      SYNTAX      OCTET STRING
      MAX-ACCESS  read-only
      STATUS      current
      DESCRIPTION "The value of the property defined as a system property. "
      ::= { jdbcPropertyOverrideEntry 4  }
   
   
   jdbcPropertyOverrideType OBJECT-TYPE
      SYNTAX      OCTET STRING
      MAX-ACCESS  read-only
      STATUS      current
      DESCRIPTION "Returns the type of the MBean. "
      ::= { jdbcPropertyOverrideEntry 5  }
   
   
   jdbcPropertyOverrideValue OBJECT-TYPE
      SYNTAX      OCTET STRING
      MAX-ACCESS  read-only
      STATUS      current
      DESCRIPTION "The value of the property. "
      ::= { jdbcPropertyOverrideEntry 6  }
   
   
   jdbcPropertyOverrideTags OBJECT-TYPE
      SYNTAX      OCTET STRING
      MAX-ACCESS  read-only
      STATUS      current
      DESCRIPTION "Return all tags on this Configuration MBean "
      ::= { jdbcPropertyOverrideEntry 7  }
   
   
   tLSTable OBJECT-TYPE
      SYNTAX      SEQUENCE OF TLSEntry
      MAX-ACCESS  not-accessible
      STATUS      current
      DESCRIPTION "A TLSMBean contains SSL/TLS connection parameters and may be organized in a user-defined inheritance hierarchy and referenced by name.  TODO: since 7.0.0.0 TODO: delegateBean TODO: validator TLSValidator.validateTLS "
      ::= { wls 2485  }
      
   
   tLSEntry OBJECT-TYPE
      SYNTAX      TLSEntry
      MAX-ACCESS  not-accessible
      STATUS      current
      DESCRIPTION "Generated SNMP Table Entry."
      INDEX { tLSIndex}
      ::= { tLSTable 1 }
      
   TLSEntry ::=
      SEQUENCE
      {
         tLSIndex             OCTET STRING,
         tLSObjectName        OCTET STRING,
         tLSHostnameVerificationIgnored OCTET STRING,
         tLSTwoWaySSLEnabled  OCTET STRING,
         tLSInboundCertificateValidation OCTET STRING,
         tLSName              OCTET STRING,
         tLSCiphersuites      OCTET STRING,
         tLSOutboundCertificateValidation OCTET STRING,
         tLSIdentityKeyStoreType OCTET STRING,
         tLSAllowUnencryptedNullCipher OCTET STRING,
         tLSClientCertificateEnforced OCTET STRING,
         tLSSSLv2HelloEnabled OCTET STRING,
         tLSTags              OCTET STRING,
         tLSUsage             OCTET STRING,
         tLSIdentityKeyStoreFileName OCTET STRING,
         tLSMinimumTLSProtocolVersion OCTET STRING,
         tLSHostnameVerifier  OCTET STRING,
         tLSType              OCTET STRING,
         tLSTrustKeyStoreType OCTET STRING,
         tLSTrustKeyStoreFileName OCTET STRING,
         tLSIdentityPrivateKeyAlias OCTET STRING
      }
      
   
   tLSIndex OBJECT-TYPE
      SYNTAX      OCTET STRING
      MAX-ACCESS  not-accessible
      STATUS      current
      DESCRIPTION "Index column"
      ::= { tLSEntry 1  }
   
   
   tLSObjectName OBJECT-TYPE
      SYNTAX      OCTET STRING
      MAX-ACCESS  read-only
      STATUS      current
      DESCRIPTION "ObjectName column"
      ::= { tLSEntry 2  }
   
   
   tLSHostnameVerificationIgnored OBJECT-TYPE
      SYNTAX      OCTET STRING
      MAX-ACCESS  read-only
      STATUS      current
      DESCRIPTION "Specifies whether to ignore the installed implementation of the weblogic.security.SSL.HostnameVerifier interface (when this server is acting as a client to another application server). "
      ::= { tLSEntry 3  }
   
   
   tLSTwoWaySSLEnabled OBJECT-TYPE
      SYNTAX      OCTET STRING
      MAX-ACCESS  read-only
      STATUS      current
      DESCRIPTION "Specifies whether to use two way SSL. "
      ::= { tLSEntry 4  }
   
   
   tLSInboundCertificateValidation OBJECT-TYPE
      SYNTAX      OCTET STRING
      MAX-ACCESS  read-only
      STATUS      current
      DESCRIPTION "Indicates the client certificate validation rules for inbound SSL.  This attribute only applies to TLS connections using 2-way SSL. "
      ::= { tLSEntry 5  }
   
   
   tLSName OBJECT-TYPE
      SYNTAX      OCTET STRING
      MAX-ACCESS  read-only
      STATUS      current
      DESCRIPTION "The name of this set of TLS connection parameters. "
      ::= { tLSEntry 6  }
   
   
   tLSCiphersuites OBJECT-TYPE
      SYNTAX      OCTET STRING
      MAX-ACCESS  read-only
      STATUS      current
      DESCRIPTION "Specifies the cipher suites for the TLS connection.  The strongest negotiated cipher suite is chosen during the SSL handshake. The set of cipher suites used by default by JSSE depends on the specific JDK version with which WebLogic Server is configured.  For a list of possible values, see Cipher Suites. "
      ::= { tLSEntry 7  }
   
   
   tLSOutboundCertificateValidation OBJECT-TYPE
      SYNTAX      OCTET STRING
      MAX-ACCESS  read-only
      STATUS      current
      DESCRIPTION "Indicates the server certificate validation rules for outbound SSL.  This attribute always applies to outbound SSL that is part of WebLogic Server (that is, an Administration Server talking to the Node Manager). It does not apply to application code in the server that is using outbound SSL unless the application code uses a weblogic.security.SSL.ServerTrustManager that is configured to use outbound SSL validation. "
      ::= { tLSEntry 8  }
   
   
   tLSIdentityKeyStoreType OBJECT-TYPE
      SYNTAX      OCTET STRING
      MAX-ACCESS  read-only
      STATUS      current
      DESCRIPTION "The type of the keystore. Generally, this is JKS. If using the Oracle Key Store Service, this would be KSS  If empty or null, then the JDK's default keystore type (specified in java.security) is used. The identity key store type is only used if ServerMBean.KeyStores is CUSTOM_IDENTITY_AND_JAVA_STANDARD_TRUST, CUSTOM_IDENTITY_AND_CUSTOM_TRUST or CUSTOM_IDENTITY_AND_COMMAND_LINE_TRUST. "
      ::= { tLSEntry 9  }
   
   
   tLSAllowUnencryptedNullCipher OBJECT-TYPE
      SYNTAX      OCTET STRING
      MAX-ACCESS  read-only
      STATUS      current
      DESCRIPTION "Specifies whether NULL ciphers are allowed for the TLS connection.  When a SSL server and a SSL client try to negotiate a commonly supported Cipher, there is a chance that they may end up with nothing in common. A NullCipher is a cipher providing no encryption for the SSL message between the client and server, and it may temporarily be used in the development environment if the SSL server and client share no common cipher for some reason. This is not a standard SSL feature, some SSL provider supports this feature.  The AllowUnEncryptedNullCipher flag is used to control whether the NullCipher feature is enabled or not, if true, the SSL message may be unencrypted when SSL server and client shares no common cipher.  This AllowUnEncryptedNullCipher flag is only effective to SSL providers which support the NullCipher feature.  Warning: this NullCipher feature should NOT be enabled for a production environment, it may leads to unencrypted SSL message  By default, the AllowUnEncryptedNullCipher is false * "
      ::= { tLSEntry 10  }
   
   
   tLSClientCertificateEnforced OBJECT-TYPE
      SYNTAX      OCTET STRING
      MAX-ACCESS  read-only
      STATUS      current
      DESCRIPTION "Specifies whether clients must present digital certificates from a trusted certificate authority. "
      ::= { tLSEntry 11  }
   
   
   tLSSSLv2HelloEnabled OBJECT-TYPE
      SYNTAX      OCTET STRING
      MAX-ACCESS  read-only
      STATUS      current
      DESCRIPTION "Indicates whether SSLv2Hello is enabled in a TLS connection. "
      ::= { tLSEntry 12  }
   
   
   tLSTags OBJECT-TYPE
      SYNTAX      OCTET STRING
      MAX-ACCESS  read-only
      STATUS      current
      DESCRIPTION "Return all tags on this Configuration MBean "
      ::= { tLSEntry 13  }
   
   
   tLSUsage OBJECT-TYPE
      SYNTAX      OCTET STRING
      MAX-ACCESS  read-only
      STATUS      current
      DESCRIPTION "The declared usages of this SSL/TLS configuration. "
      ::= { tLSEntry 14  }
   
   
   tLSIdentityKeyStoreFileName OBJECT-TYPE
      SYNTAX      OCTET STRING
      MAX-ACCESS  read-only
      STATUS      current
      DESCRIPTION "The source of the identity keystore.  For a JKS keystore, the source is the path and file name. For an Oracle Key Store Service (KSS) keystore, the source is the KSS URI.  If using a JKS keystore, the keystore path name must either be absolute or relative to where the server was booted.  If using a KSS keystore, the keystore URI must be of the form:  kss://system/keystorename  where keystorename is the name of the keystore registered in KSS.  The value in this attribute is only used for a server if ServerMBean.KeyStores is CUSTOM_IDENTITY_AND_JAVA_STANDARD_TRUST, CUSTOM_IDENTITY_AND_CUSTOM_TRUST or CUSTOM_IDENTITY_AND_COMMAND_LINE_TRUST. "
      ::= { tLSEntry 15  }
   
   
   tLSMinimumTLSProtocolVersion OBJECT-TYPE
      SYNTAX      OCTET STRING
      MAX-ACCESS  read-only
      STATUS      current
      DESCRIPTION "Get the minimum SSL/TLS protocol version to be used in a TLS connection. TODO: derivedDefault ((ServerTemplateMBean)(getParent())).getSSL().getMinimumTLSProtocolVersion() "
      ::= { tLSEntry 16  }
   
   
   tLSHostnameVerifier OBJECT-TYPE
      SYNTAX      OCTET STRING
      MAX-ACCESS  read-only
      STATUS      current
      DESCRIPTION "The name of the class that implements the weblogic.security.SSL.HostnameVerifier interface.  This class verifies whether the connection to the host with the hostname from URL should be allowed. The class is used to prevent man-in-the-middle attacks. The weblogic.security.SSL.HostnameVerifier has a verify() method that WebLogic Server calls on the client during the SSL handshake. "
      ::= { tLSEntry 17  }
   
   
   tLSType OBJECT-TYPE
      SYNTAX      OCTET STRING
      MAX-ACCESS  read-only
      STATUS      current
      DESCRIPTION "Returns the type of the MBean. "
      ::= { tLSEntry 18  }
   
   
   tLSTrustKeyStoreType OBJECT-TYPE
      SYNTAX      OCTET STRING
      MAX-ACCESS  read-only
      STATUS      current
      DESCRIPTION "The type of the trust keystore. Generally, this is JKS. If using the Oracle Key Store Service, this would be KSS  If empty or null, then the JDK's default keystore type (specified in java.security) is used. The trust key store type is only used if ServerMBean.KeyStores is CUSTOM_IDENTITY_AND_CUSTOM_TRUST. "
      ::= { tLSEntry 19  }
   
   
   tLSTrustKeyStoreFileName OBJECT-TYPE
      SYNTAX      OCTET STRING
      MAX-ACCESS  read-only
      STATUS      current
      DESCRIPTION "The source of the trust keystore.  For a JKS keystore, the source is the path and file name. For an Oracle Key Store Service (KSS) keystore, the source is the KSS URI.  If using a JKS keystore, the keystore path name must either be absolute or relative to where the server was booted.  If using a KSS keystore, the keystore URI must be of the form:  kss://system/keystorename  where keystorename is the name of the keystore registered in KSS.  The value in this attribute is only used for a server if ServerMBean.KeyStores is CUSTOM_IDENTITY_AND_CUSTOM_TRUST. "
      ::= { tLSEntry 20  }
   
   
   tLSIdentityPrivateKeyAlias OBJECT-TYPE
      SYNTAX      OCTET STRING
      MAX-ACCESS  read-only
      STATUS      current
      DESCRIPTION "The alias of the private key representing the identity for the associated connection. The alias refers to a private key in {@link #getIdentityKeyStoreFileName()} "
      ::= { tLSEntry 21  }
   
   
   webServiceResiliencyTable OBJECT-TYPE
      SYNTAX      SEQUENCE OF WebServiceResiliencyEntry
      MAX-ACCESS  not-accessible
      STATUS      current
      DESCRIPTION "Represents resilience configuration for web services. "
      ::= { wls 2490  }
      
   
   webServiceResiliencyEntry OBJECT-TYPE
      SYNTAX      WebServiceResiliencyEntry
      MAX-ACCESS  not-accessible
      STATUS      current
      DESCRIPTION "Generated SNMP Table Entry."
      INDEX { webServiceResiliencyIndex}
      ::= { webServiceResiliencyTable 1 }
      
   WebServiceResiliencyEntry ::=
      SEQUENCE
      {
         webServiceResiliencyIndex OCTET STRING,
         webServiceResiliencyObjectName OCTET STRING,
         webServiceResiliencyRetryDelay OCTET STRING,
         webServiceResiliencyName OCTET STRING,
         webServiceResiliencyType OCTET STRING,
         webServiceResiliencyRetryCount Integer32,
         webServiceResiliencyTags OCTET STRING
      }
      
   
   webServiceResiliencyIndex OBJECT-TYPE
      SYNTAX      OCTET STRING
      MAX-ACCESS  not-accessible
      STATUS      current
      DESCRIPTION "Index column"
      ::= { webServiceResiliencyEntry 1  }
   
   
   webServiceResiliencyObjectName OBJECT-TYPE
      SYNTAX      OCTET STRING
      MAX-ACCESS  read-only
      STATUS      current
      DESCRIPTION "ObjectName column"
      ::= { webServiceResiliencyEntry 2  }
   
   
   webServiceResiliencyRetryDelay OBJECT-TYPE
      SYNTAX      OCTET STRING
      MAX-ACCESS  read-only
      STATUS      current
      DESCRIPTION "The amount time between retries . Note, this value is only applicable when RetryCount > 0. Defaults to '5000' (5000 milliseconds). "
      ::= { webServiceResiliencyEntry 3  }
   
   
   webServiceResiliencyName OBJECT-TYPE
      SYNTAX      OCTET STRING
      MAX-ACCESS  read-only
      STATUS      current
      DESCRIPTION "The user-specified name of this MBean instance.  This name is included as one of the key properties in the MBean's javax.management.ObjectName:  Name=user-specified-name "
      ::= { webServiceResiliencyEntry 4  }
   
   
   webServiceResiliencyType OBJECT-TYPE
      SYNTAX      OCTET STRING
      MAX-ACCESS  read-only
      STATUS      current
      DESCRIPTION "Returns the type of the MBean. "
      ::= { webServiceResiliencyEntry 5  }
   
   
   webServiceResiliencyRetryCount OBJECT-TYPE
      SYNTAX      Integer32
      MAX-ACCESS  read-only
      STATUS      current
      DESCRIPTION "The number of times a wsdl get request can be retried before it is abandoned. Default value  is zero. "
      ::= { webServiceResiliencyEntry 6  }
   
   
   webServiceResiliencyTags OBJECT-TYPE
      SYNTAX      OCTET STRING
      MAX-ACCESS  read-only
      STATUS      current
      DESCRIPTION "Return all tags on this Configuration MBean "
      ::= { webServiceResiliencyEntry 7  }
   
   
   wlsLogNotification NOTIFICATION-TYPE
      OBJECTS {trapTime, trapServerName, trapMachineName, trapLogThreadId, trapLogTransactionId, trapLogUserId, trapLogSubsystem, trapLogMsgId, trapLogSeverity, trapLogMessage}
      STATUS      current
      DESCRIPTION "The server log."
      ::= { wls 0 60  }
   
   wlsServerStart NOTIFICATION-TYPE
      OBJECTS {trapTime, trapServerName}
      STATUS      current
      DESCRIPTION "This trap is generated when the server was started."
      ::= { wls 0 65  }
   
   wlsServerShutDown NOTIFICATION-TYPE
      OBJECTS {trapTime, trapServerName}
      STATUS      current
      DESCRIPTION "This trap is generated when the server has been shut down."
      ::= { wls 0 70  }
   
   wlsMonitorNotification NOTIFICATION-TYPE
      OBJECTS {trapTime, trapServerName, trapMonitorType, trapMonitorThreshold, trapMonitorValue, trapMBeanName, trapMBeanType, trapAttributeName, trapConfigName}
      STATUS      current
      DESCRIPTION "This trap is generated when any JMX Monitor Notification is received."
      ::= { wls 0 75  }
   
   wlsAttributeChange NOTIFICATION-TYPE
      OBJECTS {trapTime, trapServerName, trapMBeanName, trapMBeanType, trapAttributeName, trapAttributeType, trapAttributeChangeType, trapAttributeOldVal, trapAttributeNewVal, trapConfigName}
      STATUS      current
      DESCRIPTION "This trap is generated when an attribute change is observed."
      ::= { wls 0 80  }
   
   wlsWatchNotification NOTIFICATION-TYPE
      OBJECTS {trapTime, trapDomainName, trapServerName, trapWatchName, trapWatchRuleType, trapWatchRule, trapWatchSeverity, trapWatchData, trapWatchAlarmType, trapWatchAlarmResetPeriod, trapWatchSNMPNotificationName, trapWatchModule}
      STATUS      current
      DESCRIPTION "This trap is generated when a watch rule evaluates to true."
      ::= { wls 0 85  }
   
   wlsALSBAlert NOTIFICATION-TYPE
      OBJECTS {trapALSBAlertTrapType, trapALSBAlertSeverity, trapALSBAlertDomainName, trapALSBAlertServerName, trapALSBAlertAlertId, trapALSBAlertRuleId, trapALSBAlertRuleName, trapALSBAlertRuleCondition, trapALSBAlertAlertTime, trapALSBAlertAnnotation, trapALSBAlertServiceName, trapALSBAlertServicePath}
      STATUS      current
      DESCRIPTION "This trap is generated only in an ALSB environment where an Alert situation has occurred."
      ::= { alsb 0 90  }
   
   
END
